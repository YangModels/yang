submodule Cisco-IOS-XR-ip-udp-oper-sub2 {
  belongs-to Cisco-IOS-XR-ip-udp-oper {
    prefix Cisco-IOS-XR-ip-udp-oper;
  }

  import ietf-inet-types {
    prefix inet;
  }
  import Cisco-IOS-XR-types {
    prefix xr;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR ip-udp package operational data.
     
     Copyright (c) 2013-2018 by Cisco Systems, Inc.
     All rights reserved.";

  revision 2018-08-09 {
    description
      "bind_local field is added to PCB_DETAIL output";
  }
  revision 2018-03-04 {
    description
      "PCB_ID argument is passed in string format.";
  }
  revision 2017-09-07 {
    description
      "Fixed type translation error.";
  }
  revision 2016-02-26 {
    description
      "Descriptions updated.";
  }
  revision 2015-11-09 {
    description
      "IOS XR 6.0 revision.";
  }

  typedef Message-id {
    type uint32;
    description
      "Message id";
  }

  typedef Message-type-igmp {
    type enumeration {
      enum "membership-query" {
        value 17;
        description
          "IGMP Packet type: Membership query";
      }
      enum "v1-membership-report" {
        value 18;
        description
          "IGMP Packet type: V1 membership report";
      }
      enum "dvmrp" {
        value 19;
        description
          "IGMP Packet type: DVMRP";
      }
      enum "pi-mv1" {
        value 20;
        description
          "IGMP Packet type: PIM version 1";
      }
      enum "cisco-trace-messages" {
        value 21;
        description
          "IGMP Packet type: Cisco Trace Messages";
      }
      enum "v2-membership-report" {
        value 22;
        description
          "IGMP Packet type: V2 membership report";
      }
      enum "v2-leave-group" {
        value 23;
        description
          "IGMP Packet type: V2 leave group";
      }
      enum "multicast-traceroute-response" {
        value 30;
        description
          "IGMP Packet type: Multicast traceroute response";
      }
      enum "multicast-traceroute" {
        value 31;
        description
          "IGMP Packet type: MulticastTraceroute";
      }
      enum "v3-membership-report" {
        value 34;
        description
          "IGMP Packet type: V3 membership report";
      }
      enum "multicast-router-advertisement" {
        value 48;
        description
          "IGMP Packet type: Multicast router
           advertisement";
      }
      enum "multicast-router-solicitation" {
        value 49;
        description
          "IGMP Packet type: Multicast router solicitation";
      }
      enum "multicast-router-termination" {
        value 50;
        description
          "IGMP Packet type: Multicast router termination";
      }
    }
    description
      "LPTS IGMP message types";
  }

  typedef Message-igmp {
    type Message-type-igmp;
    description
      "Message igmp";
  }

  typedef Message-type-icmpv6 {
    type enumeration {
      enum "destination-unreachable" {
        value 1;
        description
          "ICMPv6 Packet type: Destination unreachable";
      }
      enum "packet-too-big" {
        value 2;
        description
          "ICMPv6 Packet type: packet too big";
      }
      enum "time-exceeded" {
        value 3;
        description
          "ICMPv6 Packet type: Time exceeded";
      }
      enum "parameter-problem" {
        value 4;
        description
          "ICMPv6 Packet type: Parameter problem";
      }
      enum "echo-request" {
        value 128;
        description
          "ICMPv6 Packet type: Echo request";
      }
      enum "echo-reply" {
        value 129;
        description
          "ICMPv6 Packet type: Echo reply";
      }
      enum "multicast-listener-query" {
        value 130;
        description
          "ICMPv6 Packet type: Multicast listener query";
      }
      enum "multicast-listener-report" {
        value 131;
        description
          "ICMPv6 Packet type: Multicast listener report";
      }
      enum "multicast-listener-done" {
        value 132;
        description
          "ICMPv6 Packet type: Multicast listener done";
      }
      enum "router-solicitation" {
        value 133;
        description
          "ICMPv6 Packet type: Router solicitation";
      }
      enum "router-advertisement" {
        value 134;
        description
          "ICMPv6 Packet type: Router advertisement";
      }
      enum "neighbor-solicitation" {
        value 135;
        description
          "ICMPv6 Packet type: Neighbor solicitation";
      }
      enum "neighbor-advertisement" {
        value 136;
        description
          "ICMPv6 Packet type: Neighbor advertisement";
      }
      enum "redirect-message" {
        value 137;
        description
          "ICMPv6 Packet type: Redirect message";
      }
      enum "router-renumbering" {
        value 138;
        description
          "ICMPv6 Packet type: Router renumbering";
      }
      enum "node-information-query" {
        value 139;
        description
          "ICMPv6 Packet type: Node information query";
      }
      enum "node-information-reply" {
        value 140;
        description
          "ICMPv6 Packet type: Node information reply";
      }
      enum "inverse-neighbor-discovery-solicitaion" {
        value 141;
        description
          "ICMPv6 Packet type: Inverse neighbor discovery
           solicitation message";
      }
      enum "inverse-neighbor-discover-advertisement" {
        value 142;
        description
          "ICMPv6 Packet type: Inverse neighbor discovery
           advertisement message";
      }
      enum "v2-multicast-listener-report" {
        value 143;
        description
          "ICMPv6 Packet type: Version 2 multicast
           listener report";
      }
      enum "home-agent-address-discovery-request" {
        value 144;
        description
          "ICMPv6 Packet type: Home agent address
           discovery request message";
      }
      enum "home-agent-address-discovery-reply" {
        value 145;
        description
          "ICMPv6 Packet type: Home agent address
           discovery reply message";
      }
      enum "mobile-prefix-solicitation" {
        value 146;
        description
          "ICMPv6 Packet type: Mobile prefix solicitation";
      }
      enum "mobile-prefix-advertisement" {
        value 147;
        description
          "ICMPv6 Packet type: Mobile prefix advertisement";
      }
      enum "certification-path-solicitation-message" {
        value 148;
        description
          "ICMPv6 Packet type: Certification path
           solicitation message";
      }
      enum "certification-path-advertisement-message" {
        value 149;
        description
          "ICMPv6 Packet type: Certification path
           advertisement message";
      }
      enum "experimental-mobility-protocols" {
        value 150;
        description
          "ICMPv6 Packet type: ICMP messages utilized by
           experimental mobility  protocols such as
           seamoby";
      }
      enum "multicast-router-advertisement" {
        value 151;
        description
          "ICMPv6 Packet type: Multicast router
           advertisement";
      }
      enum "multicast-router-solicitation" {
        value 152;
        description
          "ICMPv6 Packet type: Multicast router
           solicitation";
      }
      enum "multicast-router-termination" {
        value 153;
        description
          "ICMPv6 Packet type: Multicast router
           termination";
      }
      enum "fmipv6-messages" {
        value 154;
        description
          "ICMPv6 Packet type: FMIPv6 messages";
      }
    }
    description
      "LPTS ICMPv6 message types";
  }

  typedef Message-icmpv6 {
    type Message-type-icmpv6;
    description
      "Message icmpv6";
  }

  typedef Message-type-icmp {
    type enumeration {
      enum "echo-reply" {
        value 0;
        description
          "ICMP Packet type: Echo reply";
      }
      enum "destination-unreachable" {
        value 3;
        description
          "ICMP Packet type: Destination unreachable";
      }
      enum "source-quench" {
        value 4;
        description
          "ICMP Packet type: Source quench";
      }
      enum "redirect" {
        value 5;
        description
          "ICMP Packet type: Redirect";
      }
      enum "alternate-host-address" {
        value 6;
        description
          "ICMP Packet type: Alternate host address";
      }
      enum "echo" {
        value 8;
        description
          "ICMP Packet type: Echo";
      }
      enum "router-advertisement" {
        value 9;
        description
          "ICMP Packet type: Router advertisement";
      }
      enum "router-selection" {
        value 10;
        description
          "ICMP Packet type: Router selection";
      }
      enum "time-exceeded" {
        value 11;
        description
          "ICMP Packet type: Time exceeded";
      }
      enum "parameter-problem" {
        value 12;
        description
          "ICMP Packet type: Parameter problem";
      }
      enum "time-stamp" {
        value 13;
        description
          "ICMP Packet type: Time stamp";
      }
      enum "time-stamp-reply" {
        value 14;
        description
          "ICMP Packet type: Time stamp reply";
      }
      enum "information-request" {
        value 15;
        description
          "ICMP Packet type: Information request";
      }
      enum "information-reply" {
        value 16;
        description
          "ICMP Packet type: Information reply";
      }
      enum "address-mask-request" {
        value 17;
        description
          "ICMP Packet type: Address mask request";
      }
      enum "address-mask-reply" {
        value 18;
        description
          "ICMP Packet type: Address mask reply";
      }
      enum "trace-route" {
        value 30;
        description
          "ICMP Packet type: Trace route";
      }
      enum "datagram-conversion-error" {
        value 31;
        description
          "ICMP Packet type: Datagram Conversion error";
      }
      enum "mobile-host-redirect" {
        value 32;
        description
          "ICMP Packet type: Mobile host redirect";
      }
      enum "where-are-you" {
        value 33;
        description
          "ICMP Packet type: IPv6 where-are-you";
      }
      enum "iam-here" {
        value 34;
        description
          "ICMP Packet type: IPv6 i-am-here";
      }
      enum "mobile-registration-request" {
        value 35;
        description
          "ICMP Packet type: Mobile registration request";
      }
      enum "mobile-registration-reply" {
        value 36;
        description
          "ICMP Packet type: Mobile registration reply";
      }
      enum "domain-name-request" {
        value 37;
        description
          "ICMP Packet type: Domain name request";
      }
    }
    description
      "LPTS ICMP message types";
  }

  typedef Message-icmp {
    type Message-type-icmp;
    description
      "Message icmp";
  }

  typedef Packet {
    type enumeration {
      enum "icmp" {
        description
          "ICMP packet type";
      }
      enum "icm-pv6" {
        description
          "ICMPv6 packet type";
      }
      enum "igmp" {
        description
          "IGMP packet type";
      }
      enum "unknown" {
        description
          "Packet type unknown";
      }
    }
    description
      "Packet type";
  }

  typedef Lpts-ipv6-address {
    type inet:ipv6-address;
    description
      "Lpts ipv6 address";
  }

  typedef Addr-family {
    type enumeration {
      enum "unspecified" {
        value 0;
        description
          "Unspecified";
      }
      enum "local" {
        value 1;
        description
          "Local to host (pipes, portals)";
      }
      enum "inet" {
        value 2;
        description
          "Internetwork: UDP, TCP, etc.";
      }
      enum "implink" {
        value 3;
        description
          "arpanet imp addresses";
      }
      enum "pup" {
        value 4;
        description
          "Pup protocols: e.g. BSP";
      }
      enum "chaos" {
        value 5;
        description
          "mit CHAOS protocols";
      }
      enum "ns" {
        value 6;
        description
          "XEROX NS protocols";
      }
      enum "iso" {
        value 7;
        description
          "ISO protocols";
      }
      enum "ecma" {
        value 8;
        description
          "European computer manufacturers";
      }
      enum "data-kit" {
        value 9;
        description
          "Datakit protocols";
      }
      enum "inet6" {
        value 10;
        description
          "IP version 6";
      }
      enum "sna" {
        value 11;
        description
          "IBM SNA";
      }
      enum "de-cnet" {
        value 12;
        description
          "DECnet";
      }
      enum "dli" {
        value 13;
        description
          "DEC Direct data link interface";
      }
      enum "lat" {
        value 14;
        description
          "LAT";
      }
      enum "hylink" {
        value 15;
        description
          "NSC Hyperchannel";
      }
      enum "appletalk" {
        value 16;
        description
          "Apple Talk";
      }
      enum "route" {
        value 17;
        description
          "Internal Routing Protocol";
      }
      enum "link" {
        value 18;
        description
          "Link layer interface";
      }
      enum "pseudo-xtp" {
        value 19;
        description
          "eXpress Transfer Protocol (no AF)";
      }
      enum "coip" {
        value 20;
        description
          "Connection-oriented IP, aka ST II";
      }
      enum "cnt" {
        value 21;
        description
          "Computer Network Technology";
      }
      enum "pseudo-rtip" {
        value 22;
        description
          "Help Identify RTIP packets";
      }
      enum "ipx" {
        value 23;
        description
          "Novell Internet Protocol";
      }
      enum "sip" {
        value 24;
        description
          "Simple Internet Protocol";
      }
      enum "pseudo-pip" {
        value 25;
        description
          "Help Identify PIP packets";
      }
      enum "ccitt" {
        value 26;
        description
          "CCITT protocols, X.25 etc";
      }
      enum "snap" {
        value 27;
        description
          "802.2 SNAP sockets";
      }
      enum "clnl" {
        value 28;
        description
          "SAP_CLNS + nlpid encaps";
      }
      enum "chdlc" {
        value 29;
        description
          "cisco HDLC on serial";
      }
      enum "ppp" {
        value 30;
        description
          "PPP sockets";
      }
      enum "host-cas" {
        value 31;
        description
          "Host-based CAS signaling";
      }
      enum "dsp" {
        value 32;
        description
          "DSP messaging";
      }
      enum "sap" {
        value 33;
        description
          "SAP Sockets";
      }
      enum "atm" {
        value 34;
        description
          "ATM Sockets";
      }
      enum "fr" {
        value 35;
        description
          "Frame Relay sockets";
      }
      enum "mso" {
        value 36;
        description
          "Voice Media Stream Sockets";
      }
      enum "dchan" {
        value 37;
        description
          "ISDN D Channel Sockets";
      }
      enum "cas" {
        value 38;
        description
          "Trunk Framer media IF Sockets";
      }
      enum "nat" {
        value 39;
        description
          "Network Address Translation Sockets";
      }
      enum "ether" {
        value 40;
        description
          "Generic Ethernet Sockets";
      }
      enum "srp" {
        value 41;
        description
          "Spatial Reuse Protocol Sockets";
      }
    }
    description
      "Address Family Types";
  }

  grouping PKT-TYPE {
    description
      "PKT TYPE";
    leaf type {
      type Packet;
      description
        "Type";
    }
    leaf icmp-message-type {
      when "../type = 'icmp'" {
        description
          "../Type = 'ICMP'";
      }
      type Message-icmp;
      description
        "ICMP message type";
    }
    leaf icm-pv6-message-type {
      when "../type = 'icm-pv6'" {
        description
          "../Type = 'ICMPv6'";
      }
      type Message-icmpv6;
      description
        "ICMPv6 message type";
    }
    leaf igmp-message-type {
      when "../type = 'igmp'" {
        description
          "../Type = 'IGMP'";
      }
      type Message-igmp;
      description
        "IGMP message type";
    }
    leaf message-id {
      when "../type = 'unknown'" {
        description
          "../Type = 'Unknown'";
      }
      type Message-id;
      description
        "Message type in number";
    }
  }

  grouping LPTS-RX-FILTER {
    description
      "LPTS Interface Filter";
    container packet-type {
      description
        "Protocol-specific packet type";
      uses PKT-TYPE;
    }
    container remote-address {
      description
        "Remote address";
      uses IP-ADDR;
    }
    container local-address {
      description
        "Local address";
      uses IP-ADDR;
    }
    leaf interface-name {
      type xr:Interface-name;
      description
        "Interface name";
    }
    leaf remote-length {
      type uint16;
      description
        "Remote address length";
    }
    leaf local-length {
      type uint16;
      description
        "Local address length";
    }
    leaf receive-remote-port {
      type uint16;
      description
        "Receive Remote port";
    }
    leaf receive-local-port {
      type uint16;
      description
        "Receive Local port";
    }
    leaf priority {
      type uint8;
      description
        "Priority";
    }
    leaf ttl {
      type uint8;
      description
        "Minimum TTL";
    }
    leaf flow-types-info {
      type uint32;
      description
        "flow information";
    }
  }

  grouping LPTS-ACCEPT-MASK {
    description
      "LPTS accept mask";
    leaf is-interface {
      type boolean;
      description
        "Set interface";
    }
    leaf is-packet-type {
      type boolean;
      description
        "Set packet type";
    }
    leaf is-remote-address {
      type boolean;
      description
        "Set Remote address";
    }
    leaf is-remote-port {
      type boolean;
      description
        "Set Remote Port";
    }
    leaf is-local-address {
      type boolean;
      description
        "Set Local Address";
    }
    leaf is-local-port {
      type boolean;
      description
        "Set Local Port";
    }
  }

  grouping LPTS-FLAGS {
    description
      "LPTS flags";
    leaf is-pcb-bound {
      type boolean;
      description
        "PCB bound";
    }
    leaf is-local-address-ignore {
      type boolean;
      description
        "Sent drop packets";
    }
    leaf is-ignore-vrf-filter {
      type boolean;
      description
        "Ignore VRF Filter";
    }
  }

  grouping LPTS-OPTIONS {
    description
      "LPTS options";
    leaf is-receive-filter {
      type boolean;
      description
        "Receive filter enabled";
    }
    leaf is-ip-sla {
      type boolean;
      description
        "IP SLA";
    }
  }

  grouping LPTS-PCB {
    description
      "LPTS PCB information block";
    container options {
      description
        "Receive options";
      uses LPTS-OPTIONS;
    }
    container lpts-flags {
      description
        "LPTS flags";
      uses LPTS-FLAGS;
    }
    container accept-mask {
      description
        "AcceptMask";
      uses LPTS-ACCEPT-MASK;
    }
    leaf ttl {
      type uint8;
      description
        "Minimum TTL";
    }
    leaf flow-types-info {
      type uint32;
      description
        "flow information";
    }
    list filter {
      description
        "Interface Filters";
      uses LPTS-RX-FILTER;
    }
  }

  grouping COMMON-PCB-INFO {
    description
      "Common information for all PCB types";
    container lpts-pcb {
      description
        "LPTS PCB information";
      uses LPTS-PCB;
    }
    leaf af-name {
      type Addr-family;
      description
        "Address Family";
    }
  }

  grouping IP-ADDR {
    description
      "IP Address";
    leaf af-name {
      type Addr-family;
      description
        "AFName";
    }
    leaf ipv4-address {
      when "../af-name = 'inet'" {
        description
          "../AFName = 'INET'";
      }
      type inet:ipv4-address;
      description
        "IPv4 address";
    }
    leaf ipv6-address {
      when "../af-name = 'inet6'" {
        description
          "../AFName = 'INET6'";
      }
      type Lpts-ipv6-address;
      description
        "IPv6 address";
    }
  }

  grouping SHOW-PCB-INFO {
    description
      "PCB information to display";
    container local-address {
      description
        "Local IP address";
      uses IP-ADDR;
    }
    container foreign-address {
      description
        "Remote IP address";
      uses IP-ADDR;
    }
    container common {
      description
        "Common PCB information";
      uses COMMON-PCB-INFO;
    }
    leaf l4-protocol {
      type uint32;
      description
        "Layer 4 protocol";
    }
    leaf local-port {
      type uint16;
      description
        "Local port";
    }
    leaf foreign-port {
      type uint16;
      description
        "Remote port";
    }
  }
}
