module Cisco-IOS-XR-crypto-act {
  namespace "http://cisco.com/ns/yang/Cisco-IOS-XR-crypto-act";
  prefix crypto-act;

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR action package configuration.
     
     Copyright (c) 2016-2019 by Cisco Systems, Inc.
     All rights reserved.";

  revision 2019-06-18 {
    description
      "IOS XR 7.0.1 revision.";
  }
  revision 2016-04-17 {
    description
      "IOS XR 6.1.1 revision.";
  }

  grouping KEY-MODULUS {
    leaf key-label {
      type string;
      description
        "RSA keypair label";
    }
    leaf key-modulus {
      type int32 {
        range "512..4096";
      }
      mandatory true;
      description
        "Key modulus in the range of 512 to 4096 for your General Purpose Keypair. Choosing a key modulus greater than 512 may take a few minutes";
    }
  }

  rpc key-generate-rsa-general-keys {
    description
      "Generate a general purpose RSA key pair for signing and encryption";
    input {
      uses KEY-MODULUS;
    }
  }
  rpc key-generate-rsa-usage-keys {
    description
      "Generate seperate RSA key pairs for signing and encryption";
    input {
      uses KEY-MODULUS;
    }
  }
  rpc key-generate-rsa {
    description
      "Generate seperate RSA key pairs for signing and encryption";
    input {
      uses KEY-MODULUS;
    }
  }
  rpc key-generate-dsa {
    description
      "Generate DSA keys";
    input {
      leaf key-modulus {
        type int32 {
          range "512|768|1024";
        }
        mandatory true;
        description
          "Key modulus size can be 512, 768 or 1024 bits.";
      }
    }
  }
  rpc key-generate-ecdsa {
    description
      "Generate a ECDSA key of curve type nistp256 | nistp384 | nistp521";
    input {
      leaf key-modulus {
        type enumeration {
          enum "nistp256" {
            value 0;
          }
          enum "nistp384" {
            value 1;
          }
          enum "nistp521" {
            value 2;
          }
        }
        mandatory true;
      }
      leaf key-label {
        type string;
        description
          "ECDSA key label";
      }
    }
  }
  rpc key-zeroize-rsa {
    description
      "Remove RSA keys";
    input {
      leaf key-label {
        type string;
        description
          "RSA key label";
      }
    }
  }
  rpc key-zeroize-dsa {
    description
      "Remove DSA keys";
  }
  rpc key-zeroize-ecdsa {
    description
      "Remove ECDSA key of curve type nistp256 | nistp384 | nistp521";
    input {
      leaf key-modulus {
        type enumeration {
          enum "nistp256" {
            value 0;
          }
          enum "nistp384" {
            value 1;
          }
          enum "nistp521" {
            value 2;
          }
        }
        mandatory true;
      }
      leaf key-label {
        type string;
        description
          "ECDSA key label";
      }
    }
  }
  rpc key-zeroize-authentication-rsa {
    description
      "Remove RSA authentication key";
  }
  rpc key-zeroize-authentication-rsa-username {
    description
      "Remove RSA authentication key";
    input {
      leaf username {
        type string;
        mandatory true;
        description
          "Username";
      }
    }
  }
  rpc key-zeroize-authentication-rsa-all {
    description
      "Remove RSA authentication key";
  }
  rpc key-import-authentication-rsa-username {
    description
      "RSA authentication key for user";
    input {
      leaf path {
        type string;
        mandatory true;
        description
          "Path to RSA pubkey file";
      }
      leaf username {
        type string;
        mandatory true;
        description
          "Username";
      }
    }
  }
  rpc key-import-authentication-rsa {
    description
      "Remove RSA authentication key";
    input {
      leaf path {
        type string;
        mandatory true;
        description
          "Path to RSA pubkey file";
      }
    }
  }
  rpc ca-authenticate {
    description
      "Get the certification authority certificate";
    input {
      leaf server-name {
        type string;
        mandatory true;
        description
          "CA Server Name";
      }
    }
  }
  rpc ca-enroll {
    description
      "Request a certificate from a CA";
    input {
      leaf server-name {
        type string;
        mandatory true;
        description
          "CA Server Name";
      }
    }
  }
  rpc ca-import-certificate {
    description
      "Import a certificate from a s/tftp server or the terminal";
    input {
      leaf server-name {
        type string;
        mandatory true;
        description
          "CA Server Name";
      }
    }
  }
  rpc ca-cancel-enroll {
    description
      "Cancel enrollment from a CA";
    input {
      leaf server-name {
        type string;
        mandatory true;
        description
          "CA Server Name";
      }
    }
  }
  rpc ca-crl-request {
    description
      "Actions on certificate revocation lists";
    input {
      leaf uri {
        type string;
        mandatory true;
        description
          "CRL Distribution Point in URI format";
      }
    }
    output {
      leaf certificate {
        type string;
        mandatory true;
        description
          "Certificate returned";
      }
    }
  }
  rpc ca-trustpool-import-url {
    description
      "Manual import trustpool certificates from URL";
    input {
      leaf url {
        type string;
        description
          "in URL format";
      }
    }
  }
  rpc ca-trustpool-import-url-clean {
    description
      "Remove downloaded certificates in trustpool";
    input {
      leaf url {
        type string;
        description
          "in URL format";
      }
    }
  }
}
