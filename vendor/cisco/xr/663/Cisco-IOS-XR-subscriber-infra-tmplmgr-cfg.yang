module Cisco-IOS-XR-subscriber-infra-tmplmgr-cfg {
  namespace "http://cisco.com/ns/yang/Cisco-IOS-XR-subscriber-infra-tmplmgr-cfg";
  prefix subscriber-infra-tmplmgr-cfg;

  import Cisco-IOS-XR-types {
    prefix xr;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR subscriber-infra-tmplmgr package configuration.
     
     This module contains definitions
     for the following management objects:
       dynamic-template: All dynamic template configurations
     
     Copyright (c) 2013-2018 by Cisco Systems, Inc.
     All rights reserved.";

  revision 2015-01-07 {
    description
      "IOS XR 5.3.1 revision.";
  }

  container dynamic-template {
    description
      "All dynamic template configurations";
    container ppps {
      description
        "Templates of the PPP Type";
      list ppp {
        key "template-name";
        description
          "A Template of the PPP Type";
        leaf template-name {
          type xr:Cisco-ios-xr-string;
          description
            "The name of the template";
        }
      }
    }
    container ip-subscribers {
      description
        "The IP Subscriber Template Table";
      list ip-subscriber {
        key "template-name";
        description
          "A IP Subscriber Type Template ";
        leaf template-name {
          type xr:Cisco-ios-xr-string;
          description
            "The name of the template";
        }
      }
    }
    container subscriber-services {
      description
        "The Service Type Template Table";
      list subscriber-service {
        key "template-name";
        description
          "A Service Type Template ";
        leaf template-name {
          type xr:Cisco-ios-xr-string;
          description
            "The name of the template";
        }
      }
    }
  }
}
