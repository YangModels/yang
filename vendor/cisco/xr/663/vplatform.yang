module vplatform {
  namespace "http://cisco.com/panini/calvados/vplatform";
  prefix vplatform;
  import tailf-common {
    prefix tailf;
  }

  organization "Cisco Systems, Inc.";

  contact
    "Cisco Systems, Inc.
     Customer Service

     Postal: 170 West Tasman Drive
     San Jose, CA 95134

     Tel: +1 800 553-NETS

     E-mail: cs-yang@cisco.com";

  description 
    "This module contains definitions
     for the Calvados model objects.

    Copyright (c) 2012-2018 by Cisco Systems, Inc.
     All rights reserved.";

  revision "2015-08-30" {
    description "Initial version.";
  }

  container virtual-platform {
    config false;
    container vplatform {
      list summary {
        leaf lines {
          type string;
        }
      }
    }
    container udi {
      container history {
        list udi_his {
          leaf history_records {
            type string;
          }
        }
      }
    }
    container cpu {
      container history {
        list cpu_utl {
          leaf history_records {
            type string;
          }
        }
      }
    }
    container processor {
      container history {
        list proc_info {
          leaf history_records {
            type string;
          }
        }
      }
    }
    container memory {
      container history {
        list mem_usg {
          leaf history_records {
            type string;
          }
        }
      }
    }
    container disk {
      container history {
        list disk_utl {
          leaf history_records {
            type string;
          }
        }
      }
    }
    container Action {
      config false;
      list udi {
        min-elements 1;
        max-elements "1";
        description
          "UDI Operations";
        tailf:action "reset" {
          input;
          output {
            leaf result {
              type string;
              mandatory true;
            }
          }
        }
      }
    }
  }
}
