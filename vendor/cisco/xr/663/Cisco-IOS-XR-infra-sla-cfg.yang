module Cisco-IOS-XR-infra-sla-cfg {
  namespace "http://cisco.com/ns/yang/Cisco-IOS-XR-infra-sla-cfg";
  prefix infra-sla-cfg;

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR infra-sla package configuration.
     
     This module contains definitions
     for the following management objects:
       sla: SLA prtocol and profile Configuration
     
     Copyright (c) 2013-2018 by Cisco Systems, Inc.
     All rights reserved.";

  revision 2015-11-09 {
    description
      "IOS XR 6.0 revision.";
  }

  container sla {
    description
      "SLA prtocol and profile Configuration";
    container protocols {
      description
        "Table of all SLA protocols";
    }
  }
}
