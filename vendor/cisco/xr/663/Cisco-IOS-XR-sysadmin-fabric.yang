module Cisco-IOS-XR-sysadmin-fabric {
  namespace "http://www.cisco.com/ns/yang/Cisco-IOS-XR-sysadmin-fabric";
  prefix fabric;

  import Cisco-IOS-XR-sysadmin-fabric-mgr-fgid {
    prefix fabric-fgid;
  }
  import Cisco-IOS-XR-sysadmin-fabric-mgr-fsdb-server {
    prefix fabric-fsdb;
  }
  import Cisco-IOS-XR-sysadmin-fabric-mgr-fsdb-aggregator {
    prefix fabric-fsdb-aggr;
  }
  import Cisco-IOS-XR-sysadmin-fabric-driver-sfe {
    prefix fabric-sfe;
  }
  import Cisco-IOS-XR-sysadmin-fabric-cxp-ncs6k {
    prefix fabric-cxp;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains definitions
     for the Calvados model objects.
     
     This module contains a collection of YANG
     definitions for Cisco IOS-XR SysAdmin configuration.
     
     This module defines CLI support of fabric components
     for ncs6k.
     
     Copyright(c) 2011-2017 by Cisco Systems, Inc.
     All rights reserved.
     
     Copyright (c) 2012-2018 by Cisco Systems, Inc.
     All rights reserved.";

  revision 2017-06-15 {
    description
      "Split the file based on the platform";
  }

  grouping fabric_action_cmds {
    container fabric_action {
      container fabric {
        description
          "Fabric resource commands";
        uses fabric-fsdb-aggr:fsdb_aggr_ppu;
      }
    }
  }

  grouping fabric_clear {
    container fabric {
      description
        "Fabric resource commands";
      uses fabric-fsdb-aggr:fsdb_aggr_clear;
    }
  }

  grouping fabric {
    container fabric {
      description
        "Fabric resource commands";
      container fabric {
        description
          "Fabric configuration";
        container fsdbagg {
          uses fabric-fsdb-aggr:fsdb_agg_conf_plane;
        }
        uses fabric-fgid:fgid_conf_resource;
      }
      container oper {
        config false;
        uses fabric-cxp:fc_cxp_dom;
        uses fabric-fgid:fgid;
        uses fabric-fsdb-aggr:fsdb_aggr;
        uses fabric-fsdb:fsdb_svr;
      }
    }
    container sfe_oper {
      config false;
      uses fabric-sfe:sfe;
    }
  }
}
