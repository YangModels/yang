module Cisco-IOS-XR-um-8000-fpd-cfg {
  namespace "http://cisco.com/ns/yang/Cisco-IOS-XR-um-8000-fpd-cfg";
  prefix um-8000-fpd-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR 8000-fpd package configuration.
     
     This YANG module augments the
     modules with configuration data.
     
     Copyright (c) 2020-2024 by Cisco Systems, Inc.
     All rights reserved.";

  revision 2024-03-04 {
    description
      "Added container include
       2022-02-17
         Added container exclude";
    semver:module-version "1.1.0";
  }
  revision 2020-12-22 {
    description
      "Initial release";
    semver:module-version "1.0.0";
  }

  container fpd {
    description
      "FPD firmware configuration";
    container auto-upgrade {
      description
        "FPD auto-upgrade configuration";
      container enable {
        must "not(../disable)";
        presence "Indicates a enable node is configured.";
        description
          "Enable fpd auto upgrade";
      }
      container disable {
        must "not(../enable)";
        presence "Indicates a disable node is configured.";
        description
          "Disable fpd auto upgrade";
      }
      container exclude {
        description
          "FPD auto-upgrade exclude configuration";
        container pm {
          presence "Indicates a pm node is configured.";
          description
            "Power module entity to be excluded";
        }
      }
      container include {
        description
          "FPD auto-upgrade exclude configuration";
        container pm {
          presence "Indicates a pm node is configured.";
          description
            "Power module entity to be included";
        }
      }
    }
  }
}
