submodule Cisco-IOS-XR-ofa-npu-qos-oper-sub1 {
  belongs-to Cisco-IOS-XR-ofa-npu-qos-oper {
    prefix Cisco-IOS-XR-ofa-npu-qos-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR ofa-npu-qos package operational data.
     
     Copyright (c) 2013-2024 by Cisco Systems, Inc.
     All rights reserved.";

  revision 2024-01-19 {
    description
      "Add traffic class high water marks monitoring";
    semver:module-version "1.0.0";
  }
  revision 2022-10-10 {
    description
      "Create the initial npu-qos oper yang model.";
  }
  revision 2019-04-05 {
    description
      "Establish semantic version baseline.";
  }
  revision 2015-11-09 {
    description
      "IOS XR 6.0 revision.";
  }

  typedef Ofa-npu-qos-show-hp-level {
    type enumeration {
      enum "priority-level1" {
        description
          "Priority queue level 1";
      }
      enum "priority-level2" {
        description
          "Priority queue level 2";
      }
      enum "priority-level3" {
        description
          "Priority queue level 3";
      }
      enum "priority-level4" {
        description
          "Priority queue level 4";
      }
      enum "priority-level5" {
        description
          "Priority queue level 5";
      }
      enum "priority-level6" {
        description
          "Priority queue level 6";
      }
      enum "priority-level7" {
        description
          "Priority queue level 7";
      }
      enum "priority-level8" {
        description
          "Priority queue level 8";
      }
      enum "unknown" {
        description
          "Unknown";
      }
    }
    description
      "Priority level";
  }

  grouping OFA-NPU-QOS-Q-INFO-ST {
    description
      "OFA NPU QOS Q INFO ST";
    leaf priority-level {
      type Ofa-npu-qos-show-hp-level;
      description
        "Priority level";
    }
    leaf config-max-rate {
      type uint32;
      units "kbit/s";
      description
        "Configured maximum rate kbps";
    }
  }

  grouping OFA-NPU-QOS-SHOW-ST {
    description
      "OFA NPU QOS SHOW ST";
    leaf npu-id {
      type uint32;
      description
        "NPU ID";
    }
    leaf voq-base-address {
      type uint32;
      description
        "VOQ base address";
    }
    list q-config {
      key "priority-level";
      max-elements "8";
      description
        "Port configuration";
      uses OFA-NPU-QOS-Q-INFO-ST;
    }
  }

  grouping OFA-QOS-TC-HIGH-WATER-MARKS-DATA-ENTRY {
    description
      "OFA QOS TC HIGH WATER MARKS DATA ENTRY";
    container max-occupancy-percent {
      description
        "Max Queue Occupancy Percentage";
      uses OFA-QOS-PERCENT;
    }
    container max-occupancy-src-sys-port {
      description
        "Source System Port during Max Queue Occupancy";
      uses OFA-QOS-SSP;
    }
    container max-delay-occupancy-percent {
      description
        "Queue Occupancy Percentage during Max Queue
         Delay";
      uses OFA-QOS-PERCENT;
    }
    container max-delay-src-sys-port {
      description
        "Source System Port during Max Queue Delay";
      uses OFA-QOS-SSP;
    }
    leaf interval-number {
      type uint8;
      description
        "Index of this data interval";
    }
    leaf kilobytes-valid {
      type boolean;
      description
        "Flag to indicate whether MaxOccupancyKilobytes
         and MaxDelayOccupancyKilobytes fields contain
         valid data";
    }
    leaf start-timestamp-ms {
      type uint64;
      description
        "Start timestamp of periodic data interval
         (millisecond granularity)";
    }
    leaf end-timestamp-ms {
      type uint64;
      description
        "End timestamp of periodic data interval
         (millisecond granularity)";
    }
    leaf max-occupancy-kilobytes {
      type uint32;
      units "kilobyte";
      description
        "Max Queue Occupancy in Kilobytes";
    }
    leaf max-occupancy-delay-ns {
      type uint32;
      units "nanosecond";
      description
        "Delay in Nanoseconds during Max Queue Occupancy";
    }
    leaf max-delay-ns {
      type uint32;
      units "nanosecond";
      description
        "Max Queue Delay in Nanoseconds";
    }
    leaf max-delay-occupancy-kilobytes {
      type uint32;
      units "kilobyte";
      description
        "Queue Occupancy in Kilobytes during Max Queue
         Delay";
    }
  }

  grouping OFA-QOS-TC-HIGH-WATER-MARKS-TC-DATA {
    description
      "OFA QOS TC HIGH WATER MARKS TC DATA";
    leaf traffic-class {
      type uint8;
      description
        "Traffic Class";
    }
    list interval {
      key "interval-number";
      description
        "Per interval queue occupancy and delay high
         water marks data for recent periodic data
         collection intervals";
      uses OFA-QOS-TC-HIGH-WATER-MARKS-DATA-ENTRY;
    }
  }

  grouping OFA-QOS-SSP {
    description
      "OFA QOS SSP";
    leaf gid {
      type uint16;
      description
        "Source System Port Global ID";
    }
    leaf device {
      type uint16;
      description
        "Source System Port Device";
    }
    leaf slot {
      type uint8;
      description
        "Source System Port Slot";
    }
    leaf npu {
      type uint8;
      description
        "Source System Port NPU";
    }
    leaf slice {
      type uint8;
      description
        "Source System Port Slice";
    }
  }

  grouping OFA-QOS-PERCENT {
    description
      "OFA QOS PERCENT";
    leaf percent {
      type uint8;
      units "percentage";
      description
        "Percent";
    }
    leaf hundredths {
      type uint8;
      description
        "Hundredths";
    }
  }

  grouping OFA-QOS-TC-HIGH-WATER-MARKS {
    description
      "OFA QOS TC HIGH WATER MARKS";
    container max-occupancy-percent {
      description
        "Max Queue Occupancy Percentage";
      uses OFA-QOS-PERCENT;
    }
    container max-occupancy-src-sys-port {
      description
        "Source System Port during Max Queue Occupancy";
      uses OFA-QOS-SSP;
    }
    container max-delay-occupancy-percent {
      description
        "Queue Occupancy Percentage during Max Queue
         Delay";
      uses OFA-QOS-PERCENT;
    }
    container max-delay-src-sys-port {
      description
        "Source System Port during Max Queue Delay";
      uses OFA-QOS-SSP;
    }
    leaf traffic-class {
      type uint8;
      description
        "Traffic Class";
    }
    leaf kilobytes-valid {
      type boolean;
      description
        "Flag to indicate whether MaxOccupancyKilobytes
         and MaxDelayOccupancyKilobytes fields contain
         valid data";
    }
    leaf max-occupancy-kilobytes {
      type uint32;
      units "kilobyte";
      description
        "Max Queue Occupancy in Kilobytes";
    }
    leaf max-occupancy-delay-ns {
      type uint32;
      units "nanosecond";
      description
        "Delay in Nanoseconds during Max Queue Occupancy";
    }
    leaf max-occupancy-timestamp-ms {
      type uint64;
      description
        "Timestamp of Max Queue Occupancy (millisecond
         granularity)";
    }
    leaf max-delay-ns {
      type uint32;
      units "nanosecond";
      description
        "Max Queue Delay in Nanoseconds";
    }
    leaf max-delay-occupancy-kilobytes {
      type uint32;
      units "kilobyte";
      description
        "Queue Occupancy in Kilobytes during Max Queue
         Delay";
    }
    leaf max-delay-timestamp-ms {
      type uint64;
      description
        "Timestamp of Max Queue Delay (millisecond
         granularity)";
    }
  }

  grouping OFA-QOS-HWM-INTF-INFO {
    description
      "OFA QOS HWM INTF INFO";
    leaf sys-port-gid {
      type uint32;
      description
        "System Port Global ID of port";
    }
    list monotonic {
      key "traffic-class";
      description
        "Per traffic class monotonically increasing
         (since clear) queue occupancy and delay high
         water marks";
      uses OFA-QOS-TC-HIGH-WATER-MARKS;
    }
    list periodic {
      key "traffic-class";
      description
        "Per traffic class queue occupancy and delay high
         water marks data for recent periodic data
         collection intervals";
      uses OFA-QOS-TC-HIGH-WATER-MARKS-TC-DATA;
    }
  }
}
