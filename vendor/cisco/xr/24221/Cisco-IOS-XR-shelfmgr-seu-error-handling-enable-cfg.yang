module Cisco-IOS-XR-shelfmgr-seu-error-handling-enable-cfg {
  namespace "http://cisco.com/ns/yang/Cisco-IOS-XR-shelfmgr-seu-error-handling-enable-cfg";
  prefix shelfmgr-seu-error-handling-enable-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR shelfmgr-seu-error-handling-enable package configuration.
     
     This module contains definitions
     for the following management objects:
       shelf-mgr-hw-module-seu-config: SEU error handling
         configuration
     
     Copyright (c) 2013-2023 by Cisco Systems, Inc.
     All rights reserved.";

  revision 2023-09-15 {
    description
      "Yang Schema added for shelfmgr SEU error handling in hw-module config.";
    semver:module-version "1.0.0";
  }
  revision 2019-04-05 {
    description
      "Establish semantic version baseline.";
  }
  revision 2015-11-09 {
    description
      "IOS XR 6.0 revision.";
  }

  container shelf-mgr-hw-module-seu-config {
    description
      "SEU error handling configuration";
    container seu-card-types {
      description
        "Configure SEU error";
      list seu-card-type {
        key "location-string";
        description
          "Configure SEU error";
        leaf seu-enable {
          type string;
          description
            "SEU enable on card";
        }
        leaf location-string {
          type xr:Cisco-ios-xr-string;
          description
            "Location of SEU config";
        }
      }
    }
  }
}
