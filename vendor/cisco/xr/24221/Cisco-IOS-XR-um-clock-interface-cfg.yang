module Cisco-IOS-XR-um-clock-interface-cfg {
  namespace "http://cisco.com/ns/yang/Cisco-IOS-XR-um-clock-interface-cfg";
  prefix um-clock-interface-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR clock-interface package configuration.
     
     This YANG module augments the
     modules with configuration data.
     
     Copyright (c) 2020-2022 by Cisco Systems, Inc.
     All rights reserved.";

  revision 2020-09-23 {
    description
      "Initial release";
    semver:module-version "1.0.0";
  }

  container clock-interfaces {
    description
      "Clock interface configuration commands";
    list clock-interface {
      key "interface-name";
      description
        "Clock interface configuration commands";
      leaf interface-name {
        type xr:Cisco-ios-xr-string {
          length "1..1024" {
            description
              "Clock interface name";
          }
        }
        description
          "Clock interface name";
      }
      container frequency {
        description
          "Frequency Synchronization configuration";
        container synchronization {
          description
            "Frequency Synchronization configuration";
          container ssm {
            description
              "SSM configuration commands";
            container disable {
              presence "Indicates a disable node is configured.";
              description
                "Disable sending of SSMs";
            }
          }
          leaf priority {
            type uint32 {
              range "1..254" {
                description
                  "Source priority";
              }
            }
            description
              "Source priority";
          }
          leaf time-of-day-priority {
            type uint32 {
              range "1..254" {
                description
                  "Source time-of-day priority";
              }
            }
            description
              "Source time-of-day priority";
          }
          container quality {
            description
              "Quality level configuration";
            container transmit {
              description
                "Set the quality level to be transmitted";
              container lowest {
                description
                  "Specify the lowest acceptable QL value";
                container itu-t {
                  description
                    "ITU-T QL options";
                  container option {
                    description
                      "ITU-T QL options";
                    leaf one {
                      type enumeration {
                        enum "prc" {
                          value 22;
                          description
                            "ITU-T Option 1: Primary reference clock";
                        }
                        enum "prtc" {
                          value 21;
                          description
                            "ITU-T Option 1: Primary reference timing clock";
                        }
                        enum "e-prtc" {
                          value 20;
                          description
                            "ITU-T Option 1: Enhanced primary reference timing clock";
                        }
                        enum "ssu-a" {
                          value 23;
                          description
                            "ITU-T Option 1: Type I or V subordinate clock";
                        }
                        enum "ssu-b" {
                          value 24;
                          description
                            "ITU-T Option 1: Type IV subordinate clock";
                        }
                        enum "sec" {
                          value 27;
                          description
                            "ITU-T Option 1: SONET equipment clock";
                        }
                        enum "e-eec" {
                          value 25;
                          description
                            "ITU-T Option 1: Enhanced ethernet equipment clock";
                        }
                        enum "eec1" {
                          value 26;
                          description
                            "ITU-T Option 1: Ethernet equipment clock";
                        }
                        enum "dnu" {
                          value 1;
                          description
                            "This signal should not be used for synchronization";
                        }
                      }
                      must
                        "not(../two/generation/one or
                         ../two/generation/two or
                         ../../../../highest/itu-t/option/one or
                         ../../../../highest/itu-t/option/two/generation/one or
                         ../../../../highest/itu-t/option/two/generation/two or
                         ../../../../exact/itu-t/option/one or
                         ../../../../exact/itu-t/option/two/generation/one or
                         ../../../../exact/itu-t/option/two/generation/two)";
                      description
                        "ITU-T QL option 1";
                    }
                    container two {
                      description
                        "ITU-T QL option 2";
                      container generation {
                        description
                          "ITU-T QL option 2 generation";
                        leaf one {
                          type enumeration {
                            enum "prs" {
                              value 42;
                              description
                                "ITU-T Option 2, Generation 1: Primary reference source";
                            }
                            enum "prtc" {
                              value 41;
                              description
                                "ITU-T Option 2, Generation 1: Primary reference timing clock";
                            }
                            enum "e-prtc" {
                              value 40;
                              description
                                "ITU-T Option 2, Generation 1: Enhanced primary reference timing clock";
                            }
                            enum "stu" {
                              value 43;
                              description
                                "ITU-T Option 2, Generation 1: Synchronized - traceability unknown";
                            }
                            enum "st2" {
                              value 44;
                              description
                                "ITU-T Option 2, Generation 1: Stratum 2";
                            }
                            enum "st3" {
                              value 45;
                              description
                                "ITU-T Option 2, Generation 1: Stratum 3";
                            }
                            enum "smc" {
                              value 48;
                              description
                                "ITU-T Option 2, Generation 1: SONET clock self timed";
                            }
                            enum "eec2" {
                              value 47;
                              description
                                "ITU-T Option 2, Generation 1: Ethernet equipment clock";
                            }
                            enum "e-eec" {
                              value 46;
                              description
                                "ITU-T Option 2, Generation 1: Ethernet ethernet equipment clock";
                            }
                            enum "st4" {
                              value 49;
                              description
                                "ITU-T Option 2, Generation 1: Stratum 4 freerun";
                            }
                            enum "dus" {
                              value 1;
                              description
                                "This signal should not be used for synchronization";
                            }
                          }
                          must
                            "not(../../../one or
                             ../two or
                             ../../../../../../highest/itu-t/option/one or
                             ../../../../../../highest/itu-t/option/two/generation/one or
                             ../../../../../../highest/itu-t/option/two/generation/two or
                             ../../../../../../exact/itu-t/option/one or
                             ../../../../../../exact/itu-t/option/two/generation/one or
                             ../../../../../../exact/itu-t/option/two/generation/two)";
                          description
                            "ITU-T QL option 2, generation 1";
                        }
                        leaf two {
                          type enumeration {
                            enum "prs" {
                              value 62;
                              description
                                "ITU-T Option 2, Generation 2: Primary reference source";
                            }
                            enum "prtc" {
                              value 61;
                              description
                                "ITU-T Option 2, Generation 2: Primary reference timing clock";
                            }
                            enum "e-prtc" {
                              value 60;
                              description
                                "ITU-T Option 2, Generation 2: Enhanced primary reference timing clock";
                            }
                            enum "stu" {
                              value 63;
                              description
                                "ITU-T Option 2, Generation 2: Synchronized - traceability unknown";
                            }
                            enum "st2" {
                              value 64;
                              description
                                "ITU-T Option 2, Generation 2: Stratum 2";
                            }
                            enum "tnc" {
                              value 65;
                              description
                                "ITU-T Option 2, Generation 2: Transit node clock";
                            }
                            enum "st3e" {
                              value 66;
                              description
                                "ITU-T Option 2, Generation 2: Stratum 3E";
                            }
                            enum "st3" {
                              value 67;
                              description
                                "ITU-T Option 2, Generation 2: Stratum 3";
                            }
                            enum "smc" {
                              value 70;
                              description
                                "ITU-T Option 2, Generation 2: SONET clock self timed";
                            }
                            enum "eec2" {
                              value 69;
                              description
                                "ITU-T Option 2, Generation 2: Ethernet equipment clock";
                            }
                            enum "e-eec" {
                              value 68;
                              description
                                "ITU-T Option 2, Generation 2: Ethernet ethernet equipment clock";
                            }
                            enum "st4" {
                              value 71;
                              description
                                "ITU-T Option 2, Generation 2: Stratum 4 freerun";
                            }
                            enum "dus" {
                              value 1;
                              description
                                "This signal should not be used for synchronization";
                            }
                          }
                          must
                            "not(../../../one or
                             ../one or
                             ../../../../../../highest/itu-t/option/one or
                             ../../../../../../highest/itu-t/option/two/generation/one or
                             ../../../../../../highest/itu-t/option/two/generation/two or
                             ../../../../../../exact/itu-t/option/one or
                             ../../../../../../exact/itu-t/option/two/generation/one or
                             ../../../../../../exact/itu-t/option/two/generation/two)";
                          description
                            "ITU-T QL option 2, generation 2";
                        }
                      }
                    }
                  }
                }
              }
              container highest {
                description
                  "Specify the highest acceptable QL value";
                container itu-t {
                  description
                    "ITU-T QL options";
                  container option {
                    description
                      "ITU-T QL options";
                    leaf one {
                      type enumeration {
                        enum "prc" {
                          value 22;
                          description
                            "ITU-T Option 1: Primary reference clock";
                        }
                        enum "prtc" {
                          value 21;
                          description
                            "ITU-T Option 1: Primary reference timing clock";
                        }
                        enum "e-prtc" {
                          value 20;
                          description
                            "ITU-T Option 1: Enhanced primary reference timing clock";
                        }
                        enum "ssu-a" {
                          value 23;
                          description
                            "ITU-T Option 1: Type I or V subordinate clock";
                        }
                        enum "ssu-b" {
                          value 24;
                          description
                            "ITU-T Option 1: Type IV subordinate clock";
                        }
                        enum "sec" {
                          value 27;
                          description
                            "ITU-T Option 1: SONET equipment clock";
                        }
                        enum "e-eec" {
                          value 25;
                          description
                            "ITU-T Option 1: Enhanced ethernet equipment clock";
                        }
                        enum "eec1" {
                          value 26;
                          description
                            "ITU-T Option 1: Ethernet equipment clock";
                        }
                        enum "dnu" {
                          value 1;
                          description
                            "This signal should not be used for synchronization";
                        }
                      }
                      must
                        "not(../two/generation/one or
                         ../two/generation/two or
                         ../../../../lowest/itu-t/option/one or
                         ../../../../lowest/itu-t/option/two/generation/one or
                         ../../../../lowest/itu-t/option/two/generation/two or
                         ../../../../exact/itu-t/option/one or
                         ../../../../exact/itu-t/option/two/generation/one or
                         ../../../../exact/itu-t/option/two/generation/two)";
                      description
                        "ITU-T QL option 1";
                    }
                    container two {
                      description
                        "ITU-T QL option 2";
                      container generation {
                        description
                          "ITU-T QL option 2 generation";
                        leaf one {
                          type enumeration {
                            enum "prs" {
                              value 42;
                              description
                                "ITU-T Option 2, Generation 1: Primary reference source";
                            }
                            enum "prtc" {
                              value 41;
                              description
                                "ITU-T Option 2, Generation 1: Primary reference timing clock";
                            }
                            enum "e-prtc" {
                              value 40;
                              description
                                "ITU-T Option 2, Generation 1: Enhanced primary reference timing clock";
                            }
                            enum "stu" {
                              value 43;
                              description
                                "ITU-T Option 2, Generation 1: Synchronized - traceability unknown";
                            }
                            enum "st2" {
                              value 44;
                              description
                                "ITU-T Option 2, Generation 1: Stratum 2";
                            }
                            enum "st3" {
                              value 45;
                              description
                                "ITU-T Option 2, Generation 1: Stratum 3";
                            }
                            enum "smc" {
                              value 48;
                              description
                                "ITU-T Option 2, Generation 1: SONET clock self timed";
                            }
                            enum "eec2" {
                              value 47;
                              description
                                "ITU-T Option 2, Generation 1: Ethernet equipment clock";
                            }
                            enum "e-eec" {
                              value 46;
                              description
                                "ITU-T Option 2, Generation 1: Ethernet ethernet equipment clock";
                            }
                            enum "st4" {
                              value 49;
                              description
                                "ITU-T Option 2, Generation 1: Stratum 4 freerun";
                            }
                            enum "dus" {
                              value 1;
                              description
                                "This signal should not be used for synchronization";
                            }
                          }
                          must
                            "not(../../../one or
                             ../two or
                             ../../../../../../lowest/itu-t/option/one or
                             ../../../../../../lowest/itu-t/option/two/generation/one or
                             ../../../../../../lowest/itu-t/option/two/generation/two or
                             ../../../../../../exact/itu-t/option/one or
                             ../../../../../../exact/itu-t/option/two/generation/one or
                             ../../../../../../exact/itu-t/option/two/generation/two)";
                          description
                            "ITU-T QL option 2, generation 1";
                        }
                        leaf two {
                          type enumeration {
                            enum "prs" {
                              value 62;
                              description
                                "ITU-T Option 2, Generation 2: Primary reference source";
                            }
                            enum "prtc" {
                              value 61;
                              description
                                "ITU-T Option 2, Generation 2: Primary reference timing clock";
                            }
                            enum "e-prtc" {
                              value 60;
                              description
                                "ITU-T Option 2, Generation 2: Enhanced primary reference timing clock";
                            }
                            enum "stu" {
                              value 63;
                              description
                                "ITU-T Option 2, Generation 2: Synchronized - traceability unknown";
                            }
                            enum "st2" {
                              value 64;
                              description
                                "ITU-T Option 2, Generation 2: Stratum 2";
                            }
                            enum "tnc" {
                              value 65;
                              description
                                "ITU-T Option 2, Generation 2: Transit node clock";
                            }
                            enum "st3e" {
                              value 66;
                              description
                                "ITU-T Option 2, Generation 2: Stratum 3E";
                            }
                            enum "st3" {
                              value 67;
                              description
                                "ITU-T Option 2, Generation 2: Stratum 3";
                            }
                            enum "smc" {
                              value 70;
                              description
                                "ITU-T Option 2, Generation 2: SONET clock self timed";
                            }
                            enum "eec2" {
                              value 69;
                              description
                                "ITU-T Option 2, Generation 2: Ethernet equipment clock";
                            }
                            enum "e-eec" {
                              value 68;
                              description
                                "ITU-T Option 2, Generation 2: Ethernet ethernet equipment clock";
                            }
                            enum "st4" {
                              value 71;
                              description
                                "ITU-T Option 2, Generation 2: Stratum 4 freerun";
                            }
                            enum "dus" {
                              value 1;
                              description
                                "This signal should not be used for synchronization";
                            }
                          }
                          must
                            "not(../../../one or
                             ../one or
                             ../../../../../../lowest/itu-t/option/one or
                             ../../../../../../lowest/itu-t/option/two/generation/one or
                             ../../../../../../lowest/itu-t/option/two/generation/two or
                             ../../../../../../exact/itu-t/option/one or
                             ../../../../../../exact/itu-t/option/two/generation/one or
                             ../../../../../../exact/itu-t/option/two/generation/two)";
                          description
                            "ITU-T QL option 2, generation 2";
                        }
                      }
                    }
                  }
                }
              }
              container exact {
                description
                  "Specify the exact QL value to use";
                container itu-t {
                  description
                    "ITU-T QL options";
                  container option {
                    description
                      "ITU-T QL options";
                    leaf one {
                      type enumeration {
                        enum "prc" {
                          value 22;
                          description
                            "ITU-T Option 1: Primary reference clock";
                        }
                        enum "prtc" {
                          value 21;
                          description
                            "ITU-T Option 1: Primary reference timing clock";
                        }
                        enum "e-prtc" {
                          value 20;
                          description
                            "ITU-T Option 1: Enhanced primary reference timing clock";
                        }
                        enum "ssu-a" {
                          value 23;
                          description
                            "ITU-T Option 1: Type I or V subordinate clock";
                        }
                        enum "ssu-b" {
                          value 24;
                          description
                            "ITU-T Option 1: Type IV subordinate clock";
                        }
                        enum "sec" {
                          value 27;
                          description
                            "ITU-T Option 1: SONET equipment clock";
                        }
                        enum "e-eec" {
                          value 25;
                          description
                            "ITU-T Option 1: Enhanced ethernet equipment clock";
                        }
                        enum "eec1" {
                          value 26;
                          description
                            "ITU-T Option 1: Ethernet equipment clock";
                        }
                        enum "dnu" {
                          value 1;
                          description
                            "This signal should not be used for synchronization";
                        }
                      }
                      must
                        "not(../two/generation/one or
                         ../two/generation/two or
                         ../../../../highest/itu-t/option/one or
                         ../../../../highest/itu-t/option/two/generation/one or
                         ../../../../highest/itu-t/option/two/generation/two or
                         ../../../../lowest/itu-t/option/one or
                         ../../../../lowest/itu-t/option/two/generation/one or
                         ../../../../lowest/itu-t/option/two/generation/two)";
                      description
                        "ITU-T QL option 1";
                    }
                    container two {
                      description
                        "ITU-T QL option 2";
                      container generation {
                        description
                          "ITU-T QL option 2 generation";
                        leaf one {
                          type enumeration {
                            enum "prs" {
                              value 42;
                              description
                                "ITU-T Option 2, Generation 1: Primary reference source";
                            }
                            enum "prtc" {
                              value 41;
                              description
                                "ITU-T Option 2, Generation 1: Primary reference timing clock";
                            }
                            enum "e-prtc" {
                              value 40;
                              description
                                "ITU-T Option 2, Generation 1: Enhanced primary reference timing clock";
                            }
                            enum "stu" {
                              value 43;
                              description
                                "ITU-T Option 2, Generation 1: Synchronized - traceability unknown";
                            }
                            enum "st2" {
                              value 44;
                              description
                                "ITU-T Option 2, Generation 1: Stratum 2";
                            }
                            enum "st3" {
                              value 45;
                              description
                                "ITU-T Option 2, Generation 1: Stratum 3";
                            }
                            enum "smc" {
                              value 48;
                              description
                                "ITU-T Option 2, Generation 1: SONET clock self timed";
                            }
                            enum "eec2" {
                              value 47;
                              description
                                "ITU-T Option 2, Generation 1: Ethernet equipment clock";
                            }
                            enum "e-eec" {
                              value 46;
                              description
                                "ITU-T Option 2, Generation 1: Ethernet ethernet equipment clock";
                            }
                            enum "st4" {
                              value 49;
                              description
                                "ITU-T Option 2, Generation 1: Stratum 4 freerun";
                            }
                            enum "dus" {
                              value 1;
                              description
                                "This signal should not be used for synchronization";
                            }
                          }
                          must
                            "not(../../../one or
                             ../two or
                             ../../../../../../highest/itu-t/option/one or
                             ../../../../../../highest/itu-t/option/two/generation/one or
                             ../../../../../../highest/itu-t/option/two/generation/two or
                             ../../../../../../lowest/itu-t/option/one or
                             ../../../../../../lowest/itu-t/option/two/generation/one or
                             ../../../../../../lowest/itu-t/option/two/generation/two)";
                          description
                            "ITU-T QL option 2, generation 1";
                        }
                        leaf two {
                          type enumeration {
                            enum "prs" {
                              value 62;
                              description
                                "ITU-T Option 2, Generation 2: Primary reference source";
                            }
                            enum "prtc" {
                              value 61;
                              description
                                "ITU-T Option 2, Generation 2: Primary reference timing clock";
                            }
                            enum "e-prtc" {
                              value 60;
                              description
                                "ITU-T Option 2, Generation 2: Enhanced primary reference timing clock";
                            }
                            enum "stu" {
                              value 63;
                              description
                                "ITU-T Option 2, Generation 2: Synchronized - traceability unknown";
                            }
                            enum "st2" {
                              value 64;
                              description
                                "ITU-T Option 2, Generation 2: Stratum 2";
                            }
                            enum "tnc" {
                              value 65;
                              description
                                "ITU-T Option 2, Generation 2: Transit node clock";
                            }
                            enum "st3e" {
                              value 66;
                              description
                                "ITU-T Option 2, Generation 2: Stratum 3E";
                            }
                            enum "st3" {
                              value 67;
                              description
                                "ITU-T Option 2, Generation 2: Stratum 3";
                            }
                            enum "smc" {
                              value 70;
                              description
                                "ITU-T Option 2, Generation 2: SONET clock self timed";
                            }
                            enum "eec2" {
                              value 69;
                              description
                                "ITU-T Option 2, Generation 2: Ethernet equipment clock";
                            }
                            enum "e-eec" {
                              value 68;
                              description
                                "ITU-T Option 2, Generation 2: Ethernet ethernet equipment clock";
                            }
                            enum "st4" {
                              value 71;
                              description
                                "ITU-T Option 2, Generation 2: Stratum 4 freerun";
                            }
                            enum "dus" {
                              value 1;
                              description
                                "This signal should not be used for synchronization";
                            }
                          }
                          must
                            "not(../../../one or
                             ../one or
                             ../../../../../../highest/itu-t/option/one or
                             ../../../../../../highest/itu-t/option/two/generation/one or
                             ../../../../../../highest/itu-t/option/two/generation/two or
                             ../../../../../../lowest/itu-t/option/one or
                             ../../../../../../lowest/itu-t/option/two/generation/one or
                             ../../../../../../lowest/itu-t/option/two/generation/two)";
                          description
                            "ITU-T QL option 2, generation 2";
                        }
                      }
                    }
                  }
                }
              }
            }
            container receive {
              description
                "Adjust the received quality level";
              container lowest {
                description
                  "Specify the lowest acceptable QL value";
                container itu-t {
                  description
                    "ITU-T QL options";
                  container option {
                    description
                      "ITU-T QL options";
                    leaf one {
                      type enumeration {
                        enum "prc" {
                          value 22;
                          description
                            "ITU-T Option 1: Primary reference clock";
                        }
                        enum "prtc" {
                          value 21;
                          description
                            "ITU-T Option 1: Primary reference timing clock";
                        }
                        enum "e-prtc" {
                          value 20;
                          description
                            "ITU-T Option 1: Enhanced primary reference timing clock";
                        }
                        enum "ssu-a" {
                          value 23;
                          description
                            "ITU-T Option 1: Type I or V subordinate clock";
                        }
                        enum "ssu-b" {
                          value 24;
                          description
                            "ITU-T Option 1: Type IV subordinate clock";
                        }
                        enum "sec" {
                          value 27;
                          description
                            "ITU-T Option 1: SONET equipment clock";
                        }
                        enum "e-eec" {
                          value 25;
                          description
                            "ITU-T Option 1: Enhanced ethernet equipment clock";
                        }
                        enum "eec1" {
                          value 26;
                          description
                            "ITU-T Option 1: Ethernet equipment clock";
                        }
                        enum "dnu" {
                          value 1;
                          description
                            "This signal should not be used for synchronization";
                        }
                      }
                      must
                        "not(../two/generation/one or
                         ../two/generation/two or
                         ../../../../highest/itu-t/option/one or
                         ../../../../highest/itu-t/option/two/generation/one or
                         ../../../../highest/itu-t/option/two/generation/two or
                         ../../../../exact/itu-t/option/one or
                         ../../../../exact/itu-t/option/two/generation/one or
                         ../../../../exact/itu-t/option/two/generation/two)";
                      description
                        "ITU-T QL option 1";
                    }
                    container two {
                      description
                        "ITU-T QL option 2";
                      container generation {
                        description
                          "ITU-T QL option 2 generation";
                        leaf one {
                          type enumeration {
                            enum "prs" {
                              value 42;
                              description
                                "ITU-T Option 2, Generation 1: Primary reference source";
                            }
                            enum "prtc" {
                              value 41;
                              description
                                "ITU-T Option 2, Generation 1: Primary reference timing clock";
                            }
                            enum "e-prtc" {
                              value 40;
                              description
                                "ITU-T Option 2, Generation 1: Enhanced primary reference timing clock";
                            }
                            enum "stu" {
                              value 43;
                              description
                                "ITU-T Option 2, Generation 1: Synchronized - traceability unknown";
                            }
                            enum "st2" {
                              value 44;
                              description
                                "ITU-T Option 2, Generation 1: Stratum 2";
                            }
                            enum "st3" {
                              value 45;
                              description
                                "ITU-T Option 2, Generation 1: Stratum 3";
                            }
                            enum "smc" {
                              value 48;
                              description
                                "ITU-T Option 2, Generation 1: SONET clock self timed";
                            }
                            enum "eec2" {
                              value 47;
                              description
                                "ITU-T Option 2, Generation 1: Ethernet equipment clock";
                            }
                            enum "e-eec" {
                              value 46;
                              description
                                "ITU-T Option 2, Generation 1: Ethernet ethernet equipment clock";
                            }
                            enum "st4" {
                              value 49;
                              description
                                "ITU-T Option 2, Generation 1: Stratum 4 freerun";
                            }
                            enum "dus" {
                              value 1;
                              description
                                "This signal should not be used for synchronization";
                            }
                          }
                          must
                            "not(../../../one or
                             ../two or
                             ../../../../../../highest/itu-t/option/one or
                             ../../../../../../highest/itu-t/option/two/generation/one or
                             ../../../../../../highest/itu-t/option/two/generation/two or
                             ../../../../../../exact/itu-t/option/one or
                             ../../../../../../exact/itu-t/option/two/generation/one or
                             ../../../../../../exact/itu-t/option/two/generation/two)";
                          description
                            "ITU-T QL option 2, generation 1";
                        }
                        leaf two {
                          type enumeration {
                            enum "prs" {
                              value 62;
                              description
                                "ITU-T Option 2, Generation 2: Primary reference source";
                            }
                            enum "prtc" {
                              value 61;
                              description
                                "ITU-T Option 2, Generation 2: Primary reference timing clock";
                            }
                            enum "e-prtc" {
                              value 60;
                              description
                                "ITU-T Option 2, Generation 2: Enhanced primary reference timing clock";
                            }
                            enum "stu" {
                              value 63;
                              description
                                "ITU-T Option 2, Generation 2: Synchronized - traceability unknown";
                            }
                            enum "st2" {
                              value 64;
                              description
                                "ITU-T Option 2, Generation 2: Stratum 2";
                            }
                            enum "tnc" {
                              value 65;
                              description
                                "ITU-T Option 2, Generation 2: Transit node clock";
                            }
                            enum "st3e" {
                              value 66;
                              description
                                "ITU-T Option 2, Generation 2: Stratum 3E";
                            }
                            enum "st3" {
                              value 67;
                              description
                                "ITU-T Option 2, Generation 2: Stratum 3";
                            }
                            enum "smc" {
                              value 70;
                              description
                                "ITU-T Option 2, Generation 2: SONET clock self timed";
                            }
                            enum "eec2" {
                              value 69;
                              description
                                "ITU-T Option 2, Generation 2: Ethernet equipment clock";
                            }
                            enum "e-eec" {
                              value 68;
                              description
                                "ITU-T Option 2, Generation 2: Ethernet ethernet equipment clock";
                            }
                            enum "st4" {
                              value 71;
                              description
                                "ITU-T Option 2, Generation 2: Stratum 4 freerun";
                            }
                            enum "dus" {
                              value 1;
                              description
                                "This signal should not be used for synchronization";
                            }
                          }
                          must
                            "not(../../../one or
                             ../one or
                             ../../../../../../highest/itu-t/option/one or
                             ../../../../../../highest/itu-t/option/two/generation/one or
                             ../../../../../../highest/itu-t/option/two/generation/two or
                             ../../../../../../exact/itu-t/option/one or
                             ../../../../../../exact/itu-t/option/two/generation/one or
                             ../../../../../../exact/itu-t/option/two/generation/two)";
                          description
                            "ITU-T QL option 2, generation 2";
                        }
                      }
                    }
                  }
                }
              }
              container highest {
                description
                  "Specify the highest acceptable QL value";
                container itu-t {
                  description
                    "ITU-T QL options";
                  container option {
                    description
                      "ITU-T QL options";
                    leaf one {
                      type enumeration {
                        enum "prc" {
                          value 22;
                          description
                            "ITU-T Option 1: Primary reference clock";
                        }
                        enum "prtc" {
                          value 21;
                          description
                            "ITU-T Option 1: Primary reference timing clock";
                        }
                        enum "e-prtc" {
                          value 20;
                          description
                            "ITU-T Option 1: Enhanced primary reference timing clock";
                        }
                        enum "ssu-a" {
                          value 23;
                          description
                            "ITU-T Option 1: Type I or V subordinate clock";
                        }
                        enum "ssu-b" {
                          value 24;
                          description
                            "ITU-T Option 1: Type IV subordinate clock";
                        }
                        enum "sec" {
                          value 27;
                          description
                            "ITU-T Option 1: SONET equipment clock";
                        }
                        enum "e-eec" {
                          value 25;
                          description
                            "ITU-T Option 1: Enhanced ethernet equipment clock";
                        }
                        enum "eec1" {
                          value 26;
                          description
                            "ITU-T Option 1: Ethernet equipment clock";
                        }
                        enum "dnu" {
                          value 1;
                          description
                            "This signal should not be used for synchronization";
                        }
                      }
                      must
                        "not(../two/generation/one or
                         ../two/generation/two or
                         ../../../../lowest/itu-t/option/one or
                         ../../../../lowest/itu-t/option/two/generation/one or
                         ../../../../lowest/itu-t/option/two/generation/two or
                         ../../../../exact/itu-t/option/one or
                         ../../../../exact/itu-t/option/two/generation/one or
                         ../../../../exact/itu-t/option/two/generation/two)";
                      description
                        "ITU-T QL option 1";
                    }
                    container two {
                      description
                        "ITU-T QL option 2";
                      container generation {
                        description
                          "ITU-T QL option 2 generation";
                        leaf one {
                          type enumeration {
                            enum "prs" {
                              value 42;
                              description
                                "ITU-T Option 2, Generation 1: Primary reference source";
                            }
                            enum "prtc" {
                              value 41;
                              description
                                "ITU-T Option 2, Generation 1: Primary reference timing clock";
                            }
                            enum "e-prtc" {
                              value 40;
                              description
                                "ITU-T Option 2, Generation 1: Enhanced primary reference timing clock";
                            }
                            enum "stu" {
                              value 43;
                              description
                                "ITU-T Option 2, Generation 1: Synchronized - traceability unknown";
                            }
                            enum "st2" {
                              value 44;
                              description
                                "ITU-T Option 2, Generation 1: Stratum 2";
                            }
                            enum "st3" {
                              value 45;
                              description
                                "ITU-T Option 2, Generation 1: Stratum 3";
                            }
                            enum "smc" {
                              value 48;
                              description
                                "ITU-T Option 2, Generation 1: SONET clock self timed";
                            }
                            enum "eec2" {
                              value 47;
                              description
                                "ITU-T Option 2, Generation 1: Ethernet equipment clock";
                            }
                            enum "e-eec" {
                              value 46;
                              description
                                "ITU-T Option 2, Generation 1: Ethernet ethernet equipment clock";
                            }
                            enum "st4" {
                              value 49;
                              description
                                "ITU-T Option 2, Generation 1: Stratum 4 freerun";
                            }
                            enum "dus" {
                              value 1;
                              description
                                "This signal should not be used for synchronization";
                            }
                          }
                          must
                            "not(../../../one or
                             ../two or
                             ../../../../../../lowest/itu-t/option/one or
                             ../../../../../../lowest/itu-t/option/two/generation/one or
                             ../../../../../../lowest/itu-t/option/two/generation/two or
                             ../../../../../../exact/itu-t/option/one or
                             ../../../../../../exact/itu-t/option/two/generation/one or
                             ../../../../../../exact/itu-t/option/two/generation/two)";
                          description
                            "ITU-T QL option 2, generation 1";
                        }
                        leaf two {
                          type enumeration {
                            enum "prs" {
                              value 62;
                              description
                                "ITU-T Option 2, Generation 2: Primary reference source";
                            }
                            enum "prtc" {
                              value 61;
                              description
                                "ITU-T Option 2, Generation 2: Primary reference timing clock";
                            }
                            enum "e-prtc" {
                              value 60;
                              description
                                "ITU-T Option 2, Generation 2: Enhanced primary reference timing clock";
                            }
                            enum "stu" {
                              value 63;
                              description
                                "ITU-T Option 2, Generation 2: Synchronized - traceability unknown";
                            }
                            enum "st2" {
                              value 64;
                              description
                                "ITU-T Option 2, Generation 2: Stratum 2";
                            }
                            enum "tnc" {
                              value 65;
                              description
                                "ITU-T Option 2, Generation 2: Transit node clock";
                            }
                            enum "st3e" {
                              value 66;
                              description
                                "ITU-T Option 2, Generation 2: Stratum 3E";
                            }
                            enum "st3" {
                              value 67;
                              description
                                "ITU-T Option 2, Generation 2: Stratum 3";
                            }
                            enum "smc" {
                              value 70;
                              description
                                "ITU-T Option 2, Generation 2: SONET clock self timed";
                            }
                            enum "eec2" {
                              value 69;
                              description
                                "ITU-T Option 2, Generation 2: Ethernet equipment clock";
                            }
                            enum "e-eec" {
                              value 68;
                              description
                                "ITU-T Option 2, Generation 2: Ethernet ethernet equipment clock";
                            }
                            enum "st4" {
                              value 71;
                              description
                                "ITU-T Option 2, Generation 2: Stratum 4 freerun";
                            }
                            enum "dus" {
                              value 1;
                              description
                                "This signal should not be used for synchronization";
                            }
                          }
                          must
                            "not(../../../one or
                             ../one or
                             ../../../../../../lowest/itu-t/option/one or
                             ../../../../../../lowest/itu-t/option/two/generation/one or
                             ../../../../../../lowest/itu-t/option/two/generation/two or
                             ../../../../../../exact/itu-t/option/one or
                             ../../../../../../exact/itu-t/option/two/generation/one or
                             ../../../../../../exact/itu-t/option/two/generation/two)";
                          description
                            "ITU-T QL option 2, generation 2";
                        }
                      }
                    }
                  }
                }
              }
              container exact {
                description
                  "Specify the exact QL value to use";
                container itu-t {
                  description
                    "ITU-T QL options";
                  container option {
                    description
                      "ITU-T QL options";
                    leaf one {
                      type enumeration {
                        enum "prc" {
                          value 22;
                          description
                            "ITU-T Option 1: Primary reference clock";
                        }
                        enum "prtc" {
                          value 21;
                          description
                            "ITU-T Option 1: Primary reference timing clock";
                        }
                        enum "e-prtc" {
                          value 20;
                          description
                            "ITU-T Option 1: Enhanced primary reference timing clock";
                        }
                        enum "ssu-a" {
                          value 23;
                          description
                            "ITU-T Option 1: Type I or V subordinate clock";
                        }
                        enum "ssu-b" {
                          value 24;
                          description
                            "ITU-T Option 1: Type IV subordinate clock";
                        }
                        enum "sec" {
                          value 27;
                          description
                            "ITU-T Option 1: SONET equipment clock";
                        }
                        enum "e-eec" {
                          value 25;
                          description
                            "ITU-T Option 1: Enhanced ethernet equipment clock";
                        }
                        enum "eec1" {
                          value 26;
                          description
                            "ITU-T Option 1: Ethernet equipment clock";
                        }
                        enum "dnu" {
                          value 1;
                          description
                            "This signal should not be used for synchronization";
                        }
                      }
                      must
                        "not(../two/generation/one or
                         ../two/generation/two or
                         ../../../../highest/itu-t/option/one or
                         ../../../../highest/itu-t/option/two/generation/one or
                         ../../../../highest/itu-t/option/two/generation/two or
                         ../../../../lowest/itu-t/option/one or
                         ../../../../lowest/itu-t/option/two/generation/one or
                         ../../../../lowest/itu-t/option/two/generation/two)";
                      description
                        "ITU-T QL option 1";
                    }
                    container two {
                      description
                        "ITU-T QL option 2";
                      container generation {
                        description
                          "ITU-T QL option 2 generation";
                        leaf one {
                          type enumeration {
                            enum "prs" {
                              value 42;
                              description
                                "ITU-T Option 2, Generation 1: Primary reference source";
                            }
                            enum "prtc" {
                              value 41;
                              description
                                "ITU-T Option 2, Generation 1: Primary reference timing clock";
                            }
                            enum "e-prtc" {
                              value 40;
                              description
                                "ITU-T Option 2, Generation 1: Enhanced primary reference timing clock";
                            }
                            enum "stu" {
                              value 43;
                              description
                                "ITU-T Option 2, Generation 1: Synchronized - traceability unknown";
                            }
                            enum "st2" {
                              value 44;
                              description
                                "ITU-T Option 2, Generation 1: Stratum 2";
                            }
                            enum "st3" {
                              value 45;
                              description
                                "ITU-T Option 2, Generation 1: Stratum 3";
                            }
                            enum "smc" {
                              value 48;
                              description
                                "ITU-T Option 2, Generation 1: SONET clock self timed";
                            }
                            enum "eec2" {
                              value 47;
                              description
                                "ITU-T Option 2, Generation 1: Ethernet equipment clock";
                            }
                            enum "e-eec" {
                              value 46;
                              description
                                "ITU-T Option 2, Generation 1: Ethernet ethernet equipment clock";
                            }
                            enum "st4" {
                              value 49;
                              description
                                "ITU-T Option 2, Generation 1: Stratum 4 freerun";
                            }
                            enum "dus" {
                              value 1;
                              description
                                "This signal should not be used for synchronization";
                            }
                          }
                          must
                            "not(../../../one or
                             ../two or
                             ../../../../../../highest/itu-t/option/one or
                             ../../../../../../highest/itu-t/option/two/generation/one or
                             ../../../../../../highest/itu-t/option/two/generation/two or
                             ../../../../../../lowest/itu-t/option/one or
                             ../../../../../../lowest/itu-t/option/two/generation/one or
                             ../../../../../../lowest/itu-t/option/two/generation/two)";
                          description
                            "ITU-T QL option 2, generation 1";
                        }
                        leaf two {
                          type enumeration {
                            enum "prs" {
                              value 62;
                              description
                                "ITU-T Option 2, Generation 2: Primary reference source";
                            }
                            enum "prtc" {
                              value 61;
                              description
                                "ITU-T Option 2, Generation 2: Primary reference timing clock";
                            }
                            enum "e-prtc" {
                              value 60;
                              description
                                "ITU-T Option 2, Generation 2: Enhanced primary reference timing clock";
                            }
                            enum "stu" {
                              value 63;
                              description
                                "ITU-T Option 2, Generation 2: Synchronized - traceability unknown";
                            }
                            enum "st2" {
                              value 64;
                              description
                                "ITU-T Option 2, Generation 2: Stratum 2";
                            }
                            enum "tnc" {
                              value 65;
                              description
                                "ITU-T Option 2, Generation 2: Transit node clock";
                            }
                            enum "st3e" {
                              value 66;
                              description
                                "ITU-T Option 2, Generation 2: Stratum 3E";
                            }
                            enum "st3" {
                              value 67;
                              description
                                "ITU-T Option 2, Generation 2: Stratum 3";
                            }
                            enum "smc" {
                              value 70;
                              description
                                "ITU-T Option 2, Generation 2: SONET clock self timed";
                            }
                            enum "eec2" {
                              value 69;
                              description
                                "ITU-T Option 2, Generation 2: Ethernet equipment clock";
                            }
                            enum "e-eec" {
                              value 68;
                              description
                                "ITU-T Option 2, Generation 2: Ethernet ethernet equipment clock";
                            }
                            enum "st4" {
                              value 71;
                              description
                                "ITU-T Option 2, Generation 2: Stratum 4 freerun";
                            }
                            enum "dus" {
                              value 1;
                              description
                                "This signal should not be used for synchronization";
                            }
                          }
                          must
                            "not(../../../one or
                             ../one or
                             ../../../../../../highest/itu-t/option/one or
                             ../../../../../../highest/itu-t/option/two/generation/one or
                             ../../../../../../highest/itu-t/option/two/generation/two or
                             ../../../../../../lowest/itu-t/option/one or
                             ../../../../../../lowest/itu-t/option/two/generation/one or
                             ../../../../../../lowest/itu-t/option/two/generation/two)";
                          description
                            "ITU-T QL option 2, generation 2";
                        }
                      }
                    }
                  }
                }
              }
            }
          }
          leaf wait-to-restore {
            type uint32 {
              range "0..12" {
                description
                  "Wait-to-restore time, in minutes";
              }
            }
            description
              "Set the wait-to-restore time";
          }
          container selection {
            description
              "Selection configuration commands";
            container input {
              presence "Indicates a input node is configured.";
              description
                "Enable this source for selection";
            }
          }
        }
      }
      container port-parameters {
        description
          "clock port parameter setting";
        container bits-input {
          description
            "BITS RX interface";
          container t1 {
            description
              "t1 mode";
            container esf {
              description
                "esf mode";
              container ami {
                must "not(../b8zs)";
                presence "Indicates a ami node is configured.";
                description
                  "ami mode";
              }
              container b8zs {
                must "not(../ami)";
                presence "Indicates a b8zs node is configured.";
                description
                  "b8zs mode";
              }
            }
            container d4 {
              description
                "d4 mode";
              container ami {
                must "not(../b8zs)";
                presence "Indicates a ami node is configured.";
                description
                  "ami mode";
              }
              container b8zs {
                must "not(../ami)";
                presence "Indicates a b8zs node is configured.";
                description
                  "b8zs mode";
              }
            }
          }
          container e1 {
            description
              "e1 mode";
            container non-crc-4 {
              description
                "non-crc-4 mode";
              container ami {
                must "not(../hdb3)";
                presence "Indicates a ami node is configured.";
                description
                  "ami mode";
              }
              container hdb3 {
                must "not(../ami)";
                presence "Indicates a hdb3 node is configured.";
                description
                  "hdb3 mode";
              }
            }
            container crc-4 {
              description
                "crc4 mode";
              container sa4 {
                description
                  "SSM on Sa4 bit channel";
                container ami {
                  must "not(../hdb3)";
                  presence "Indicates a ami node is configured.";
                  description
                    "ami mode";
                }
                container hdb3 {
                  must "not(../ami)";
                  presence "Indicates a hdb3 node is configured.";
                  description
                    "hdb3 mode";
                }
              }
              container sa5 {
                description
                  "SSM on Sa5 bit channel";
                container ami {
                  must "not(../hdb3)";
                  presence "Indicates a ami node is configured.";
                  description
                    "ami mode";
                }
                container hdb3 {
                  must "not(../ami)";
                  presence "Indicates a hdb3 node is configured.";
                  description
                    "hdb3 mode";
                }
              }
              container sa6 {
                description
                  "SSM on Sa6 bit channel";
                container ami {
                  must "not(../hdb3)";
                  presence "Indicates a ami node is configured.";
                  description
                    "ami mode";
                }
                container hdb3 {
                  must "not(../ami)";
                  presence "Indicates a hdb3 node is configured.";
                  description
                    "hdb3 mode";
                }
              }
              container sa7 {
                description
                  "SSM on Sa7 bit channel";
                container ami {
                  must "not(../hdb3)";
                  presence "Indicates a ami node is configured.";
                  description
                    "ami mode";
                }
                container hdb3 {
                  must "not(../ami)";
                  presence "Indicates a hdb3 node is configured.";
                  description
                    "hdb3 mode";
                }
              }
              container sa8 {
                description
                  "SSM on Sa8 bit channel";
                container ami {
                  must "not(../hdb3)";
                  presence "Indicates a ami node is configured.";
                  description
                    "ami mode";
                }
                container hdb3 {
                  must "not(../ami)";
                  presence "Indicates a hdb3 node is configured.";
                  description
                    "hdb3 mode";
                }
              }
            }
          }
          container two-m {
            must "not(../sixty-four-k-input-only)";
            presence "Indicates a two-m node is configured.";
            description
              "2m mode";
          }
          container sixty-four-k-input-only {
            must "not(../two-m)";
            presence "Indicates a sixty-four-k-input-only node is configured.";
            description
              "64k-input-only mode";
          }
        }
        container bits-output {
          description
            "BITS TX interface";
          container t1 {
            description
              "t1 mode";
            container esf {
              description
                "esf mode";
              container ami {
                description
                  "ami mode";
                container zero {
                  must
                    "not(../one or ../two
                     or ../three or ../four)";
                  presence "Indicates a zero node is configured.";
                  description
                    "line buildout 0-133ft";
                }
                container one {
                  must
                    "not(../zero or ../two
                     or ../three or ../four)";
                  presence "Indicates a one node is configured.";
                  description
                    "line buildout 134-266ft";
                }
                container two {
                  must
                    "not(../zero or ../one
                     or ../three or ../four)";
                  presence "Indicates a two node is configured.";
                  description
                    "line buildout 267-399ft";
                }
                container three {
                  must
                    "not(../zero or ../one
                     or ../two or ../four)";
                  presence "Indicates a three node is configured.";
                  description
                    "line buildout 400-533ft";
                }
                container four {
                  must
                    "not(../zero or ../one
                     or ../two or ../three)";
                  presence "Indicates a four node is configured.";
                  description
                    "line buildout 534-655ft";
                }
              }
              container b8zs {
                description
                  "b8zs mode";
                container zero {
                  must
                    "not(../one or ../two
                     or ../three or ../four)";
                  presence "Indicates a zero node is configured.";
                  description
                    "line buildout 0-133ft";
                }
                container one {
                  must
                    "not(../zero or ../two
                     or ../three or ../four)";
                  presence "Indicates a one node is configured.";
                  description
                    "line buildout 134-266ft";
                }
                container two {
                  must
                    "not(../zero or ../one
                     or ../three or ../four)";
                  presence "Indicates a two node is configured.";
                  description
                    "line buildout 267-399ft";
                }
                container three {
                  must
                    "not(../zero or ../one
                     or ../two or ../four)";
                  presence "Indicates a three node is configured.";
                  description
                    "line buildout 400-533ft";
                }
                container four {
                  must
                    "not(../zero or ../one
                     or ../two or ../three)";
                  presence "Indicates a four node is configured.";
                  description
                    "line buildout 534-655ft";
                }
              }
            }
            container d4 {
              description
                "d4 mode";
              container ami {
                description
                  "ami mode";
                container zero {
                  must
                    "not(../one or ../two
                     or ../three or ../four)";
                  presence "Indicates a zero node is configured.";
                  description
                    "line buildout 0-133ft";
                }
                container one {
                  must
                    "not(../zero or ../two
                     or ../three or ../four)";
                  presence "Indicates a one node is configured.";
                  description
                    "line buildout 134-266ft";
                }
                container two {
                  must
                    "not(../zero or ../one
                     or ../three or ../four)";
                  presence "Indicates a two node is configured.";
                  description
                    "line buildout 267-399ft";
                }
                container three {
                  must
                    "not(../zero or ../one
                     or ../two or ../four)";
                  presence "Indicates a three node is configured.";
                  description
                    "line buildout 400-533ft";
                }
                container four {
                  must
                    "not(../zero or ../one
                     or ../two or ../three)";
                  presence "Indicates a four node is configured.";
                  description
                    "line buildout 534-655ft";
                }
              }
              container b8zs {
                description
                  "b8zs mode";
                container zero {
                  must
                    "not(../one or ../two
                     or ../three or ../four)";
                  presence "Indicates a zero node is configured.";
                  description
                    "line buildout 0-133ft";
                }
                container one {
                  must
                    "not(../zero or ../two
                     or ../three or ../four)";
                  presence "Indicates a one node is configured.";
                  description
                    "line buildout 134-266ft";
                }
                container two {
                  must
                    "not(../zero or ../one
                     or ../three or ../four)";
                  presence "Indicates a two node is configured.";
                  description
                    "line buildout 267-399ft";
                }
                container three {
                  must
                    "not(../zero or ../one
                     or ../two or ../four)";
                  presence "Indicates a three node is configured.";
                  description
                    "line buildout 400-533ft";
                }
                container four {
                  must
                    "not(../zero or ../one
                     or ../two or ../three)";
                  presence "Indicates a four node is configured.";
                  description
                    "line buildout 534-655ft";
                }
              }
            }
          }
          container e1 {
            description
              "e1 mode";
            container non-crc-4 {
              description
                "non-crc-4 mode";
              container ami {
                must "not(../hdb3)";
                presence "Indicates a ami node is configured.";
                description
                  "ami mode";
              }
              container hdb3 {
                must "not(../ami)";
                presence "Indicates a hdb3 node is configured.";
                description
                  "hdb3 mode";
              }
            }
            container crc-4 {
              description
                "crc4 mode";
              container sa4 {
                description
                  "SSM on Sa4 bit channel";
                container ami {
                  must "not(../hdb3)";
                  presence "Indicates a ami node is configured.";
                  description
                    "ami mode";
                }
                container hdb3 {
                  must "not(../ami)";
                  presence "Indicates a hdb3 node is configured.";
                  description
                    "hdb3 mode";
                }
              }
              container sa5 {
                description
                  "SSM on Sa5 bit channel";
                container ami {
                  must "not(../hdb3)";
                  presence "Indicates a ami node is configured.";
                  description
                    "ami mode";
                }
                container hdb3 {
                  must "not(../ami)";
                  presence "Indicates a hdb3 node is configured.";
                  description
                    "hdb3 mode";
                }
              }
              container sa6 {
                description
                  "SSM on Sa6 bit channel";
                container ami {
                  must "not(../hdb3)";
                  presence "Indicates a ami node is configured.";
                  description
                    "ami mode";
                }
                container hdb3 {
                  must "not(../ami)";
                  presence "Indicates a hdb3 node is configured.";
                  description
                    "hdb3 mode";
                }
              }
              container sa7 {
                description
                  "SSM on Sa7 bit channel";
                container ami {
                  must "not(../hdb3)";
                  presence "Indicates a ami node is configured.";
                  description
                    "ami mode";
                }
                container hdb3 {
                  must "not(../ami)";
                  presence "Indicates a hdb3 node is configured.";
                  description
                    "hdb3 mode";
                }
              }
              container sa8 {
                description
                  "SSM on Sa8 bit channel";
                container ami {
                  must "not(../hdb3)";
                  presence "Indicates a ami node is configured.";
                  description
                    "ami mode";
                }
                container hdb3 {
                  must "not(../ami)";
                  presence "Indicates a hdb3 node is configured.";
                  description
                    "hdb3 mode";
                }
              }
            }
          }
          container two-m {
            must "not(../six-m-output-only)";
            presence "Indicates a two-m node is configured.";
            description
              "2m mode";
          }
          container six-m-output-only {
            must "not(../two-m)";
            presence "Indicates a six-m-output-only node is configured.";
            description
              "6m-output-only mode";
          }
        }
        container gps-input {
          description
            "GPS TOD/10MHz/1PPS input interface";
          container tod-format {
            description
              "Specify the TOD msg format";
            container cisco {
              description
                "TOD msg in Cisco ASCII format";
              container pps-input {
                description
                  "Specify the 1PPS input mode select";
                container ttl {
                  must "not(../rs422)";
                  presence "Indicates a ttl node is configured.";
                  description
                    "TTL 1PPS input";
                }
                container rs422 {
                  must "not(../ttl)";
                  presence "Indicates a rs422 node is configured.";
                  description
                    "RS422 1PPS input";
                }
              }
            }
            container ntp4 {
              description
                "TOD msg in NTP Type 4 format";
              container pps-input {
                description
                  "Specify the 1PPS input mode select";
                container ttl {
                  must "not(../rs422)";
                  presence "Indicates a ttl node is configured.";
                  description
                    "TTL 1PPS input";
                }
                container rs422 {
                  must "not(../ttl)";
                  presence "Indicates a rs422 node is configured.";
                  description
                    "RS422 1PPS input";
                }
              }
            }
            container gprmc {
              description
                "TOD msg in NMEA/GPRMC format";
              container pps-input {
                description
                  "Specify the 1PPS input mode select";
                container ttl {
                  must "not(../rs422)";
                  presence "Indicates a ttl node is configured.";
                  description
                    "TTL 1PPS input";
                }
                container rs422 {
                  must "not(../ttl)";
                  presence "Indicates a rs422 node is configured.";
                  description
                    "RS422 1PPS input";
                }
              }
            }
          }
          container offset {
            description
              "Set a fixed offset from received TOD to translate into PTP time";
            container utc {
              must "not(../tai or ../gps)";
              presence "Indicates a utc node is configured.";
              description
                "ToD provides UTC time";
            }
            container tai {
              must "not(../utc or ../gps)";
              presence "Indicates a tai node is configured.";
              description
                "ToD provides TAI time";
            }
            container gps {
              must "not(../utc or ../tai)";
              presence "Indicates a gps node is configured.";
              description
                "ToD provides GPS time";
            }
          }
          container baud-rate {
            description
              "Set the baud-rate for the ToD UART input";
            container bps-1200 {
              must
                "not(../bps-2400 or ../bps-4800
                 or ../bps-9600 or ../bps-19200
                 or ../bps-38400 or ../bps-76800
                 or ../bps-153600)";
              presence "Indicates a bps-1200 node is configured.";
              description
                "1200 bps";
            }
            container bps-2400 {
              must
                "not(../bps-1200 or ../bps-4800
                 or ../bps-9600 or ../bps-19200
                 or ../bps-38400 or ../bps-76800
                 or ../bps-153600)";
              presence "Indicates a bps-2400 node is configured.";
              description
                "2400 bps";
            }
            container bps-4800 {
              must
                "not(../bps-1200 or ../bps-2400
                 or ../bps-9600 or ../bps-19200
                 or ../bps-38400 or ../bps-76800
                 or ../bps-153600)";
              presence "Indicates a bps-4800 node is configured.";
              description
                "4800 bps";
            }
            container bps-9600 {
              must
                "not(../bps-1200 or ../bps-2400
                 or ../bps-4800 or ../bps-19200
                 or ../bps-38400 or ../bps-76800
                 or ../bps-153600)";
              presence "Indicates a bps-9600 node is configured.";
              description
                "9600 bps";
            }
            container bps-19200 {
              must
                "not(../bps-1200 or ../bps-2400
                 or ../bps-4800 or ../bps-9600
                 or ../bps-38400 or ../bps-76800
                 or ../bps-153600)";
              presence "Indicates a bps-19200 node is configured.";
              description
                "19200 bps";
            }
            container bps-38400 {
              must
                "not(../bps-1200 or ../bps-2400
                 or ../bps-4800 or ../bps-9600
                 or ../bps-19200 or ../bps-76800
                 or ../bps-153600)";
              presence "Indicates a bps-38400 node is configured.";
              description
                "38400 bps";
            }
            container bps-76800 {
              must
                "not(../bps-1200 or ../bps-2400
                 or ../bps-4800 or ../bps-9600
                 or ../bps-19200 or ../bps-38400
                 or ../bps-153600)";
              presence "Indicates a bps-76800 node is configured.";
              description
                "76800 bps";
            }
            container bps-153600 {
              must
                "not(../bps-1200 or ../bps-2400
                 or ../bps-4800 or ../bps-9600
                 or ../bps-19200 or ../bps-38400
                 or ../bps-76800)";
              presence "Indicates a bps-153600 node is configured.";
              description
                "153600 bps";
            }
          }
        }
      }
      container shutdown {
        presence "Indicates a shutdown node is configured.";
        description
          "Disable the SyncE Port";
      }
    }
  }
}
