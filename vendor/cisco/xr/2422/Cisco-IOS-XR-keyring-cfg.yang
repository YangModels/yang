module Cisco-IOS-XR-keyring-cfg {
  namespace "http://cisco.com/ns/yang/Cisco-IOS-XR-keyring-cfg";
  prefix keyring-cfg;

  import ietf-inet-types {
    prefix inet;
  }
  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR keyring package configuration.
     
     This module contains definitions
     for the following management objects:
       keyring: Keyring config commands
     
     Copyright (c) 2013-2024 by Cisco Systems, Inc.
     All rights reserved.";

  revision 2024-01-10 {
    description
      "FQDN identity Support
       2023-01-30
         PPK Support";
    semver:module-version "1.2.0";
  }
  revision 2019-04-05 {
    description
      "Establish semantic version baseline.";
    semver:module-version "1.1.0";
  }
  revision 2019-02-04 {
    description
      "Keyring Configuration Yang Support";
  }
  revision 2015-11-09 {
    description
      "IOS XR 6.0 revision.";
  }

  typedef Ikev2-id {
    type enumeration {
      enum "ikev2-cli-identity-type-ipv4" {
        value 1;
        description
          "IPv4 Address Identity";
      }
      enum "ikev2-cli-identity-type-fqdn" {
        value 2;
        description
          "FQDN Identity";
      }
      enum "ikev2-cli-identity-type-fqdn-domain" {
        value 3;
        description
          "Domain Identity";
      }
    }
    description
      "Ikev2 id";
  }

  typedef Keyring-encryption {
    type enumeration {
      enum "type7" {
        value 1;
        description
          "Type 7 encryption";
      }
    }
    description
      "Keyring encryption";
  }

  container keyring {
    description
      "Keyring config commands";
    list keyring-name {
      key "name";
      description
        "Keyring name";
      container peer-names {
        description
          "Keyring peer config commands";
        list peer-name {
          key "name";
          description
            "Keyring peer name";
          container address {
            presence "enable address";
            description
              "IP Address to identify the peer";
            leaf ip {
              type inet:ipv4-address-no-zone;
              description
                "IP Address";
            }
            leaf subnet {
              type inet:ipv4-address-no-zone;
              description
                "Subnet";
            }
          }
          container identity {
            description
              "Specify IKE identity to use";
            leaf id-type {
              type Ikev2-id;
              description
                "identity type";
            }
            leaf ip-address {
              type inet:ipv4-address-no-zone;
              description
                "IPv4 Address identity";
            }
            leaf fqdn {
              type string {
                length "1..255";
              }
              description
                "Fqdn/Domain identity";
            }
          }
          container psk {
            description
              "Pre-shared key for peer";
            container local-remote-key {
              description
                "Local/Remote pre-shared key for the peer";
              leaf local {
                type xr:Proprietary-password;
                description
                  "Local pre-shared key";
              }
              leaf remote {
                type xr:Proprietary-password;
                description
                  "Remote pre-shared key";
              }
              leaf encryption-type {
                type Keyring-encryption;
                default "type7";
                description
                  "encryption type used to store key";
              }
            }
            container both-key {
              description
                "Both pre-shared key for the peer";
              leaf string {
                type xr:Proprietary-password;
                description
                  "Both pre-shared key";
              }
              leaf encryption-type {
                type Keyring-encryption;
                default "type7";
                description
                  "encryption type used to store key";
              }
            }
          }
          container ppk {
            description
              "ppk configuration";
            container dynamic {
              description
                "Dynamic mode ppk configuration";
              leaf sks-profile {
                type string {
                  length "1..127";
                }
                description
                  "SKS profile to be used";
              }
              leaf required {
                type empty;
                description
                  "ppk required or not";
              }
            }
            container manual {
              description
                "Manual mode ppk configuration";
              leaf id {
                type string {
                  length "1..127";
                  pattern "(([0-9]+)|([a-z]+)|([A-Z]+)|([+/]+))+";
                }
                description
                  "PPK id to be used";
              }
              leaf key {
                type xr:Proprietary-password {
                  pattern "([^!](([0-9]+)|([a-f]+)|([A-F]+))+)|(!(([0-9]+)|([a-z]+)|([A-Z]+)|([/+]))+)";
                }
                description
                  "key for ppk manual mode";
              }
              leaf encryption-type {
                type Keyring-encryption;
                default "type7";
                description
                  "encryption type used to store key";
              }
              leaf required {
                type empty;
                description
                  "ppk required or not";
              }
            }
          }
          leaf peer-sub {
            type empty;
            mandatory true;
            description
              "This indicates existence of keyring-peer";
          }
          leaf name {
            type xr:Cisco-ios-xr-string {
              length "1..32";
            }
            description
              "Name of the keyring-peer";
          }
        }
      }
      leaf keyring-sub {
        type empty;
        mandatory true;
        description
          "This indicated existence of keyring";
      }
      leaf name {
        type xr:Cisco-ios-xr-string {
          length "1..32";
        }
        description
          "Name of the keyring";
      }
    }
  }
}
