module Cisco-IOS-XR-um-ppp-cfg {
  namespace "http://cisco.com/ns/yang/Cisco-IOS-XR-um-ppp-cfg";
  prefix um-ppp-cfg;

  import Cisco-IOS-XR-types {
    prefix xr;
  }
  import ietf-inet-types {
    prefix inet;
  }
  import Cisco-IOS-XR-um-interface-cfg {
    prefix a1;
  }
  import Cisco-IOS-XR-um-dynamic-template-cfg {
    prefix a2;
  }
  import Cisco-IOS-XR-um-location-cfg {
    prefix location;
  }
  import tailf-common {
    prefix tailf;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ppp package configuration.
     
     This YANG module augments the
     modules with configuration data.
     
     Copyright (c) 2021-2022 by Cisco Systems, Inc.
     All rights reserved.";

  revision 2022-07-11 {
    description
      "Added missing description statement to nodes";
    semver:module-version "1.1.0";
  }
  revision 2021-05-10 {
    description
      "Initial release";
    semver:module-version "1.0.0";
  }

  grouping IF-BODY {
    description
      "Grouping for interface";
    container ppp {
      when "../a1:interface-name[starts-with(text(),'POS')] or ../a1:interface-name[starts-with(text(),'serial')] or ../a1:interface-name[starts-with(text(),'GCC0')] or ../a1:interface-name[starts-with(text(),'GCC1')] or ../a1:interface-name[starts-with(text(),'multilink')]" {
        tailf:dependency "../a1:interface-name";
      }
      description
        "Point-to-Point Protocol";
      leaf max-terminate {
        type uint32 {
          range "2..10" {
            description
              "number of retries";
          }
        }
        description
          "Configure maximum number of Term-Requests";
      }
      leaf max-configure {
        type uint32 {
          range "4..20" {
            description
              "number of retries";
          }
        }
        description
          "Configure maximum number of unacknowledged Conf-Requests";
      }
      leaf max-failure {
        type uint32 {
          range "2..10" {
            description
              "number of retries";
          }
        }
        description
          "Configure maximum number of consecutive Conf-Naks";
      }
      container ipcp {
        description
          "Set IPCP negotiation options";
        container peer-address {
          description
            "Change peer-address configuration";
          leaf default {
            type inet:ipv4-address-no-zone;
            description
              "Default peer-address";
          }
        }
        container neighbor-route {
          description
            "IPCP neighbor route installation";
          container disable {
            presence "Indicates a disable node is configured.";
            description
              "disable IPCP neighbor route installation";
          }
        }
        container dns {
          presence "Indicates a dns node is configured.";
          description
            "DNS options";
          leaf primary-address {
            type inet:ipv4-address-no-zone;
            mandatory true;
            description
              "Primary DNS IP address";
          }
          leaf secondary-address {
            type inet:ipv4-address-no-zone;
            description
              "Secondary DNS IP address";
          }
        }
        leaf proxy-address {
          type inet:ipv4-address-no-zone;
          description
            "Change proxy-address configuration for IP Interworking";
        }
      }
      container authentication {
        presence "Indicates a authentication node is configured.";
        description
          "Set PPP link authentication method";
        leaf method1 {
          type enumeration {
            enum "pap" {
              value 1;
              description
                "Authenticate using PAP";
            }
            enum "chap" {
              value 2;
              description
                "Authenticate using CHAP";
            }
            enum "ms-chap" {
              value 3;
              description
                "Authenticate using Microsoft-CHAP";
            }
          }
          mandatory true;
          description
            "Set 1st authentication method";
        }
        leaf method2 {
          type enumeration {
            enum "pap" {
              value 1;
              description
                "Authenticate using PAP";
            }
            enum "chap" {
              value 2;
              description
                "Authenticate using CHAP";
            }
            enum "ms-chap" {
              value 3;
              description
                "Authenticate using Microsoft-CHAP";
            }
          }
          must "../method1";
          description
            "Set 2nd authentication method";
        }
        leaf method3 {
          type enumeration {
            enum "pap" {
              value 1;
              description
                "Authenticate using PAP";
            }
            enum "chap" {
              value 2;
              description
                "Authenticate using CHAP";
            }
            enum "ms-chap" {
              value 3;
              description
                "Authenticate using Microsoft-CHAP";
            }
          }
          must "../method2";
          description
            "Set 3rd authentication method";
        }
        leaf list-name {
          type union {
            type string {
              pattern "default" {
                description
                  "Use the default authentication list";
              }
            }
            type string {
              length "1..1024";
            }
          }
          description
            "Use an authentication list with this name";
        }
      }
      container chap {
        description
          "Challenge Handshake Authentication Protocol (CHAP)";
        container password {
          description
            "Set default CHAP password";
          leaf encrypted {
            type xr:Proprietary-password;
            description
              "Specifies a HIDDEN password will follow";
          }
        }
        container refuse {
          presence "Indicates a refuse node is configured.";
          description
            "Refuse to authenticate using CHAP";
        }
        leaf hostname {
          type xr:Cisco-ios-xr-string {
            length "1..800" {
              description
                "The CHAP hostname";
            }
          }
          description
            "Set the CHAP hostname";
        }
      }
      container loopback {
        description
          "Loopback configuration";
        container ignore {
          presence "Indicates a ignore node is configured.";
          description
            "Allow magic numbers to be equal";
        }
      }
      leaf max-bad-auth {
        type uint32 {
          range "0..10" {
            description
              "Number of attempts allowed";
          }
        }
        description
          "Allow multiple authentication failures";
      }
      container multilink {
        when "../../a1:interface-name[starts-with(text(),'Multilink')]" {
          tailf:dependency "../../a1:interface-name";
        }
        description
          "Configure PPP Multilink settings";
        container minimum-active {
          description
            "Configure the minimum requirements to activate the interface";
          leaf links {
            type uint32 {
              range "1..65535" {
                description
                  "Number of links";
              }
            }
            description
              "Configure the minimum number of active links required";
          }
        }
        container multiclass {
          presence "Indicates a multiclass node is configured.";
          description
            "Configure Multi-Class Multilink PPP settings";
          container local {
            description
              "Configure MCMP options for the local host";
            leaf initial {
              type uint32 {
                range "1..16" {
                  description
                    "Local Initial number of MCMP classes";
                }
              }
              must "../maximum";
              description
                "Set initial number of suspension classes to offer in our Conf-req";
            }
            leaf maximum {
              type uint32 {
                range "1..16" {
                  description
                    "Local maximum number of MCMP classes";
                }
              }
              must "../initial";
              description
                "Set maximum number of suspension classes to offer in our Conf-req";
            }
          }
          container remote {
            description
              "Configure MCMP Options for the peer";
            leaf apply {
              type uint32 {
                range "1..16" {
                  description
                    "Minimum number of MCMP classes for Peer";
                }
              }
              description
                "Set minimum number of suspension classes to accept in peer's Conf-req";
            }
          }
        }
      }
      container ms-chap {
        description
          "Microsoft Challenge Handshake Authentication Protocol (MS-CHAP)";
        container password {
          description
            "Set default MS-CHAP password";
          leaf encrypted {
            type xr:Proprietary-password;
            description
              "Specifies a HIDDEN password will follow";
          }
        }
        container refuse {
          presence "Indicates a refuse node is configured.";
          description
            "Refuse to authenticate using MS-CHAP";
        }
        leaf hostname {
          type xr:Cisco-ios-xr-string {
            length "1..800" {
              description
                "The MS-CHAP hostname";
            }
          }
          description
            "Set the MS-CHAP hostname";
        }
      }
      container pap {
        description
          "Configure PAP user name and password to send";
        leaf sent-username {
          type xr:Cisco-ios-xr-string {
            length "1..800" {
              description
                "Outbound PAP username";
            }
          }
          description
            "Set outbound PAP username";
        }
        container password {
          description
            "Set outbound PAP password";
          leaf encrypted {
            type xr:Proprietary-password;
            description
              "Specifies a HIDDEN password will follow";
          }
        }
        container refuse {
          presence "Indicates a refuse node is configured.";
          description
            "Refuse to authenticate using PAP";
        }
      }
      container timeout {
        description
          "Set PPP timeout parameters";
        leaf authentication {
          type uint32 {
            range "3..30" {
              description
                "Seconds";
            }
          }
          description
            "Maximum time to wait for an authentication response";
        }
      }
    }
    container ssrp {
      presence "Indicates a ssrp node is configured.";
      description
        "Session State Replication Protocol config";
      leaf group {
        type uint32 {
          range "1..65535" {
            description
              "SSRP Group ID";
          }
        }
        mandatory true;
        description
          "SSRP Session's group";
      }
      leaf id {
        type uint32 {
          range "1..4294967295" {
            description
              "SSRP Session ID";
          }
        }
        mandatory true;
        description
          "SSRP Session's ID";
      }
    }
  }

  grouping TEMPLATE-BODY {
    description
      "Grouping for template";
    container ppp {
      description
        "Point-to-Point Protocol";
      container ipcp {
        description
          "Set IPCP negotiation options";
        container peer-address {
          description
            "Change peer-address configuration";
          leaf pool {
            type xr:Cisco-ios-xr-string {
              length "1..800" {
                description
                  "Name of pool";
              }
            }
            description
              "Name of peer-address pool to use";
          }
        }
        container dns {
          presence "Indicates a dns node is configured.";
          description
            "DNS options";
          leaf primary-address {
            type inet:ipv4-address-no-zone;
            mandatory true;
            description
              "Primary DNS IP address";
          }
          leaf secondary-address {
            type inet:ipv4-address-no-zone;
            description
              "Secondary DNS IP address";
          }
        }
        leaf wins-primary {
          type inet:ipv4-address-no-zone;
          description
            "Primary WINS IP address";
        }
        leaf wins-secondary {
          type inet:ipv4-address-no-zone;
          must "../wins-primary";
          description
            "Secondary WINS IP address";
        }
        leaf mask {
          type inet:ipv4-address-no-zone;
          description
            "The IPv4 netmask to use for the peer";
        }
        container renegotiation {
          description
            "Peer renegotiation options";
          container ignore {
            presence "Indicates a ignore node is configured.";
            description
              "Ignore attempts by the peer to renegotiate IPCP";
          }
        }
        container passive {
          presence "Indicates a passive node is configured.";
          description
            "Run IPCP in Passive mode";
        }
        container prot-rej {
          presence "Indicates a prot-rej node is configured.";
          description
            "Protocol-Reject IPCP";
        }
      }
      container ipv6cp {
        description
          "Set IPv6CP negotiation options";
        leaf peer-interface-id {
          type xr:Cisco-ios-xr-string {
            length "16" {
              description
                "64-bit Peer Interface-ID (hex value without leading 0x)";
            }
            pattern "[0-9a-fA-F]{16}";
          }
          description
            "Specify the Interface-ID for the peer";
        }
        container renegotiation {
          description
            "Peer renegotiation options";
          container ignore {
            presence "Indicates a ignore node is configured.";
            description
              "Ignore attempts by the peer to renegotiate IPv6CP";
          }
        }
        container passive {
          presence "Indicates a passive node is configured.";
          description
            "Run IPv6CP in Passive mode";
        }
        container prot-rej {
          presence "Indicates a prot-rej node is configured.";
          description
            "Protocol-Reject IPv6CP";
        }
      }
      leaf max-configure {
        type uint32 {
          range "4..20" {
            description
              "number of retries";
          }
        }
        description
          "Configure maximum number of unacknowledged Conf-Requests";
      }
      leaf max-failure {
        type uint32 {
          range "2..10" {
            description
              "number of retries";
          }
        }
        description
          "Configure maximum number of consecutive Conf-Naks";
      }
      leaf prot-reject-timeout {
        type uint32 {
          range "1..60" {
            description
              "timeout value in seconds";
          }
        }
        description
          "Configure protocol reject timeout";
      }
      leaf max-bad-auth {
        type uint32 {
          range "0..10" {
            description
              "Number of attempts allowed";
          }
        }
        description
          "Allow multiple authentication failures";
      }
      container chap {
        description
          "Configure CHAP";
        leaf hostname {
          type xr:Cisco-ios-xr-string {
            length "1..800" {
              description
                "The CHAP hostname";
            }
          }
          description
            "Set the CHAP hostname";
        }
        container password {
          description
            "Set default CHAP password";
          leaf encrypted {
            type xr:Proprietary-password;
            description
              "Specifies a HIDDEN password will follow";
          }
        }
      }
      container ms-chap {
        description
          "Configure MS-CHAP";
        leaf hostname {
          type xr:Cisco-ios-xr-string {
            length "1..800" {
              description
                "The MS-CHAP hostname";
            }
          }
          description
            "Set the MS-CHAP hostname";
        }
        container password {
          description
            "Set default MS-CHAP password";
          leaf encrypted {
            type xr:Proprietary-password;
            description
              "Specifies a HIDDEN password will follow";
          }
        }
      }
      container timeout {
        description
          "Set timeout";
        leaf authentication {
          type uint32 {
            range "3..30" {
              description
                "Seconds";
            }
          }
          description
            "Maximum time to wait for an authentication response";
        }
        leaf absolute {
          type uint32 {
            range "0..35000000" {
              description
                "Minutes";
            }
          }
          description
            "The absolute timeout for a PPP session";
        }
        leaf seconds {
          type uint32 {
            range "0..59" {
              description
                "Seconds";
            }
          }
          must "../absolute";
          description
            "Seconds";
        }
        leaf retry {
          type uint32 {
            range "1..10" {
              description
                "Seconds";
            }
          }
          description
            "Maximum time to wait for a response during PPP negotiation";
        }
      }
      container lcp {
        description
          "LCP global config";
        container renegotiation {
          description
            "Peer renegotiation options";
          container ignore {
            presence "Indicates a ignore node is configured.";
            description
              "Ignore attempts by the peer to renegotiate LCP";
          }
        }
        leaf delay {
          type uint32 {
            range "0..255" {
              description
                "Seconds";
            }
          }
          description
            "Set the time to delay before starting active LCP negotiations";
        }
        leaf milliseconds {
          type uint32 {
            range "0..999" {
              description
                "Milliseconds";
            }
          }
          must "../delay";
          description
            "Milliseconds";
        }
        container send-termreq-on-shutdown {
          presence "Indicates a send-termreq-on-shutdown node is configured.";
          description
            "Send LCP Term Request on shutdown option";
        }
      }
      container mru {
        description
          "Maximum receive unit option";
        container ignore {
          presence "Indicates a ignore node is configured.";
          description
            "Ignore the MRU value negotiated with peer";
        }
      }
      container pap {
        description
          "Configure PAP";
        container accept {
          description
            "Accept parameters during authentication";
          container null-password {
            presence "Indicates a null-password node is configured.";
            description
              "Accept null password";
          }
        }
        leaf sent-username {
          type xr:Cisco-ios-xr-string {
            length "1..800" {
              description
                "Outbound PAP username";
            }
          }
          description
            "Set outbound PAP username";
        }
        container password {
          description
            "Set outbound PAP password";
          leaf encrypted {
            type xr:Proprietary-password;
            description
              "Specifies a HIDDEN password will follow";
          }
        }
      }
      container authentication {
        presence "Indicates a authentication node is configured.";
        description
          "Set PPP link authentication method";
        leaf method1 {
          type enumeration {
            enum "pap" {
              value 1;
              description
                "Authenticate using PAP";
            }
            enum "chap" {
              value 2;
              description
                "Authenticate using CHAP";
            }
            enum "ms-chap" {
              value 3;
              description
                "Authenticate using Microsoft-CHAP";
            }
          }
          mandatory true;
          description
            "Set 1st authentication method";
        }
        leaf method2 {
          type enumeration {
            enum "pap" {
              value 1;
              description
                "Authenticate using PAP";
            }
            enum "chap" {
              value 2;
              description
                "Authenticate using CHAP";
            }
            enum "ms-chap" {
              value 3;
              description
                "Authenticate using Microsoft-CHAP";
            }
          }
          must "../method1";
          description
            "Set 2nd authentication method";
        }
        leaf method3 {
          type enumeration {
            enum "pap" {
              value 1;
              description
                "Authenticate using PAP";
            }
            enum "chap" {
              value 2;
              description
                "Authenticate using CHAP";
            }
            enum "ms-chap" {
              value 3;
              description
                "Authenticate using Microsoft-CHAP";
            }
          }
          must "../method2";
          description
            "Set 3rd authentication method";
        }
      }
    }
    container keepalive {
      description
        "Set the keepalive interval, or disable keepalives";
      container disable {
        must "not(../enable)";
        presence "Indicates a disable node is configured.";
        description
          "Disable keepalives";
      }
      leaf enable {
        type uint32 {
          range "10..180" {
            description
              "Enable keepalives with this interval (default is 60 seconds for RP Subscriber, 120 seconds for LC Subscriber)";
          }
        }
        must "not(../disable) and ../keepalive-retry-count";
        description
          "Enable keepalives with this interval (default is 60 seconds for RP Subscriber, 120 seconds for LC Subscriber)";
      }
      leaf keepalive-retry-count {
        type uint32 {
          range "1..255" {
            description
              "Set the keepalive retry count (default is 5)";
          }
        }
        must "../enable";
        description
          "Set the keepalive retry count (default is 5)";
      }
    }
  }

  grouping LOCATION-BODY {
    description
      "Grouping for location";
    container ssrp {
      presence "Indicates a ssrp node is configured.";
      description
        "Session State Replication Protocol config";
      container groups {
        description
          "SSRP Group config";
        list group {
          key "group-id";
          description
            "SSRP Group config";
          leaf group-id {
            type uint32 {
              range "1..65535" {
                description
                  "SSRP Group ID";
              }
            }
            description
              "SSRP Group config";
          }
          leaf profile {
            type union {
              type string {
                pattern "default" {
                  description
                    "Use the default profile";
                }
              }
              type xr:Cisco-ios-xr-string {
                length "1..1024" {
                  description
                    "The profile name for the group";
                }
              }
            }
            mandatory true;
            description
              "The profile name for the group";
          }
        }
      }
    }
  }

  augment "/a1:interfaces/a1:interface" {
    description
      "This augment extends active nodes configuration";
    uses IF-BODY;
  }
  augment "/a1:interfaces/a1:interface-preconfigure" {
    description
      "This augment extends preconfigured nodes
       configuration";
    uses IF-BODY;
  }
  augment "/a2:dynamic-template/a2:type/a2:ppp/a2:template" {
    description
      "This augment extends dynamic-template ppp nodes
       configuration";
    uses TEMPLATE-BODY;
  }
  augment "/location:locations/location:location" {
    description
      "This augment extends active nodes configuration";
    uses LOCATION-BODY;
  }
  augment "/location:locations/location:preconfigured-location" {
    description
      "This augment extends preconfigured nodes
       configuration";
    uses LOCATION-BODY;
  }
  container ssrp {
    description
      "Session State Replication Protocol config";
    container profiles {
      description
        "SSRP Profile Configuration";
      list profile {
        key "profile-name";
        description
          "SSRP Profile Configuration";
        leaf profile-name {
          type xr:Cisco-ios-xr-string {
            length "1..1024" {
              description
                "Name of Profile";
            }
          }
          description
            "SSRP Profile Configuration";
        }
        container peer {
          description
            "Peer SSRP config";
          container ipv4 {
            description
              "Peer IPv4 SSRP config";
            leaf address {
              type inet:ipv4-address-no-zone;
              description
                "Peer IPv4 address SSRP config";
            }
          }
        }
        container security {
          description
            "Security config";
          container ttl {
            description
              "Enable TTL checking";
            leaf max-hops {
              type uint32 {
                range "1..255" {
                  description
                    "Specify the max-hops value";
                }
              }
              description
                "Specify the max-hops value";
            }
          }
        }
      }
    }
  }
  container ppp {
    description
      "PPP Configuration";
    container syslog {
      description
        "Syslog Configuration";
      container enable-session-status {
        presence "Indicates a enable-session-status node is configured.";
        description
          "Enable Syslog for Session Status";
      }
    }
  }
}
