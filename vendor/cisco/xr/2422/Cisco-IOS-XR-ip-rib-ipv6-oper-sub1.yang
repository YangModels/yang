submodule Cisco-IOS-XR-ip-rib-ipv6-oper-sub1 {
  belongs-to Cisco-IOS-XR-ip-rib-ipv6-oper {
    prefix Cisco-IOS-XR-ip-rib-ipv6-oper;
  }

  import ietf-inet-types {
    prefix inet;
  }
  import ietf-yang-types {
    prefix yang;
  }
  import Cisco-IOS-XR-types {
    prefix xr;
  }
  import cisco-semver {
    prefix semver;
  }
  include Cisco-IOS-XR-ip-rib-ipv6-oper-sub2 {
    revision-date 2023-11-01;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR ip-rib-ipv6 package operational data.
     
     This model is deprecated and is replaced by
     Cisco-IOS-XR-ip-rib-oper.yang which will provide the
     compatible functionalities.
     
     Copyright (c) 2013-2023 by Cisco Systems, Inc.
     All rights reserved.";

  revision 2023-11-01 {
    description
      "Deprecated. Move to Cisco-IOS-XR-ip-rib-oper";
    semver:module-version "5.0.0";
  }
  revision 2021-08-08 {
    description
      "SRv6 uSID context extended with uDX
       2021-07-20
          Flexible Algorithm attribute added to IP Route
       2021-06-24
          IID context extended with EVPN ELAN support SRv6 SID context extended with EVPN ELAN support uDT2U uDT2M EndDT2U EndDT2M L2 Path attribute extended with support for Split Horizong Group and BridgeID
       2021-03-31
          SRv6 SID Manager include per operation mode block parameters
       2021-03-25
          Add FIB redistribution flag to route bag
       2021-03-14
          SRv6 SID context extensions";
    semver:module-version "4.1.0";
  }
  revision 2020-12-11 {
    description
      "Add forwarding sidlist
       2020-09-30
           Nexthop notification model now includes client specific registration flags
       2020-09-24
           Changes to SRv6 uSID platform capabilities
       2020-07-24
           SRv6 uSID context extended for evpn";
    semver:module-version "4.0.0";
  }
  revision 2020-05-29 {
    description
      "Updated the max number of elements for opaque stats to 16 Extended rib edm path to include IID info and SID Format type
       2020-04-30
         Updated sidmgr oper to add contexts for F1 SID: DT6, DX6
       2020-04-02
         Increased path_num size in redist hist route bag to 16 bits
       2019-12-05
         Extended SidMgr info to include uSID platform capabilities
       2019-11-21
         Extended SidMgr info to include flag string and anycast flag";
    semver:module-version "3.0.0";
  }
  revision 2019-11-05 {
    description
      "Extended Nexthop and NexhopPrefix paths to include all by NH flags
       2019-10-22
         Extended rib_edm_client_stats_summary to include client stats on bcdl ugs Extended rib_edm_local_label to support AIB prefer Added EDM support for large SID stack Extended rib_edm_path to include recursion length field Extended rib_edm_path to include metric field Extended iidmgr_summary to include oor summary info Extended rib_edm_route to include l3 route type field";
    semver:module-version "2.0.0";
  }
  revision 2019-06-28 {
    description
      "Fixed NexthopPrefix path";
    semver:module-version "1.0.0";
  }
  revision 2019-06-15 {
    description
      "Fixed IPv6 Address format for Nexthops";
  }
  revision 2019-06-08 {
    description
      "Added RPF list and NHIDs";
  }
  revision 2019-05-30 {
    description
      "Fixed adverts and backup paths";
  }
  revision 2019-05-17 {
    description
      "Added Nexthops Summary, Nexthop Route, Longer Routes, Redist Clients and Client Stasts";
  }
  revision 2019-04-25 {
    description
      "Updated yang schema to extend Native Yang model for the data exposed via CLI";
  }
  revision 2019-04-05 {
    description
      "Establish semantic version baseline.";
  }
  revision 2019-02-21 {
    description
      "Yang evaluator: updates to schema descriptions and ranges";
  }
  revision 2019-01-11 {
    description
      "Route lookup key is limited to Prefix and Prefix Length";
  }
  revision 2018-11-20 {
    description
      "Add keys for route lookup via restconf.";
  }
  revision 2018-11-06 {
    description
      "Support Algorithm Label List per route";
  }
  revision 2017-09-07 {
    description
      "Fixed type translation error.";
  }
  revision 2015-11-09 {
    description
      "IOS XR 6.0 revision.";
  }

  typedef Internal-id-state {
    type enumeration {
      enum "unknown" {
        description
          "InternalID state is Unknown";
      }
      enum "in-use" {
        description
          "InternalID state is In_Use";
      }
      enum "stale" {
        description
          "InternalID state is Stale";
      }
    }
    description
      "InternalID state";
  }

  typedef Internal-id-context-nhg-key {
    type enumeration {
      enum "nhg-key-type-name" {
        value 1;
        description
          "InternalID context NHG key type name";
      }
    }
    description
      "InternalID context NHG key type";
  }

  typedef Internal-id-context {
    type enumeration {
      enum "none" {
        value 0;
        description
          "No InternalID context";
      }
      enum "evpn-vpws" {
        value 1;
        description
          "InternalID context type for EVPN-VPWS";
      }
      enum "large-sid-stack" {
        value 2;
        description
          "InternalID context type for Large SID Stack";
      }
      enum "evpn-elan" {
        value 3;
        description
          "InternalID context type for EVPN-ELAN";
      }
      enum "aft-nhg" {
        value 4;
        description
          "InternalID context type for AFT-NHG";
      }
      enum "l2vpn-ip-tunnel" {
        value 5;
        description
          "InternalID context type for L2VPN IP Tunnels";
      }
      enum "sl-id" {
        value 6;
        description
          "InternalID context type for Segment List ID";
      }
      enum "nhg" {
        value 7;
        description
          "InternalID context type for NHG";
      }
      enum "invalid" {
        value 255;
        description
          "Invalid InternalID context type";
      }
    }
    description
      "InternalID context type";
  }

  typedef Internal-id-out-of-resource-state {
    type enumeration {
      enum "oor-green" {
        description
          "Resources Available";
      }
      enum "oor-yellow" {
        description
          "Resources Warning. Minor threshold exceeded";
      }
      enum "oor-red" {
        description
          "Out of Resources. Major threshold exceeded";
      }
    }
    description
      "InternalID Out of Resource State";
  }

  grouping IIDMGR-TIMESTAMP {
    description
      "iidmgr generic timestamp";
    leaf time-in-nano-seconds {
      type uint64;
      units "nanosecond";
      description
        "Time in nano seconds elapsed since 1970-01-01 00
         :00:00 +0000 (UTC)";
    }
    leaf age-in-nano-seconds {
      type uint64;
      units "nanosecond";
      description
        "Age in nano seconds relative to current system
         time";
    }
  }

  grouping IID-OWNER {
    description
      "InternalID Owner";
    leaf owner {
      type string;
      description
        "Owner";
    }
  }

  grouping MGMT-RIB-IID-CTX-NHG-KEY-NAME {
    description
      "InternalID context NHG key name";
    leaf name {
      type string;
      description
        "Name";
    }
  }

  grouping MGMT-RIB-IID-CTX-NHG-KEY {
    description
      "MGMT RIB IID CTX NHG KEY";
    container nhg-name {
      when "../internal-id-context-nhg-key-type = 'nhg-key-type-name'" {
        description
          "../InternalIDContextNHGKeyType =
           'NHGKeyTypeName'";
      }
      description
        "InternalID context for NHG name";
      uses MGMT-RIB-IID-CTX-NHG-KEY-NAME;
    }
    leaf internal-id-context-nhg-key-type {
      type Internal-id-context-nhg-key;
      description
        "InternalIDContextNHGKeyType";
    }
  }

  grouping MGMT-RIB-IID-NHG-CTX {
    description
      "InternalID context for NHG";
    container nhg-key {
      description
        "IID ctx NHG key";
      uses MGMT-RIB-IID-CTX-NHG-KEY;
    }
  }

  grouping MGMT-RIB-IID-SL-ID-CTX {
    description
      "InternalID context for Segment List ID";
    leaf policy-id {
      type uint16;
      description
        "Policy ID";
    }
    leaf cp-preference {
      type uint32;
      description
        "Candidate Path preference";
    }
    leaf sl-name {
      type string;
      description
        "Segment List Name";
    }
  }

  grouping MGMT-RIB-IID-L2VPN-IP-TUNNEL-CTX {
    description
      "InternalID context for L2VPN_IP_TUNNEL";
    leaf evi {
      type uint32;
      description
        "EVPN Instance";
    }
    leaf encapsulation {
      type uint32;
      description
        "EVPN Encapsulation Type Differentiator";
    }
    leaf nexthop-address {
      type inet:ipv6-address;
      description
        "NH Address as V6 native or V6-encoded-v4";
    }
    leaf eth-tag {
      type uint32;
      description
        "Ethernet Tag";
    }
    leaf opaque-id {
      type uint32;
      description
        "Additional differentiator - opaque to IIDmgr";
    }
    leaf esi {
      type yang:hex-string;
      description
        "Ethernet Segment Identifier";
    }
    leaf type {
      type uint32;
      description
        "L2 route type";
    }
  }

  grouping MGMT-RIB-IID-AFT-NHG-CTX {
    description
      "InternalID context for AFT_NHG";
    leaf vrf-id {
      type uint32;
      description
        "VRF id";
    }
    leaf aft-id {
      type uint64;
      description
        "AFT id";
    }
  }

  grouping IID-EDM-SRV6-SID {
    description
      "Information for Large SID stack context used in
       IID";
    leaf sid {
      type inet:ipv6-address;
      description
        "Segment Identifier Attribute";
    }
  }

  grouping MGMT-RIB-IID-LSS-CTX {
    description
      "InternalID context for Large SID Stack";
    leaf path-interface-name {
      type xr:Interface-name;
      description
        "Path NH interface";
    }
    leaf nexthop-prefix {
      type inet:ipv6-address;
      description
        "Path NH Prefix";
    }
    leaf headend-oper-type {
      type Mgmt-srv6-headend;
      description
        "SRv6 Headend Oper type";
    }
    leaf num-sids {
      type uint32;
      description
        "Number of SID's";
    }
    leaf srv6sid-format {
      type Mgmt-srv6-sid-fmt;
      description
        "Format of the SRv6 InternalID uSID";
    }
    list sid {
      description
        "SID list";
      uses IID-EDM-SRV6-SID;
    }
  }

  grouping MGMT-RIB-IID-EVPN-ELAN-CTX {
    description
      "InternalID context for EVPN_ELAN";
    leaf evi {
      type uint32;
      description
        "EVPN Instance";
    }
    leaf encapsulation {
      type uint32;
      description
        "EVPN Encapsulation Type Differentiator";
    }
    leaf nexthop-address {
      type inet:ipv6-address;
      description
        "NH Address as V6 native or V6-encoded-v4";
    }
    leaf eth-tag {
      type uint32;
      description
        "Ethernet Tag";
    }
    leaf opaque-id {
      type uint32;
      description
        "Additional differentiator - opaque to IIDmgr";
    }
    leaf esi {
      type yang:hex-string;
      description
        "Ethernet Segment Identifier";
    }
    leaf type {
      type uint32;
      description
        "L2 route type";
    }
  }

  grouping MGMT-RIB-IID-EVPN-VPWS-CTX {
    description
      "InternalID context for EVPN_VPWS";
    leaf evi {
      type uint32;
      description
        "EVPN Instance";
    }
    leaf eth-tag {
      type uint32;
      description
        "Ethernet Tag";
    }
    leaf type {
      type uint32;
      description
        "Type";
    }
  }

  grouping MGMT-RIB-IID-CTX-KEY {
    description
      "MGMT RIB IID CTX KEY";
    container evpn-vpws {
      when "../internal-id-context-type = 'evpn-vpws'" {
        description
          "../InternalIDContextType = 'EVPN_VPWS'";
      }
      description
        "InternalID context for EVPN_VPWS";
      uses MGMT-RIB-IID-EVPN-VPWS-CTX;
    }
    container evpn-elan {
      when "../internal-id-context-type = 'evpn-elan'" {
        description
          "../InternalIDContextType = 'EVPN_ELAN'";
      }
      description
        "InternalID context for EVPN_ELAN";
      uses MGMT-RIB-IID-EVPN-ELAN-CTX;
    }
    container large-sid-stack {
      when "../internal-id-context-type = 'large-sid-stack'" {
        description
          "../InternalIDContextType = 'LargeSIDStack'";
      }
      description
        "InternalID context for LSS";
      uses MGMT-RIB-IID-LSS-CTX;
    }
    container aft-nhg {
      when "../internal-id-context-type = 'aft-nhg'" {
        description
          "../InternalIDContextType = 'AFT_NHG'";
      }
      description
        "InternalID context for AFT_NHG";
      uses MGMT-RIB-IID-AFT-NHG-CTX;
    }
    container l2vpn-ip-tunnel {
      when "../internal-id-context-type = 'l2vpn-ip-tunnel'" {
        description
          "../InternalIDContextType = 'L2VPN_IP_TUNNEL'";
      }
      description
        "InternalID context for L2VPN IP Tunnels";
      uses MGMT-RIB-IID-L2VPN-IP-TUNNEL-CTX;
    }
    container segment-list-id {
      when "../internal-id-context-type = 'sl-id'" {
        description
          "../InternalIDContextType = 'SL_ID'";
      }
      description
        "InternalID context for Segment List ID";
      uses MGMT-RIB-IID-SL-ID-CTX;
    }
    container nhg {
      when "../internal-id-context-type = 'nhg'" {
        description
          "../InternalIDContextType = 'NHG'";
      }
      description
        "InternalID context for NHG";
      uses MGMT-RIB-IID-NHG-CTX;
    }
    leaf internal-id-context-type {
      type Internal-id-context;
      description
        "InternalIDContextType";
    }
  }

  grouping MGMT-IID-CTX {
    description
      "InternalID context";
    container key {
      description
        "InternalID Context";
      uses MGMT-RIB-IID-CTX-KEY;
    }
  }

  grouping IIDMGR-IID-INFO {
    description
      "InternalID info";
    container internal-id-context {
      description
        "InternalID Context";
      uses MGMT-IID-CTX;
    }
    container create-timestamp {
      description
        "Creation timestamp";
      uses IIDMGR-TIMESTAMP;
    }
    leaf iid {
      type inet:ipv6-address;
      description
        "InternalID Prefix representation";
    }
    leaf internal-id {
      type uint32;
      description
        "InternalID Value";
    }
    leaf internal-id-table-id {
      type uint32;
      description
        "InternalID Table ID";
    }
    leaf internal-id-prod-id {
      type uint8;
      description
        "InternalID Producer ID";
    }
    leaf state {
      type Internal-id-state;
      description
        "InternalID State";
    }
    leaf has-forwarding {
      type boolean;
      description
        "Rewrite done or not";
    }
    leaf iid-usid-block {
      type inet:ipv6-address;
      description
        "Block where InternalID uSID is allocated";
    }
    list owner {
      description
        "InternalID Owner";
      uses IID-OWNER;
    }
  }

  grouping IIDMGR-PLATFORM-CAPABILITY {
    description
      "Platform Capabilities for InternalID manager";
    leaf internal-id-holdtime-mins {
      type uint32;
      units "minute";
      description
        "Default InternalID Holdtime in mins";
    }
  }

  grouping IIDMGR-PARAMS {
    description
      "InternalID Manager runtime and configured
       parameters";
    leaf is-internal-id-holdtime-configured {
      type boolean;
      description
        "Is InternalID Holdtime configured?";
    }
    leaf internal-id-holdtime-mins-configured {
      type uint32;
      units "minute";
      description
        "Configured InternalID Holdtime in mins";
    }
  }

  grouping IID-OOR-SUMMARY {
    description
      "InternalID Manager Out of Resource Summary";
    leaf out-of-resources-state {
      type Internal-id-out-of-resource-state;
      description
        "Out of Resources State for InternalIDs";
    }
    leaf oor-yellow-free-internal-id-threshold {
      type uint32;
      description
        "Threshold for Number of Free InternalID below
         which OOR Yellow State is reached";
    }
    leaf oor-green-free-internal-id-threshold {
      type uint32;
      description
        "Threshold for Number of Free InternalID above
         which OOR Green State is restored";
    }
    leaf oor-green-count {
      type uint32;
      description
        "Number of times Resources Warning or Out of
         Resources state has been cleared";
    }
    leaf oor-yellow-count {
      type uint32;
      description
        "Number of times system went into Resources
         Warning state";
    }
    leaf oor-red-count {
      type uint32;
      description
        "Number of times system went into Out of
         Resources state";
    }
  }

  grouping IIDMGR-SUMMARY {
    description
      "InternalID Manager summary";
    container internal-ids-out-of-resource-summary {
      description
        "InternalIDs Out of Resource info";
      uses IID-OOR-SUMMARY;
    }
    leaf prod-id {
      type uint8;
      description
        "Producer ID of InternalIDs";
    }
    leaf prod-internal-id-count {
      type uint32;
      description
        "Active InternalIDs of Producer";
    }
    leaf prod-stale-internal-id-count {
      type uint32;
      description
        "Stale InternalIDs of Producer";
    }
    leaf prod-checkpoint-object-count {
      type uint32;
      description
        "Checkpoint object count of Producer";
    }
  }

  grouping IIDMGR-INFO {
    description
      "InternalID manager info";
    container internal-id-mgr-summary {
      description
        "InternalID Manager summary";
      uses IIDMGR-SUMMARY;
    }
    container internal-id-mgr-params {
      description
        "InternalID Manager runtime and configured
         parameters";
      uses IIDMGR-PARAMS;
    }
    container platform-capabilities {
      description
        "Platform Capabilities";
      uses IIDMGR-PLATFORM-CAPABILITY;
    }
  }
}
