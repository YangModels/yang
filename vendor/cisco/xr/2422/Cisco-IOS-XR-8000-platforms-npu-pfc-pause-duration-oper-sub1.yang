submodule Cisco-IOS-XR-8000-platforms-npu-pfc-pause-duration-oper-sub1 {
  belongs-to Cisco-IOS-XR-8000-platforms-npu-pfc-pause-duration-oper {
    prefix Cisco-IOS-XR-8000-platforms-npu-pfc-pause-duration-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR 8000-platforms-npu-pfc-pause-duration package operational data.
     
     Copyright (c) 2013-2024 by Cisco Systems, Inc.
     All rights reserved.";

  revision 2024-02-09 {
    description
      "Added all interface support in oper yang model.";
    semver:module-version "1.0.0";
  }
  revision 2019-04-05 {
    description
      "Establish semantic version baseline.";
  }
  revision 2015-11-09 {
    description
      "IOS XR 6.0 revision.";
  }

  grouping OFA-PFC-PAUSE-DURATION-USAGE {
    description
      "Per time record  structure for a pause duration
       usage";
    leaf timestamp {
      type uint64;
      description
        "timestamp";
    }
    leaf tc {
      type uint8;
      description
        "tc";
    }
    leaf pause-percent {
      type string {
        length "0..20";
      }
      description
        "pause percent";
    }
    leaf ifhandle {
      type uint32;
      description
        "ifhandle";
    }
  }

  grouping OFA-PFC-PAUSE-DURATION-USAGE-ARRAY-ST {
    description
      "Resource level information";
    leaf entry-xr {
      type uint32;
      description
        "entry xr";
    }
    list entry {
      description
        "entry";
      uses OFA-PFC-PAUSE-DURATION-USAGE;
    }
  }
}
