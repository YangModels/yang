module Cisco-IOS-XR-controller-och-cfg {
  namespace "http://cisco.com/ns/yang/Cisco-IOS-XR-controller-och-cfg";
  prefix controller-och-cfg;

  import cisco-semver {
    prefix semver;
  }
  import Cisco-IOS-XR-ifmgr-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR controller-och package configuration.
     
     This YANG module augments the
       Cisco-IOS-XR-ifmgr-cfg
     module with configuration data.
     
     Copyright (c) 2013-2023 by Cisco Systems, Inc.
     All rights reserved.";

  revision 2023-09-01 {
    description
      "rx-threshold and tx-threshold config range enhanced";
    semver:module-version "1.0.0";
  }
  revision 2022-12-28 {
    description
      "och-tone-rate datatype is changed to signed int32";
  }
  revision 2022-08-26 {
    description
      "length 8..64 is added";
  }
  revision 2022-04-18 {
    description
      "Name of the enum ThresholdType is changed to OchThresholdType";
  }
  revision 2019-04-05 {
    description
      "Establish semantic version baseline.";
  }
  revision 2015-11-09 {
    description
      "IOS XR 6.0 revision.";
  }

  typedef Och-threshold {
    type enumeration {
      enum "low" {
        value 1;
        description
          "Low Threshold";
      }
      enum "high" {
        value 2;
        description
          "High Threshold";
      }
    }
    description
      "Och threshold";
  }

  augment "/a1:interface-configurations/a1:interface-configuration" {
    description
      "This augment extends the configuration data of
       'Cisco-IOS-XR-ifmgr-cfg'";
    container och {
      description
        "Och controller configuration";
      container rx-thresholds {
        description
          "Configure RX threshold";
        list rx-threshold {
          key "rx-threshold-type";
          description
            "Configure transponder receive power threshold";
          leaf rx-threshold-type {
            type Och-threshold;
            description
              "Low or high rx threshold";
          }
          leaf rx-threshold {
            type int32 {
              range "-500..300";
            }
            mandatory true;
            description
              "Select power level (in units of 0.1dBm)";
          }
        }
      }
      container tx-thresholds {
        description
          "Configure TX threshold";
        list tx-threshold {
          key "tx-threshold-type";
          description
            "Configure transponder transmit power threshold";
          leaf tx-threshold-type {
            type Och-threshold;
            description
              "Low or high tx threshold";
          }
          leaf tx-threshold {
            type int32 {
              range "-500..300";
            }
            mandatory true;
            description
              "Select power level (in units of 0.1dBm";
          }
        }
      }
      leaf och-tone-pattern-expected {
        type string {
          length "8..64";
        }
        description
          "Enter Hex Values(Min Length 8 Bytes to Max
           Length 64 Bytes)";
      }
      leaf och-tone-rate {
        type int32 {
          range "2..25";
        }
        description
          "Configure Tone Rate";
      }
      leaf och-tone-detect-oob {
        type empty;
        description
          "configure tone detect oob";
      }
    }
  }
}
