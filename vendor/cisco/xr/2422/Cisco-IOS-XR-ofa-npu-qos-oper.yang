module Cisco-IOS-XR-ofa-npu-qos-oper {
  namespace "http://cisco.com/ns/yang/Cisco-IOS-XR-ofa-npu-qos-oper";
  prefix ofa-npu-qos-oper;

  import Cisco-IOS-XR-types {
    prefix xr;
  }
  import cisco-semver {
    prefix semver;
  }
  include Cisco-IOS-XR-ofa-npu-qos-oper-sub1 {
    revision-date 2024-01-19;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ofa-npu-qos package operational data.
     
     This module contains definitions
     for the following management objects:
       npu-qos: NPU QOS data
     
     Copyright (c) 2013-2024 by Cisco Systems, Inc.
     All rights reserved.";

  revision 2024-01-19 {
    description
      "Add traffic class high water marks monitoring";
    semver:module-version "1.0.0";
  }
  revision 2022-10-10 {
    description
      "Create the initial npu-qos oper yang model.";
  }
  revision 2019-04-05 {
    description
      "Establish semantic version baseline.";
  }
  revision 2015-11-09 {
    description
      "IOS XR 6.0 revision.";
  }

  grouping INTERFACE-TABLE {
    description
      "Common node of monotonic, periodic";
    container interfaces {
      description
        "Per interface per traffic class high water marks
         grouped by interface";
      list interface {
        key "interface-name";
        description
          "Per traffic class high water marks for a
           specific interface, default is all interfaces";
        leaf interface-name {
          type xr:Interface-name;
          description
            "Interface Name, such as FourHundredGigE0/0/0/1";
        }
        uses OFA-QOS-HWM-INTF-INFO;
      }
    }
  }

  container npu-qos {
    config false;
    description
      "NPU QOS data";
    container nodes {
      description
        "NPU QOS data for available nodes";
      list node {
        key "node-name";
        description
          "NPU QOS operational data for a particular node";
        container high-water-marks {
          description
            "Per interface per traffic class high water
             marks";
          container periodic {
            description
              "Periodic per interface per traffic class high
               water marks";
            uses INTERFACE-TABLE;
          }
          container monotonic {
            description
              "Monotonically increasing (since clear) per
               interface per traffic class high water marks";
            uses INTERFACE-TABLE;
          }
        }
        container npu-numbers {
          description
            "Punt interface type";
          list npu-number {
            key "npu-id";
            description
              "QOS data for a particular NPU";
            container display {
              description
                "NPU specific QOS data";
              uses OFA-NPU-QOS-SHOW-ST;
            }
            leaf npu-id {
              type uint32;
              description
                "Npu number";
            }
          }
        }
        leaf node-name {
          type xr:Node-id;
          description
            "Node ID";
        }
      }
    }
  }
}
