module Cisco-IOS-XR-controller-oms-cfg {
  namespace "http://cisco.com/ns/yang/Cisco-IOS-XR-controller-oms-cfg";
  prefix controller-oms-cfg;

  import cisco-semver {
    prefix semver;
  }
  import Cisco-IOS-XR-ifmgr-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR controller-oms package configuration.
     
     This YANG module augments the
       Cisco-IOS-XR-ifmgr-cfg
     module with configuration data.
     
     Copyright (c) 2013-2023 by Cisco Systems, Inc.
     All rights reserved.";

  revision 2023-09-20 {
    description
      "oms-ingress-amplifier-gain, oms-egress-amplifier-gain leaf range enhanced";
    semver:module-version "1.0.0";
  }
  revision 2023-09-01 {
    description
      "rx-threshold and tx-threshold config range enhanced";
  }
  revision 2023-08-21 {
    description
      "Added support for Egress Amplifier Back Reflection status and Egress Amplifier Back Reflection high threshold";
  }
  revision 2023-06-02 {
    description
      "Added support for tx-voa-attenuation and rx-voa-attenuation";
  }
  revision 2023-06-02 {
    description
      "Added support for ingress-ampli-osri and egress-ampli-osri";
  }
  revision 2023-06-02 {
    description
      "Added support for EDFA parameters";
  }
  revision 2022-12-28 {
    description
      "oms-tone-rate datatype is changed to signed int32";
  }
  revision 2022-08-23 {
    description
      "length 8..64 is added";
  }
  revision 2022-03-21 {
    description
      "Name of the enum ThresholdType is changed to OmsThresholdType";
  }
  revision 2019-04-05 {
    description
      "Establish semantic version baseline.";
  }
  revision 2015-11-09 {
    description
      "IOS XR 6.0 revision.";
  }

  typedef Oms-ingress-egress-ampli-gain-range {
    type enumeration {
      enum "normal" {
        value 1;
        description
          "Normal Amplifier Gain Range";
      }
      enum "extended" {
        value 2;
        description
          "Extended Amplifier Gain Range";
      }
    }
    description
      "Oms ingress egress ampli gain range";
  }

  typedef Oms-ampli-working-mode {
    type enumeration {
      enum "power" {
        value 2;
        description
          "Power control mode";
      }
    }
    description
      "Oms ampli working mode";
  }

  typedef Oms-threshold {
    type enumeration {
      enum "low" {
        value 1;
        description
          "Low Threshold";
      }
      enum "high" {
        value 2;
        description
          "High Threshold";
      }
    }
    description
      "Oms threshold";
  }

  augment "/a1:interface-configurations/a1:interface-configuration" {
    description
      "This augment extends the configuration data of
       'Cisco-IOS-XR-ifmgr-cfg'";
    container oms {
      description
        "Oms controller configuration";
      container rx-thresholds {
        description
          "Configure RX threshold";
        list rx-threshold {
          key "rx-threshold-type";
          description
            "Configure transponder receive power threshold";
          leaf rx-threshold-type {
            type Oms-threshold;
            description
              "Low or high rx threshold";
          }
          leaf rx-threshold {
            type int32 {
              range "-500..300";
            }
            mandatory true;
            description
              "Select power level (in units of 0.1dBm)";
          }
        }
      }
      container tx-thresholds {
        description
          "Configure TX threshold";
        list tx-threshold {
          key "tx-threshold-type";
          description
            "Configure transponder transmit power threshold";
          leaf tx-threshold-type {
            type Oms-threshold;
            description
              "Low or high tx threshold";
          }
          leaf tx-threshold {
            type int32 {
              range "-500..300";
            }
            mandatory true;
            description
              "Select power level (in units of 0.1dBm";
          }
        }
      }
      leaf oms-tx-voa-attenuation {
        type int32 {
          range "0..200";
        }
        description
          "Select TX Voa Attenuation Setpoint(in units of
           0.1dBm)";
      }
      leaf oms-ingress-amplifier-gain {
        type int32 {
          range "-30..400";
        }
        description
          "Select Amplifier Gain value(in units of 0.1dBm)";
      }
      leaf oms-ingress-amplifier-power {
        type int32 {
          range "-90..250";
        }
        description
          "Select ingress amplifier power value (in units
           of 0.1dBm)";
      }
      leaf oms-egress-amplifier-power {
        type int32 {
          range "-30..250";
        }
        description
          "Select egress amplifier power value (in units
           of 0.1dBm)";
      }
      leaf oms-egress-amplifier-mode {
        type Oms-ampli-working-mode;
        description
          "Configure egress amplifier working mode";
      }
      leaf oms-egress-amplifier-back-reflection-high-threshold {
        type int32 {
          range "-500..300";
        }
        description
          "Configure egress amplifier back reflection high
           threshold to report alarm and trigger safety if
           it is crossed";
      }
      leaf oms-egress-amplifier-gain {
        type int32 {
          range "-30..400";
        }
        description
          "Select Amplifier Gain value(in units of 0.1dBm)";
      }
      leaf oms-tone-rate {
        type int32 {
          range "2..25";
        }
        description
          "Configure Tone Rate";
      }
      leaf oms-ingress-osri {
        type empty;
        description
          "Configure Ingress Optical safety remote
           interlock (OSRI)";
      }
      leaf oms-rx-voa-attenuation {
        type int32 {
          range "0..200";
        }
        description
          "Select RX Voa Attenuation Setpoint(in units of
           0.1dBm)";
      }
      leaf oms-egress-osri {
        type empty;
        description
          "Configure Egress Optical safety remote
           interlock (OSRI)";
      }
      leaf oms-egress-amplifier-back-reflection {
        type empty;
        description
          "Enable egress amplifier back reflection to
           trigger safety in case egress amplifier back
           reflection high threshold is crossed";
      }
      leaf oms-egress-amplifier-gain-range {
        type Oms-ingress-egress-ampli-gain-range;
        description
          "Configure EGRESS AMPLIFIER GAIN Range";
      }
      leaf oms-tone-pattern-expected {
        type string {
          length "8..64";
        }
        description
          "Enter Hex Values(Min Length 8 Bytes to Max
           Length 64 Bytes)";
      }
      leaf oms-tone-detect-oob {
        type empty;
        description
          "configure tone detect oob";
      }
      leaf oms-ingress-amplifier-mode {
        type Oms-ampli-working-mode;
        description
          "Configure ingress amplifier working mode";
      }
    }
  }
}
