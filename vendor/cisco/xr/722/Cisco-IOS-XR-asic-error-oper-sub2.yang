submodule Cisco-IOS-XR-asic-error-oper-sub2 {
  belongs-to Cisco-IOS-XR-asic-error-oper {
    prefix Cisco-IOS-XR-asic-error-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR asic-error package operational data.
     
     Copyright (c) 2013-2019 by Cisco Systems, Inc.
     All rights reserved.";

  revision 2019-09-27 {
    description
      "Introduced working oper model for asic-errors.";
    semver:module-version "1.0.0";
  }
  revision 2019-09-24 {
    description
      "Introduced working oper model for asic-errors.";
    semver:module-version "1.0.0";
  }
  revision 2019-04-05 {
    description
      "Establish semantic version baseline.";
  }
  revision 2015-11-09 {
    description
      "IOS XR 6.0 revision.";
  }

  grouping PCIE-TLP-HEADER-DATA-BG {
    description
      "PCIE TLP HEADER DATA BG";
    leaf fmt-type {
      type uint32;
      description
        "fmt type";
    }
    leaf traffic-class {
      type uint32;
      description
        "traffic class";
    }
    leaf tlp-digest-field-present {
      type boolean;
      description
        "tlp digest field present";
    }
    leaf poisoned-data {
      type boolean;
      description
        "poisoned data";
    }
    leaf relaxed-ordering {
      type boolean;
      description
        "relaxed ordering";
    }
    leaf no-snoop {
      type boolean;
      description
        "no snoop";
    }
    leaf length {
      type uint16;
      description
        "length";
    }
    leaf first-dw-byte-enables {
      type uint8;
      description
        "first dw byte enables";
    }
    leaf last-dw-byte-enables {
      type uint8;
      description
        "last dw byte enables";
    }
    leaf-list transaction-descriptor {
      type uint8;
      description
        "transaction descriptor";
    }
  }

  grouping PCIE-ASIC-ERRORS-DATA-BG {
    description
      "PCIE ASIC ERRORS DATA BG";
    container tlp-header-data {
      description
        "tlp header data";
      uses PCIE-TLP-HEADER-DATA-BG;
    }
    leaf err-type {
      type uint32;
      description
        "err type";
    }
    leaf severity {
      type uint32;
      description
        "severity";
    }
    leaf err-attribute {
      type uint32;
      description
        "err attribute";
    }
    leaf is-tlp-header-present {
      type boolean;
      description
        "is tlp header present";
    }
    leaf-list raw-tlp-header {
      type uint32;
      description
        "raw tlp header";
    }
  }

  grouping PCIE-DATA-BG {
    description
      "PCIE DATA BG";
    container error-data {
      description
        "error data";
      uses PCIE-ASIC-ERRORS-DATA-BG;
    }
    leaf at-time {
      type uint64;
      description
        "at time";
    }
    leaf at-time-nsec {
      type uint64;
      description
        "at time nsec";
    }
    leaf counter-val {
      type uint32;
      description
        "counter val";
    }
    leaf top-ec {
      type uint32;
      description
        "top ec";
    }
    leaf block-ec {
      type uint32;
      description
        "block ec";
    }
  }

  grouping PCIE-NODE-BG {
    description
      "PCIE NODE BG";
    leaf name {
      type string;
      description
        "Name assigned to mem";
    }
    leaf node-key {
      type uint32;
      description
        "32 bit key";
    }
    leaf alarm-on {
      type boolean;
      description
        "High threshold crossed";
    }
    leaf thresh-hi {
      type uint32;
      description
        "High threshold value";
    }
    leaf period-hi {
      type uint32;
      description
        "High period value";
    }
    leaf count {
      type uint32;
      description
        "Accumulated count";
    }
    leaf last-cleared {
      type uint64;
      description
        "Time  cleared";
    }
    list last-err {
      description
        "Collection of last errs";
      uses PCIE-DATA-BG;
    }
  }

  grouping PCIE-NODES-BG {
    description
      "PCIE NODES BG";
    list error {
      description
        "Collection of errors";
      uses PCIE-NODE-BG;
    }
  }

  grouping CIHERR-ERROR-DATA-BG {
    description
      "CIHERR ERROR DATA BG";
    leaf at-time {
      type uint64;
      description
        "Asic error time";
    }
    leaf at-time-nsec {
      type uint64;
      description
        "Asic error nsec";
    }
    leaf counter-val {
      type uint32;
      description
        "Number of occurrence";
    }
    leaf error-desc {
      type string;
      description
        "Error description";
    }
    list error-regval {
      description
        "Error register value";
      leaf entry {
        type uint8;
        description
          "Error register value";
      }
    }
  }

  grouping CSRS-INFO-BG {
    description
      "CSRS INFO BG";
    leaf name {
      type string;
      description
        "Name of csrs register";
    }
    leaf address {
      type uint64;
      description
        "Address of csrs register";
    }
    leaf width {
      type uint32;
      description
        "Width of csrs register";
    }
  }

  grouping CIHERR-NODE-BG {
    description
      "CIHERR NODE BG";
    leaf name {
      type string;
      description
        "Name assigned to mem";
    }
    leaf asic-info {
      type string;
      description
        "Name of rack/board/asic";
    }
    leaf node-key {
      type uint32;
      description
        "32 bit key";
    }
    leaf alarm-on {
      type boolean;
      description
        "High threshold crossed";
    }
    leaf thresh-hi {
      type uint32;
      description
        "High threshold value";
    }
    leaf period-hi {
      type uint32;
      description
        "High period value";
    }
    leaf thresh-lo {
      type uint32;
      description
        "High threshold value";
    }
    leaf period-lo {
      type uint32;
      description
        "High period value";
    }
    leaf count {
      type uint32;
      description
        "Accumulated count";
    }
    leaf intr-type {
      type uint32;
      description
        "Type of error";
    }
    leaf leaf-id {
      type uint32;
      description
        "Leaf ID defined in user data";
    }
    leaf last-cleared {
      type uint64;
      description
        "Time  cleared";
    }
    list csrs-info {
      description
        "List of csrs_info";
      uses CSRS-INFO-BG;
    }
    list last-err {
      description
        "Last Printable error information";
      uses CIHERR-ERROR-DATA-BG;
    }
  }

  grouping CIHERR-NODES-BG {
    description
      "CIHERR NODES BG";
    list error {
      description
        "Collection of errors";
      uses CIHERR-NODE-BG;
    }
  }

  grouping PACERR-ERROR-DATA-BG {
    description
      "PACERR ERROR DATA BG";
    leaf at-time {
      type uint64;
      description
        "at time";
    }
    leaf at-time-nsec {
      type uint64;
      description
        "at time nsec";
    }
    leaf counter-val {
      type uint32;
      description
        "counter val";
    }
    leaf error-desc {
      type string;
      description
        "error desc";
    }
  }

  grouping PACERR-NODE-BG {
    description
      "PACERR NODE BG";
    leaf name {
      type string;
      description
        "Name assigned to mem";
    }
    leaf asic-info {
      type string;
      description
        "Name of rack/board/asic";
    }
    leaf node-key {
      type uint32;
      description
        "32 bit key";
    }
    leaf alarm-on {
      type boolean;
      description
        "High threshold crossed";
    }
    leaf thresh-hi {
      type uint32;
      description
        "High threshold value";
    }
    leaf period-hi {
      type uint32;
      description
        "High period value";
    }
    leaf thresh-lo {
      type uint32;
      description
        "Low threshold value";
    }
    leaf period-lo {
      type uint32;
      description
        "Low period value";
    }
    leaf count {
      type uint32;
      description
        "Accumulated count";
    }
    leaf block-id {
      type uint32;
      description
        "block where error occurred";
    }
    leaf addr {
      type uint32;
      description
        "addr of the error interrupt inside node";
    }
    leaf leaf-id {
      type uint32;
      description
        "leaf_id of the error occurred";
    }
    leaf intr-type {
      type uint32;
      description
        "Type of error";
    }
    leaf last-cleared {
      type uint64;
      description
        "Time  cleared";
    }
    list last-err {
      description
        "Last Printable error information";
      uses PACERR-ERROR-DATA-BG;
    }
  }

  grouping PACERR-NODES-BG {
    description
      "PACERR NODES BG";
    list error {
      description
        "Collection of errors";
      uses PACERR-NODE-BG;
    }
  }

  grouping SCHEMA-DATA-BG {
    description
      "SCHEMA DATA BG";
    container pacerr-nodes {
      description
        "pacerr nodes";
      uses PACERR-NODES-BG;
    }
    container ciherr-nodes {
      description
        "ciherr nodes";
      uses CIHERR-NODES-BG;
    }
    container pcie-nodes {
      description
        "pcie nodes";
      uses PCIE-NODES-BG;
    }
  }
}
