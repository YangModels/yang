submodule Cisco-IOS-XR-ipv6-ping-act {
  belongs-to Cisco-IOS-XR-ping-act {
    prefix ping-act;
  }

  import cisco-semver {
    prefix semver;
  }
  import ietf-inet-types {
    prefix inet;
  }
  include Cisco-IOS-XR-ipv4-ping-act;

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR IPv6 ping action package configuration.
     
     Copyright (c) 2016-2019 by Cisco Systems, Inc.
     All rights reserved.";

  revision 2019-10-01 {
    description
      "Made changes to be RFC6087 compliant";
    semver:module-version "1.1.0";
  }
  revision 2019-04-05 {
    description
      "Establish semantic version baseline.";
    semver:module-version "1.0.0";
  }
  revision 2018-11-28 {
    description
      "IOS XR 7.0.1 revision.";
  }
  revision 2016-09-13 {
    description
      "IOS XR 6.2.1 revision.";
  }

  grouping IPV6-SPECIFIC-OPTIONS {
    description
      "IPv6 specific options";
    leaf priority {
      type uint8 {
        range "0..15";
      }
      description
        "Priority of the packet";
    }
    leaf outgoing-interface {
      type string;
      description
        "Outgoing interface, needed in case of ping to link local address";
    }
    container flowlabel {
      description
        "Flowlabel value or flowlabel random,
         if both are given then flowabel value is chosen.";
      leaf value {
        type uint32 {
          range "0..1048575";
        }
        description
          "Flowlabel of the packet";
      }
      leaf random {
        type empty;
        description
          "Random flowlabel value of the packet,
           repeats after every 5 packets";
      }
    }
    container use-srv6-end-op-sid {
      presence "enable srv6 END.OP operations";
      description
        "Use End.OP SID in Segment Routing Header";
      leaf user-end-op-sid {
        type inet:ipv6-address;
        description
          "IPv6 End.OP address";
      }
    }
  }

  grouping IPV6-PING-INPUT {
    description
      "IPv6 ping input";
    uses PING-OPTIONS;
    uses IPV6-SPECIFIC-OPTIONS;
  }

  grouping IPV6-PING-OUTPUT {
    description
      "IPv6 ping output";
    uses PING-COMMON-INPUT-OUTPUT-OPTIONS;
    leaf sweep-min {
      type uint32;
      description
        "Minimum value of sweep size";
    }
    leaf sweep-max {
      type uint64;
      description
        "Maximum value of sweep size";
    }
    leaf rotate-pattern {
      type boolean;
      description
        "Rotate Pattern is enabled";
    }
    container replies {
      description
        "IPv6 ping replies";
      list reply {
        key "reply-index";
        description
          "IPv6 ping reply";
        leaf reply-index {
          type uint64 {
            range "1..2147483647";
          }
          description
            "Index of the reply list";
        }
        leaf result {
          type string;
          description
            "Response for each packet";
        }
      }
    }
    leaf hits {
      type uint64;
      description
        "Number of packets reach to destination and get reply back";
    }
    leaf total {
      type uint64;
      description
        "Total number of packets sent out";
    }
    leaf success-rate {
      type uint64;
      description
        "Successful rate of ping";
    }
    leaf rtt-min {
      type uint64;
      description
        "Minimum value of Round Trip Time";
    }
    leaf rtt-avg {
      type uint64;
      description
        "Average value of Round Trip Time";
    }
    leaf rtt-max {
      type uint64;
      description
        "Maximum value of Round Trip Time";
    }
  }
}
