module Cisco-IOS-XR-platforms-ofa-table-stats-oper {
  namespace "http://cisco.com/ns/yang/Cisco-IOS-XR-platforms-ofa-table-stats-oper";
  prefix platforms-ofa-table-stats-oper;

  import Cisco-IOS-XR-types {
    prefix xr;
  }
  import cisco-semver {
    prefix semver;
  }
  include Cisco-IOS-XR-platforms-ofa-table-stats-oper-sub1 {
    revision-date 2020-06-25;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR platforms-ofa-table-stats package operational data.
     
     This module contains definitions
     for the following management objects:
       ofa: OFA Data
     
     Copyright (c) 2013-2020 by Cisco Systems, Inc.
     All rights reserved.";

  revision 2020-06-25 {
    description
      "Updated task-name";
    semver:module-version "2.0.0";
  }
  revision 2019-12-14 {
    description
      "Added the Yang Model for ofa sw resources";
    semver:module-version "1.1.0";
  }
  revision 2019-06-06 {
    description
      "Added the Yang Model for ofa sw resources";
    semver:module-version "1.0.0";
  }
  revision 2019-04-05 {
    description
      "Establish semantic version baseline.";
  }
  revision 2015-11-09 {
    description
      "IOS XR 6.0 revision.";
  }

  typedef Ofa-table {
    type enumeration {
      enum "test-if" {
        value 0;
        description
          "test if";
      }
      enum "test-if-with-create-reject" {
        value 1;
        description
          "testifwithcreatereject";
      }
      enum "test-nh" {
        value 2;
        description
          "test nh";
      }
      enum "test-global-discard" {
        value 3;
        description
          "testglobaldiscard";
      }
      enum "test-nhg" {
        value 4;
        description
          "test nhg";
      }
      enum "test-rt" {
        value 5;
        description
          "test rt";
      }
      enum "test-dynhg" {
        value 6;
        description
          "testdynhg";
      }
      enum "test-async-nhg" {
        value 7;
        description
          "testasyncnhg";
      }
      enum "test-async-nhgstats" {
        value 8;
        description
          "testasyncnhgstats";
      }
      enum "test-ip-punt-policy" {
        value 9;
        description
          "test ippuntpolicy";
      }
      enum "test-punt" {
        value 10;
        description
          "test punt";
      }
      enum "test-punt-policy-stats" {
        value 11;
        description
          "testpuntpolicystats";
      }
      enum "test-async-update" {
        value 12;
        description
          "testasyncupdate";
      }
      enum "test-async-barrier-with-knob" {
        value 13;
        description
          "testasyncbarrierwithknob";
      }
      enum "test-async-barrier-with-outknob" {
        value 14;
        description
          "testasyncbarrierwithoutknob";
      }
      enum "test-o-fast-ats" {
        value 15;
        description
          "testofastats";
      }
      enum "test-o-fast-ats1" {
        value 16;
        description
          "testofastats1";
      }
      enum "test-o-fast-ats2" {
        value 17;
        description
          "testofastats2";
      }
      enum "test-dpastats1" {
        value 18;
        description
          "testdpastats1";
      }
      enum "test-dpastats2" {
        value 19;
        description
          "testdpastats2";
      }
      enum "test-srvgrid" {
        value 20;
        description
          "testsrvgrid";
      }
      enum "test-ddel-q" {
        value 21;
        description
          "test ddel q";
      }
      enum "test-mco-list" {
        value 22;
        description
          "testmcolist";
      }
      enum "test-syncmco-list" {
        value 23;
        description
          "testsyncmcolist";
      }
      enum "test-syncmctblstats" {
        value 24;
        description
          "testsyncmctblstats";
      }
      enum "test-dddp" {
        value 25;
        description
          "testdddp";
      }
      enum "test-grid1" {
        value 26;
        description
          "testgrid1";
      }
      enum "sys" {
        value 27;
        description
          "sys";
      }
      enum "npu" {
        value 28;
        description
          "npu";
      }
      enum "npuhwid" {
        value 29;
        description
          "npuhwid";
      }
      enum "optics-port" {
        value 30;
        description
          "opticsport";
      }
      enum "gi-port" {
        value 31;
        description
          "giport";
      }
      enum "l1-port" {
        value 32;
        description
          "l1port";
      }
      enum "mac-port" {
        value 33;
        description
          "macport";
      }
      enum "l2-port" {
        value 34;
        description
          "l2port";
      }
      enum "eth-port" {
        value 35;
        description
          "ethport";
      }
      enum "l2intf" {
        value 36;
        description
          "l2intf";
      }
      enum "l2if" {
        value 37;
        description
          "l2if";
      }
      enum "mplspwe-port" {
        value 38;
        description
          "mplspweport";
      }
      enum "mplspwe-port-o-list" {
        value 39;
        description
          "mplspweport olist";
      }
      enum "mhpwe-port" {
        value 40;
        description
          "mhpweport";
      }
      enum "l2xc" {
        value 41;
        description
          "l2xc";
      }
      enum "l2vpnstats" {
        value 42;
        description
          "l2vpnstats";
      }
      enum "l1-ports-tats" {
        value 43;
        description
          "l1portstats";
      }
      enum "mac-ports-tats" {
        value 44;
        description
          "macportstats";
      }
      enum "l3intf" {
        value 45;
        description
          "l3intf";
      }
      enum "l3if" {
        value 46;
        description
          "l3if";
      }
      enum "l3intfrxstats" {
        value 47;
        description
          "l3intfrxstats";
      }
      enum "ip-route" {
        value 48;
        description
          "iproute";
      }
      enum "ip6-route" {
        value 49;
        description
          "ip6route";
      }
      enum "punt-policy-stats" {
        value 50;
        description
          "puntpolicystats";
      }
      enum "tep" {
        value 51;
        description
          "tep";
      }
      enum "ip-punt-policy" {
        value 52;
        description
          "ippuntpolicy";
      }
      enum "ip6-punt-policy" {
        value 53;
        description
          "ip6puntpolicy";
      }
      enum "isis-punt-policy" {
        value 54;
        description
          "isispuntpolicy";
      }
      enum "nh-group" {
        value 55;
        description
          "nhgroup";
      }
      enum "ipnh-group" {
        value 56;
        description
          "ipnhgroup";
      }
      enum "ip6nh-group" {
        value 57;
        description
          "ip6nhgroup";
      }
      enum "ipnh" {
        value 58;
        description
          "ipnh";
      }
      enum "ip6nh" {
        value 59;
        description
          "ip6nh";
      }
      enum "ipvrf" {
        value 60;
        description
          "ipvrf";
      }
      enum "mplsnh" {
        value 61;
        description
          "mplsnh";
      }
      enum "lspnh" {
        value 62;
        description
          "lspnh";
      }
      enum "mpls-label" {
        value 63;
        description
          "mplslabel";
      }
      enum "punt" {
        value 64;
        description
          "punt";
      }
      enum "punt-police-r" {
        value 65;
        description
          "puntpolicer";
      }
      enum "punt-lpts-police-r" {
        value 66;
        description
          "puntlptspolicer";
      }
      enum "punt-stats" {
        value 67;
        description
          "puntstats";
      }
      enum "tm-port" {
        value 68;
        description
          "tmport";
      }
      enum "span-session" {
        value 69;
        description
          "spansession";
      }
      enum "police-rstats" {
        value 70;
        description
          "policerstats";
      }
      enum "tm-ports-tats" {
        value 71;
        description
          "tmportstats";
      }
      enum "l3intftxstats" {
        value 72;
        description
          "l3intftxstats";
      }
      enum "mplstetxstats" {
        value 73;
        description
          "mplstetxstats";
      }
      enum "mplslblstats" {
        value 74;
        description
          "mplslblstats";
      }
      enum "police-r" {
        value 75;
        description
          "policer";
      }
      enum "l2intfrxstats" {
        value 76;
        description
          "l2intfrxstats";
      }
      enum "l2intftxstats" {
        value 77;
        description
          "l2intftxstats";
      }
      enum "pbr-tt-ipv4" {
        value 78;
        description
          "pbr tt ipv4";
      }
      enum "pbr-tt-ipv6" {
        value 79;
        description
          "pbr tt ipv6";
      }
      enum "bfdhwoff" {
        value 80;
        description
          "bfdhwoff";
      }
      enum "bfdoff" {
        value 81;
        description
          "bfdoff";
      }
      enum "bfdoffstats" {
        value 82;
        description
          "bfdoffstats";
      }
      enum "global" {
        value 83;
        description
          "global";
      }
      enum "lag-port" {
        value 84;
        description
          "lagport";
      }
      enum "agg-port" {
        value 85;
        description
          "aggport";
      }
      enum "agg-member" {
        value 86;
        description
          "aggmember";
      }
      enum "qos-profile" {
        value 87;
        description
          "qosprofile";
      }
      enum "acl-profile" {
        value 88;
        description
          "acl profile";
      }
      enum "tmrate-profile" {
        value 89;
        description
          "tmrateprofile";
      }
      enum "ipacl" {
        value 90;
        description
          "ipacl";
      }
      enum "ip6acl" {
        value 91;
        description
          "ip6acl";
      }
      enum "sched-tree" {
        value 92;
        description
          "schedtree";
      }
      enum "tmcos" {
        value 93;
        description
          "tmcos";
      }
      enum "statsagg" {
        value 94;
        description
          "statsagg";
      }
      enum "nhprotect" {
        value 95;
        description
          "nhprotect";
      }
      enum "sampler" {
        value 96;
        description
          "sampler";
      }
      enum "l2qos" {
        value 97;
        description
          "l2qos";
      }
      enum "peer-qos" {
        value 98;
        description
          "peerqos";
      }
      enum "ipqos" {
        value 99;
        description
          "ipqos";
      }
      enum "ip6qos" {
        value 100;
        description
          "ip6qos";
      }
      enum "mplsqos" {
        value 101;
        description
          "mplsqos";
      }
      enum "qos-group" {
        value 102;
        description
          "qosgroup";
      }
      enum "qosid" {
        value 103;
        description
          "qosid";
      }
      enum "extlif" {
        value 104;
        description
          "extlif";
      }
      enum "elif" {
        value 105;
        description
          "elif";
      }
      enum "ingaclstats" {
        value 106;
        description
          "ingaclstats";
      }
      enum "egraclstats" {
        value 107;
        description
          "egraclstats";
      }
      enum "edpl" {
        value 108;
        description
          "edpl";
      }
      enum "l2protect" {
        value 109;
        description
          "l2protect";
      }
      enum "sat" {
        value 110;
        description
          "sat";
      }
      enum "satstats" {
        value 111;
        description
          "satstats";
      }
      enum "cfmoam-profile-def" {
        value 112;
        description
          "cfmoamprofiledef";
      }
      enum "cfmmaid" {
        value 113;
        description
          "cfmmaid";
      }
      enum "cfmdefmps" {
        value 114;
        description
          "cfmdefmps";
      }
      enum "cfmofflmep" {
        value 115;
        description
          "cfmofflmep";
      }
      enum "cfmoffrmep" {
        value 116;
        description
          "cfmoffrmep";
      }
      enum "cfmnonoff" {
        value 117;
        description
          "cfmnonoff";
      }
      enum "cfmhwoffrxstats" {
        value 118;
        description
          "cfmhwoffrxstats";
      }
      enum "ipmc-route" {
        value 119;
        description
          "ipmcroute";
      }
      enum "l2ipmc-route" {
        value 120;
        description
          "l2ipmcroute";
      }
      enum "ipmco-list" {
        value 121;
        description
          "ipmcolist";
      }
      enum "l2mco-list" {
        value 122;
        description
          "l2mcolist";
      }
      enum "meshmc" {
        value 123;
        description
          "meshmc";
      }
      enum "l2-bridge" {
        value 124;
        description
          "l2bridge";
      }
      enum "l2-bridge-port" {
        value 125;
        description
          "l2bridgeport";
      }
      enum "l2-bridge-vni" {
        value 126;
        description
          "l2bridgevni";
      }
      enum "l2-bridge-vnidecap" {
        value 127;
        description
          "l2bridgevnidecap";
      }
      enum "l2-bridge-mac" {
        value 128;
        description
          "l2bridgemac";
      }
      enum "l2brmac" {
        value 129;
        description
          "l2brmac";
      }
      enum "ip-tunnel-decap" {
        value 130;
        description
          "iptunneldecap";
      }
      enum "l2vlan-range" {
        value 131;
        description
          "l2vlanrange";
      }
      enum "ip-tunnel-encap" {
        value 132;
        description
          "iptunnelencap";
      }
      enum "iptnlnh" {
        value 133;
        description
          "iptnlnh";
      }
      enum "iptnl-encap" {
        value 134;
        description
          "iptnlencap";
      }
      enum "iptnldecap" {
        value 135;
        description
          "iptnldecap";
      }
      enum "rawget" {
        value 136;
        description
          "rawget";
      }
      enum "ip6mc-route" {
        value 137;
        description
          "ip6mcroute";
      }
      enum "ip6mc-comp-grp" {
        value 138;
        description
          "ip6mc comp grp";
      }
      enum "l2evpnact-remote-peer-id" {
        value 139;
        description
          "l2evpnactremotepeerid";
      }
      enum "l2evpnact-local-shl" {
        value 140;
        description
          "l2evpnactlocalshl";
      }
      enum "l2evpnact-remote-shl" {
        value 141;
        description
          "l2evpnactremoteshl";
      }
      enum "evpn-iml-range" {
        value 142;
        description
          "evpn imlrange";
      }
      enum "l2-bridge-o-list" {
        value 143;
        description
          "l2bridgeolist";
      }
      enum "l2-bridge-vnio-list" {
        value 144;
        description
          "l2bridgevniolist";
      }
      enum "l2acl" {
        value 145;
        description
          "l2acl";
      }
      enum "l2evpn-nh" {
        value 146;
        description
          "l2evpn nh";
      }
      enum "l2-bridge-port-sc" {
        value 147;
        description
          "l2bridgeport sc";
      }
      enum "l3intfmctxstats" {
        value 148;
        description
          "l3intfmctxstats";
      }
      enum "tidl-sample" {
        value 149;
        description
          "tidl sample";
      }
      enum "tidl-ref-sample" {
        value 150;
        description
          "tidl ref sample";
      }
      enum "ipacl-prefix" {
        value 151;
        description
          "ipaclprefix";
      }
      enum "ip6acl-prefix" {
        value 152;
        description
          "ip6aclprefix";
      }
      enum "ipacl-port" {
        value 153;
        description
          "ipaclport";
      }
      enum "scaleacl" {
        value 154;
        description
          "scaleacl";
      }
      enum "ipmcf-hop" {
        value 155;
        description
          "ipmcfhop";
      }
      enum "bundle-swoff" {
        value 156;
        description
          "bundle swoff";
      }
      enum "mcidswoff" {
        value 157;
        description
          "mcidswoff";
      }
      enum "dest-map" {
        value 158;
        description
          "destmap";
      }
      enum "l2-bridge-port-pw" {
        value 159;
        description
          "l2bridgeport pw";
      }
      enum "l2evpnact-local-shlstats" {
        value 160;
        description
          "l2evpnactlocalshlstats";
      }
      enum "test-hidden" {
        value 161;
        description
          "testhidden";
      }
      enum "test-local" {
        value 162;
        description
          "testlocal";
      }
      enum "test-repeated" {
        value 163;
        description
          "testrepeated";
      }
      enum "limd" {
        value 164;
        description
          "limd";
      }
      enum "litap" {
        value 165;
        description
          "litap";
      }
      enum "l3ifstats" {
        value 166;
        description
          "l3ifstats";
      }
      enum "mplsstats" {
        value 167;
        description
          "mplsstats";
      }
      enum "exception-nh" {
        value 168;
        description
          "exceptionnh";
      }
      enum "srv6sid" {
        value 169;
        description
          "srv6sid";
      }
      enum "srv6nh" {
        value 170;
        description
          "srv6nh";
      }
      enum "sr6sid" {
        value 171;
        description
          "sr6sid";
      }
      enum "sr6nh" {
        value 172;
        description
          "sr6nh";
      }
      enum "redirect-vrf" {
        value 173;
        description
          "redirectvrf";
      }
      enum "test-xtf" {
        value 174;
        description
          "test xtf";
      }
      enum "ippbr" {
        value 175;
        description
          "ippbr";
      }
      enum "ippbrstats" {
        value 176;
        description
          "ippbrstats";
      }
      enum "mpls-mdt-bud" {
        value 177;
        description
          "mplsmdtbud";
      }
      enum "mpls-label-rxstats" {
        value 178;
        description
          "mplslabelrxstats";
      }
      enum "l2mac-static" {
        value 179;
        description
          "l2macstatic";
      }
      enum "dot1x" {
        value 180;
        description
          "dot1x";
      }
      enum "iprte" {
        value 181;
        description
          "iprte";
      }
      enum "ip6rte" {
        value 182;
        description
          "ip6rte";
      }
      enum "llnh" {
        value 183;
        description
          "llnh";
      }
      enum "urpfintf" {
        value 184;
        description
          "urpfintf";
      }
      enum "ipmcrxstats" {
        value 185;
        description
          "ipmcrxstats";
      }
      enum "mplsrte" {
        value 186;
        description
          "mplsrte";
      }
      enum "protectnh" {
        value 187;
        description
          "protectnh";
      }
      enum "ipllnh" {
        value 188;
        description
          "ipllnh";
      }
      enum "ip6llnh" {
        value 189;
        description
          "ip6llnh";
      }
      enum "macnh" {
        value 190;
        description
          "macnh";
      }
      enum "qos-match-stats" {
        value 191;
        description
          "qosmatchstats";
      }
      enum "ofal2xc" {
        value 192;
        description
          "ofal2xc";
      }
      enum "ofamplspwe-port" {
        value 193;
        description
          "ofamplspweport";
      }
      enum "pwenh" {
        value 194;
        description
          "pwenh";
      }
      enum "pwenh-group" {
        value 195;
        description
          "pwenhgroup";
      }
      enum "ipmcrte" {
        value 196;
        description
          "ipmcrte";
      }
      enum "ip6mcrte" {
        value 197;
        description
          "ip6mcrte";
      }
      enum "ipmcr-test-ats" {
        value 198;
        description
          "ipmcrtestats";
      }
      enum "ip6mcr-test-ats" {
        value 199;
        description
          "ip6mcrtestats";
      }
      enum "transport-nh" {
        value 200;
        description
          "transportnh";
      }
      enum "port-range" {
        value 201;
        description
          "portrange";
      }
      enum "bvi-port" {
        value 202;
        description
          "bviport";
      }
      enum "mcid" {
        value 203;
        description
          "mcid";
      }
      enum "mc-gid" {
        value 204;
        description
          "mc gid";
      }
      enum "mco-list" {
        value 205;
        description
          "mcolist";
      }
      enum "test-da" {
        value 206;
        description
          "testda";
      }
      enum "test-ca" {
        value 207;
        description
          "testca";
      }
      enum "test-ba" {
        value 208;
        description
          "testba";
      }
      enum "test-aa" {
        value 209;
        description
          "testaa";
      }
      enum "test-async-aa" {
        value 210;
        description
          "testasyncaa";
      }
      enum "test-reliable-notif" {
        value 211;
        description
          "testreliablenotif";
      }
      enum "test-de" {
        value 212;
        description
          "testde";
      }
      enum "test-ce" {
        value 213;
        description
          "testce";
      }
      enum "test-be" {
        value 214;
        description
          "testbe";
      }
      enum "test-db" {
        value 215;
        description
          "testdb";
      }
      enum "test-cb" {
        value 216;
        description
          "testcb";
      }
      enum "test-bb" {
        value 217;
        description
          "testbb";
      }
      enum "test-df" {
        value 218;
        description
          "testdf";
      }
      enum "test-cf" {
        value 219;
        description
          "testcf";
      }
      enum "test-bf" {
        value 220;
        description
          "testbf";
      }
      enum "test-af" {
        value 221;
        description
          "testaf";
      }
      enum "test-ax" {
        value 222;
        description
          "testax";
      }
      enum "test-ay" {
        value 223;
        description
          "testay";
      }
      enum "test-ef" {
        value 224;
        description
          "testef";
      }
      enum "test-ff" {
        value 225;
        description
          "testff";
      }
      enum "test-gf" {
        value 226;
        description
          "testgf";
      }
      enum "test-eastwestscheduling" {
        value 227;
        description
          "testeastwestscheduling";
      }
      enum "test-transnh" {
        value 228;
        description
          "testtransnh";
      }
      enum "test-eth-port" {
        value 229;
        description
          "testethport";
      }
      enum "test-eastwest" {
        value 230;
        description
          "testeastwest";
      }
      enum "test-ifstats" {
        value 231;
        description
          "testifstats";
      }
      enum "test-async-oor" {
        value 232;
        description
          "testasyncoor";
      }
      enum "test-syncmcas-too-r" {
        value 233;
        description
          "testsyncmcastoor";
      }
      enum "test-syncdeviceoor" {
        value 234;
        description
          "testsyncdeviceoor";
      }
      enum "police-r-group" {
        value 235;
        description
          "policergroup";
      }
      enum "meter-profile" {
        value 236;
        description
          "meterprofile";
      }
      enum "acl-mirror" {
        value 237;
        description
          "acl mirror";
      }
      enum "meter-action-profile" {
        value 238;
        description
          "meteractionprofile";
      }
      enum "voqrm" {
        value 239;
        description
          "voqrm";
      }
      enum "port-wfq-profile" {
        value 240;
        description
          "portwfqprofile";
      }
      enum "rpfif" {
        value 241;
        description
          "rpfif";
      }
      enum "brmac" {
        value 242;
        description
          "brmac";
      }
      enum "br-static-mac" {
        value 243;
        description
          "brstaticmac";
      }
      enum "xconnect" {
        value 244;
        description
          "xconnect";
      }
      enum "bridge" {
        value 245;
        description
          "bridge";
      }
      enum "pwe-port" {
        value 246;
        description
          "pweport";
      }
      enum "olist" {
        value 247;
        description
          "olist";
      }
      enum "lsmprotect" {
        value 248;
        description
          "lsmprotect";
      }
      enum "monitor-session" {
        value 249;
        description
          "monitorsession";
      }
      enum "monitor-session-stats" {
        value 250;
        description
          "monitorsessionstats";
      }
      enum "mplsmcast" {
        value 251;
        description
          "mplsmcast";
      }
      enum "l2ifstats" {
        value 252;
        description
          "l2ifstats";
      }
      enum "imlnh" {
        value 253;
        description
          "imlnh";
      }
      enum "evinh" {
        value 254;
        description
          "evinh";
      }
      enum "member-list" {
        value 255;
        description
          "memberlist";
      }
      enum "test-oor" {
        value 256;
        description
          "testoor";
      }
      enum "hwre-source-s-oor" {
        value 257;
        description
          "hwresources oor";
      }
      enum "qospfcstats" {
        value 258;
        description
          "qospfcstats";
      }
      enum "pfctc" {
        value 259;
        description
          "pfctc";
      }
      enum "pfc-watchdog" {
        value 260;
        description
          "pfc watchdog";
      }
      enum "qos-shared" {
        value 261;
        description
          "qosshared";
      }
      enum "tm-remote-credit" {
        value 262;
        description
          "tmremotecredit";
      }
      enum "ipmcole" {
        value 263;
        description
          "ipmcole";
      }
      enum "ip6mcole" {
        value 264;
        description
          "ip6mcole";
      }
      enum "pbr" {
        value 265;
        description
          "pbr";
      }
      enum "pbrstats" {
        value 266;
        description
          "pbrstats";
      }
      enum "punt-stormcontrol" {
        value 267;
        description
          "puntstormcontrol";
      }
      enum "ip6mcrxstats" {
        value 268;
        description
          "ip6mcrxstats";
      }
      enum "ipmctxintf" {
        value 269;
        description
          "ipmctxintf";
      }
      enum "op2tap" {
        value 270;
        description
          "op2tap";
      }
      enum "mplsole" {
        value 271;
        description
          "mplsole";
      }
      enum "syncrpc" {
        value 272;
        description
          "syncrpc";
      }
    }
    description
      "Ofa table";
  }

  container ofa {
    config false;
    description
      "OFA Data";
    container stats {
      description
        "OFA Stats Data";
      container nodes {
        description
          "OFA data for available nodes";
        list node {
          key "node-name";
          description
            "OFA operational data for a particular node";
          container table-datas {
            description
              "OFA Resources table";
            list table-data {
              key "resource";
              description
                "OFA Resources table";
              leaf resource {
                type Ofa-table;
                description
                  "Resource type";
              }
              uses OFA-NPD-SYSDB-TABLE-RESOURCE;
            }
          }
          leaf node-name {
            type xr:Node-id;
            description
              "Node ID";
          }
        }
      }
    }
  }
}
