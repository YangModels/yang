submodule Cisco-IOS-XR-ethernet-lldp-oper-sub1 {
  belongs-to Cisco-IOS-XR-ethernet-lldp-oper {
    prefix Cisco-IOS-XR-ethernet-lldp-oper;
  }

  import ietf-inet-types {
    prefix inet;
  }
  import ietf-yang-types {
    prefix yang;
  }
  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR ethernet-lldp package operational data.
     
     Copyright (c) 2013-2020 by Cisco Systems, Inc.
     All rights reserved.";

  revision 2020-09-01 {
    description
      "Fixing backward compatibility error in module.";
    semver:module-version "1.1.0";
  }
  revision 2019-04-05 {
    description
      "Establish semantic version baseline.";
    semver:module-version "1.0.1";
  }
  revision 2017-11-13 {
    description
      "Added a new notification.";
  }
  revision 2015-11-09 {
    description
      "IOS XR 6.0 revision.";
  }

  typedef In6-addr {
    type inet:ipv6-address;
    description
      "In6 addr";
  }

  typedef Lldp-l3-addr-protocol {
    type enumeration {
      enum "ipv4" {
        description
          "IPv4";
      }
      enum "ipv6" {
        description
          "IPv6";
      }
    }
    description
      "Lldp l3 addr protocol";
  }

  grouping LLDP-STATS {
    description
      "LLDP statistics";
    leaf transmitted-packets {
      type uint32;
      description
        "Transmitted packets";
    }
    leaf aged-out-entries {
      type uint32;
      description
        "Aged out entries";
    }
    leaf discarded-packets {
      type uint32;
      description
        "Discarded packets";
    }
    leaf bad-packets {
      type uint32;
      description
        "Bad packet received and dropped";
    }
    leaf received-packets {
      type uint32;
      description
        "Received packets";
    }
    leaf discarded-tl-vs {
      type uint32;
      description
        "Discarded TLVs";
    }
    leaf unrecognized-tl-vs {
      type uint32;
      description
        "Unrecognized TLVs";
    }
    leaf out-of-memory-errors {
      type uint32;
      description
        "Out-of-memory conditions";
    }
    leaf encapsulation-errors {
      type uint32;
      description
        "Transmission errors";
    }
    leaf queue-overflow-errors {
      type uint32;
      description
        "Queue overflows";
    }
    leaf table-overflow-errors {
      type uint32;
      description
        "Table overflows";
    }
  }

  grouping LLDP-INTERFACE {
    description
      "Information about an interface that LLDP is
       running on";
    container local-network-addresses {
      description
        "Local Management Addresses";
      uses LLDP-ADDRESS-ENTRY;
    }
    leaf interface-name-xr {
      type xr:Interface-name;
      description
        "Interface";
    }
    leaf tx-enabled {
      type uint8;
      description
        "TX Enabled";
    }
    leaf rx-enabled {
      type uint8;
      description
        "RX Enabled";
    }
    leaf tx-state {
      type string;
      description
        "TX State";
    }
    leaf rx-state {
      type string;
      description
        "RX State";
    }
    leaf if-index {
      type uint32;
      description
        "ifIndex";
    }
    leaf port-id {
      type string;
      description
        "Outgoing port identifier";
    }
    leaf port-id-sub-type {
      type uint8;
      description
        "Port ID sub type";
    }
    leaf port-description {
      type string;
      description
        "Port Description";
    }
  }

  grouping LLDP-ORG-DEF-TLV-ENTRY {
    description
      "LLDP Org Def TLV entry";
    list lldp-org-def-tlv-entry {
      description
        "Next Org Def TLV entry in list";
      leaf oui {
        type uint32;
        description
          "Organizationally Unique Identifier";
      }
      leaf tlv-subtype {
        type uint8;
        description
          "Org Def TLV subtype";
      }
      leaf tlv-info-indes {
        type uint32;
        description
          "lldpRemOrgDefInfoIndex";
      }
      leaf tlv-value {
        type yang:hex-string;
        description
          "Org Def TLV payload";
      }
    }
  }

  grouping LLDP-UNKNOWN-TLV-ENTRY {
    description
      "LLDP Unknown TLV entry";
    list lldp-unknown-tlv-entry {
      description
        "Next unknown TLV entry in list";
      leaf tlv-type {
        type uint8;
        description
          "Unknown TLV type";
      }
      leaf tlv-value {
        type yang:hex-string;
        description
          "Unknown TLV payload";
      }
    }
  }

  grouping LLDP-NEIGHBOR-ENTRY-MIB-DETAILS {
    description
      "MIB neighbor info";
    container unknown-tlv-list {
      description
        "Unknown TLV list";
      uses LLDP-UNKNOWN-TLV-ENTRY;
    }
    container org-def-tlv-list {
      description
        "Org Def TLV list";
      uses LLDP-ORG-DEF-TLV-ENTRY;
    }
    leaf rem-time-mark {
      type uint32;
      description
        "TimeFilter";
    }
    leaf rem-local-port-num {
      type uint32;
      description
        "LldpPortNumber";
    }
    leaf rem-index {
      type uint32;
      description
        "lldpRemIndex";
    }
    leaf chassis-id-sub-type {
      type uint8;
      description
        "Chassis ID sub type";
    }
    leaf chassis-id-len {
      type uint16;
      description
        "Chassis ID length";
    }
    leaf port-id-sub-type {
      type uint8;
      description
        "Port ID sub type";
    }
    leaf port-id-len {
      type uint16;
      description
        "Port ID length";
    }
    leaf combined-capabilities {
      type uint32;
      description
        "Supported and combined cpabilities";
    }
  }

  grouping LLDP-L3-ADDR {
    description
      "LLDP L3 ADDR";
    leaf address-type {
      type Lldp-l3-addr-protocol;
      description
        "AddressType";
    }
    leaf ipv4-address {
      when "../address-type = 'ipv4'" {
        description
          "../AddressType = 'IPv4'";
      }
      type inet:ipv4-address;
      description
        "IPv4 address";
    }
    leaf ipv6-address {
      when "../address-type = 'ipv6'" {
        description
          "../AddressType = 'IPv6'";
      }
      type In6-addr;
      description
        "IPv6 address";
    }
  }

  grouping LLDP-ADDRESS-ENTRY {
    description
      "LLDP Address entry";
    list lldp-addr-entry {
      description
        "Next address entry in list";
      container address {
        description
          "Network layer address";
        uses LLDP-L3-ADDR;
      }
      leaf ma-subtype {
        type uint8;
        description
          "MA sub type";
      }
      leaf if-num {
        type uint32;
        description
          "Interface num";
      }
    }
  }

  grouping LLDP-NEIGHBOR-ENTRY-DETAILS {
    description
      "Detailed neighbor info";
    container network-addresses {
      description
        "Management Addresses";
      uses LLDP-ADDRESS-ENTRY;
    }
    leaf peer-mac-address {
      type yang:mac-address;
      description
        "Peer Mac Address";
    }
    leaf port-description {
      type string;
      description
        "Port Description";
    }
    leaf system-name {
      type string;
      description
        "System Name";
    }
    leaf system-description {
      type string;
      description
        "System Description";
    }
    leaf time-remaining {
      type uint32;
      description
        "Time remaining";
    }
    leaf system-capabilities {
      type string;
      description
        "System Capabilities";
    }
    leaf enabled-capabilities {
      type string;
      description
        "Enabled Capabilities";
    }
    leaf auto-negotiation {
      type string;
      description
        "Auto Negotiation";
    }
    leaf physical-media-capabilities {
      type string;
      description
        "Physical media capabilities";
    }
    leaf media-attachment-unit-type {
      type uint32;
      description
        "Media Attachment Unit type";
    }
    leaf port-vlan-id {
      type uint32;
      description
        "Vlan ID";
    }
  }

  grouping LLDP-NEIGHBOR {
    description
      "LLDP neighbor info";
    list lldp-neighbor {
      description
        "Next neighbor in the list";
      container detail {
        description
          "Detailed neighbor info";
        uses LLDP-NEIGHBOR-ENTRY-DETAILS;
      }
      container mib {
        description
          "MIB nieghbor info";
        uses LLDP-NEIGHBOR-ENTRY-MIB-DETAILS;
      }
      leaf receiving-interface-name {
        type xr:Interface-name;
        description
          "Interface the neighbor entry was received on ";
      }
      leaf receiving-parent-interface-name {
        type xr:Interface-name;
        description
          "Parent Interface the neighbor entry was
           received on ";
      }
      leaf device-id {
        type string;
        description
          "Device identifier";
      }
      leaf chassis-id {
        type string;
        description
          "Chassis id";
      }
      leaf port-id-detail {
        type string;
        description
          "Outgoing port identifier";
      }
      leaf header-version {
        type uint8;
        description
          "Version number";
      }
      leaf hold-time {
        type uint16;
        description
          "Remaining hold time";
      }
      leaf enabled-capabilities {
        type string;
        description
          "Enabled Capabilities";
      }
      leaf platform {
        type string;
        description
          "Platform type";
      }
    }
  }
}
