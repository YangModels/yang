submodule Cisco-IOS-XR-crypto-sam-oper-sub1 {
  belongs-to Cisco-IOS-XR-crypto-sam-oper {
    prefix Cisco-IOS-XR-crypto-sam-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR crypto-sam package operational data.
     
     Copyright (c) 2013-2019 by Cisco Systems, Inc.
     All rights reserved.";

  revision 2019-04-05 {
    description
      "Establish semantic version baseline.";
    semver:module-version "1.0.1";
  }
  revision 2017-09-07 {
    description
      "Fixed type translation error.";
  }
  revision 2015-01-07 {
    description
      "IOS XR 5.3.1 revision.";
  }

  typedef Log-tables {
    type enumeration {
      enum "unkown" {
        description
          "Table is not known";
      }
      enum "memory-digest-table" {
        description
          "Table is memory digest table";
      }
      enum "system-database-digest" {
        description
          "Table is system database digest table";
      }
      enum "sam-tables" {
        description
          "Table is SAM table";
      }
    }
    description
      "Log tables";
  }

  typedef Certificate-issuer {
    type enumeration {
      enum "unknown" {
        description
          "Issuer is not known";
      }
      enum "code-signing-server-certificate-authority" {
        description
          "Issuer is code signing server certificate
           authority";
      }
    }
    description
      "Certificate issuers";
  }

  typedef Log-error {
    type enumeration {
      enum "unknown" {
        description
          "Log error is not known";
      }
      enum "log-message-error" {
        description
          "Log error is message error";
      }
      enum "get-issuer-name-failed" {
        description
          "Log error is get issuer name failed";
      }
    }
    description
      "Log errors";
  }

  typedef Log-code {
    type enumeration {
      enum "unknown" {
        description
          "Log code is not known";
      }
      enum "sam-server-restared-router-reboot" {
        description
          "Log code is SAM server restarted through router
           reboot";
      }
      enum "sam-server-restared" {
        description
          "Log code is SAM server restarted";
      }
      enum "added-certificate-in-table" {
        description
          "Log code is Added certificate in table";
      }
      enum "copied-certificate-in-table" {
        description
          "Log code is Copied certificate in table";
      }
      enum "certificate-flag-changed" {
        description
          "Log code is Certificate flag changed";
      }
      enum "validated-certificate" {
        description
          "Log code is validated ceritificate";
      }
      enum "certificate-expired-detected" {
        description
          "Log code is Ceritificate expired detected";
      }
      enum "certificate-revoked-detected" {
        description
          "Log code is Ceritificate revoked detected";
      }
      enum "ca-certificate-expired-detected" {
        description
          "Log code is CA Ceritificate expired detected";
      }
      enum "ca-certificate-revoked-detected" {
        description
          "Log code is CA Ceritificate revoked detected";
      }
      enum "deleted-certificate-from-table" {
        description
          "Log code is Deleted certificate from table";
      }
      enum "crl-added-updated-in-table" {
        description
          "Log code is CRL added/updated in table";
      }
      enum "checked-memory-digest" {
        description
          "Log code is Checked memory digest";
      }
      enum "nvram-digest-mismatch-detected" {
        description
          "Log code is NVRAM digest Mistmatch detected";
      }
      enum "insecure-backup-file-detected" {
        description
          "Log code is Insecure backup file detected";
      }
      enum "error-restore-operation" {
        description
          "Log code is Error during restore operation,
           backup file might have not been intact";
      }
      enum "backup-file-on-nvram-deleted" {
        description
          "Log code is Found backup file on NVRAM for SAM
           log had been deleted";
      }
      enum "sam-log-file-recovered-from-system-database" {
        description
          "Log code is SAM log backup file recovered from
           system database";
      }
      enum "validated-elf" {
        description
          "Log code is validated ELF";
      }
      enum "namespace-deleted-recovered-by-sam" {
        description
          "Log code is SAM system database name space
           deleted/recovered by SAM";
      }
    }
    description
      "Log code types";
  }

  grouping ISSUER-INFO {
    description
      "CRL issuer information";
    leaf common-name {
      type string;
      description
        "Common name";
    }
    leaf organization {
      type string;
      description
        "Organization";
    }
    leaf country {
      type string;
      description
        "Country";
    }
  }

  grouping CRYPTO-SAM-CRL-INFO {
    description
      "CRL table entry information";
    container issuer {
      description
        "Issuer name";
      uses ISSUER-INFO;
    }
    leaf crl-index {
      type uint16;
      description
        " CRL index";
    }
    leaf updates {
      type string;
      description
        "Updated time of CRL is displayed";
    }
  }

  grouping FLAGS {
    description
      "Certificate flags";
    leaf is-trusted {
      type boolean;
      description
        "Trusted flag";
    }
    leaf is-revoked {
      type boolean;
      description
        "Revoked flag";
    }
    leaf is-expired {
      type boolean;
      description
        "Expired flag";
    }
    leaf is-validated {
      type boolean;
      description
        "Validated flag";
    }
  }

  grouping CRYPTO-SAM-CERTIFICATE-COMMON {
    description
      "Certificate table common information";
    container certificate-flags {
      description
        "Certificate flags";
      uses FLAGS;
    }
    leaf location {
      type string;
      description
        "Certificate location";
    }
    leaf certificate-index {
      type uint16;
      description
        "Certificate index";
    }
  }

  grouping LOG-SAM-INFO {
    description
      "SAM log information";
    leaf time {
      type string;
      description
        "Log time";
    }
    leaf code {
      type Log-code;
      description
        "Log code";
    }
    leaf target-device {
      type string;
      description
        "Target device";
    }
    leaf index {
      type uint32;
      description
        "Device index";
    }
    leaf error {
      type Log-error;
      description
        "Log error message";
    }
    leaf issuer {
      type Certificate-issuer;
      description
        "Issuer of the certificate";
    }
    leaf serial-no {
      type string;
      description
        "Serial number";
    }
    leaf sam-table-index {
      type uint32;
      description
        "SAM table index";
    }
    leaf update-time {
      type string;
      description
        "Last update time of the certificate";
    }
    leaf source-device {
      type string;
      description
        "source device name";
    }
    leaf table {
      type Log-tables;
      description
        "Log table information";
    }
  }

  grouping CRYPTO-LOG {
    description
      "SAM logs data";
    leaf total-entries {
      type uint32;
      description
        "Total log entries available";
    }
    leaf entries-shown {
      type uint32;
      description
        "Total entries shown";
    }
    list logs {
      description
        "SAM logs";
      uses LOG-SAM-INFO;
    }
  }

  grouping CRYPTO-SAM-SYSINFO {
    description
      "SAM system information";
    leaf is-running {
      type boolean;
      description
        "True if SAM status information runs";
    }
    leaf prompt-interval {
      type uint32;
      units "second";
      description
        "Prompt interval atreboot time in seconds";
    }
    leaf is-default-response {
      type boolean;
      description
        "True if promptdefault response is true";
    }
  }
}
