module Cisco-IOS-XR-roe-cfg {
  namespace "http://cisco.com/ns/yang/Cisco-IOS-XR-roe-cfg";
  prefix roe-cfg;

  import ietf-yang-types {
    prefix yang;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR roe package configuration.
     
     This module contains definitions
     for the following management objects:
       roe: ROE configuration data
     
     Copyright (c) 2013-2020 by Cisco Systems, Inc.
     All rights reserved.";

  revision 2020-02-27 {
    description
      "Initial ROE config yang";
    semver:module-version "1.0.0";
  }
  revision 2019-04-05 {
    description
      "Establish semantic version baseline.";
  }
  revision 2015-11-09 {
    description
      "IOS XR 6.0 revision.";
  }

  typedef Roe-order-info {
    type enumeration {
      enum "sequence-num" {
        value 0;
        description
          "Sequence Number";
      }
      enum "time-stamp" {
        value 1;
        description
          "Time Stamp";
      }
      enum "both" {
        value 2;
        description
          "Both";
      }
    }
    description
      "Roe order info";
  }

  typedef Roe-mapper {
    type enumeration {
      enum "structure-agnostic-tunneling" {
        value 0;
        description
          "Structure agnostic tunneling mode";
      }
      enum "structure-agnostic-wo-line-coding" {
        value 1;
        description
          "Structure agnostic without line coding mode";
      }
      enum "structure-aware" {
        value 2;
        description
          "Structure aware mode";
      }
      enum "native-timing" {
        value 3;
        description
          "Native timing mode";
      }
      enum "native-frequency" {
        value 4;
        description
          "Native frequency mode";
      }
    }
    description
      "Roe mapper";
  }

  container roe {
    description
      "ROE configuration data";
    container ethlinks {
      description
        "List of ROE Eth link profiles";
      list ethlink {
        key "ethlink-id";
        description
          "ROE Eth link configuration parameters";
        leaf enable {
          type empty;
          description
            "Enable Ethlink submode";
        }
        leaf destination-mac {
          type yang:mac-address;
          description
            "Ethlink <id> destination MAC address";
        }
        leaf source-mac {
          type yang:mac-address;
          description
            "Ethlink <id> source MAC address";
        }
        leaf ethlink-id {
          type uint32;
          description
            "Ethlink identifier";
        }
      }
    }
    container profiles {
      description
        "List of ROE Profile";
      list profile {
        key "profile-id";
        description
          "ROE profile parameters";
        leaf enable {
          type empty;
          description
            "Enable Profile submode";
        }
        leaf compress {
          type uint32 {
            range "0..1";
          }
          default "0";
          description
            "enable/disable compression";
        }
        leaf sample-width {
          type uint32 {
            range "0..255";
          }
          description
            "Sample width";
        }
        leaf num-of-containers {
          type uint32 {
            range "0..255";
          }
          description
            "Number of Containers";
        }
        leaf num-of-prach {
          type uint32 {
            range "0..255";
          }
          description
            "Number of PRACH";
        }
        leaf num-of-fft {
          type uint32 {
            range "0..255";
          }
          description
            "Number of FFT";
        }
        leaf packet-length {
          type uint32 {
            range "0..65535";
          }
          description
            "Packet length";
        }
        leaf demapper-flow-id {
          type uint32 {
            range "0..255";
          }
          description
            "Demapper flow id";
        }
        leaf mapper-flow-id {
          type uint32 {
            range "0..255";
          }
          description
            "Mapper flow id";
        }
        leaf idle-frame-thresh {
          type uint32 {
            range "0..255";
          }
          description
            "Idle Frame Threshold";
        }
        leaf num-of-control-containers {
          type uint32 {
            range "0..255";
          }
          description
            "Number of control containers";
        }
        leaf mapper-type {
          type Roe-mapper;
          description
            "Mapper type";
        }
        leaf idle-frame-size {
          type uint32 {
            range "0..255";
          }
          description
            "Idle Frame Size";
        }
        leaf accept-time-window {
          type uint32 {
            range "0..536870911";
          }
          description
            "Accept time window";
        }
        leaf order-info {
          type Roe-order-info;
          description
            "Order info type";
        }
        leaf ethlink-identifier {
          type uint32 {
            range "0..255";
          }
          description
            "Ethlink profile to be attached to this ROE
             profile";
        }
        leaf retimer-buffer {
          type uint32 {
            range "0..255";
          }
          description
            "Retimer buffer";
        }
        leaf encrypt {
          type uint32 {
            range "0..1";
          }
          default "0";
          description
            "enable/disable encryption";
        }
        leaf profile-id {
          type uint32;
          description
            "Profile identifier";
        }
      }
    }
  }
}
