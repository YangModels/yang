submodule Cisco-IOS-XR-invmgr-oper-sub2 {
  belongs-to Cisco-IOS-XR-invmgr-oper {
    prefix Cisco-IOS-XR-invmgr-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR invmgr package operational data.
     
     Copyright (c) 2013-2020 by Cisco Systems, Inc.
     All rights reserved.";

  revision 2020-07-24 {
    description
      "Addition of revision to match LNT.";
    semver:module-version "3.0.0";
  }
  revision 2020-05-08 {
    description
      "Deprecated Inventory:Rack container.
       2020-03-30
       Changed threshold-value type to int32.
       2019-10-07
       Added pluggable-info bag.
       2019-10-04
       Removed slot-info, vm-done bags.";
    semver:module-version "2.0.0";
  }
  revision 2019-04-05 {
    description
      "Establish semantic version baseline.";
    semver:module-version "1.0.0";
  }
  revision 2019-03-21 {
    description
      "Resolved string constraints issue.";
  }
  revision 2018-08-03 {
    description
      "Added slot-info and parent-info bags.";
  }
  revision 2018-04-19 {
    description
      "Added additional bags";
  }
  revision 2017-09-07 {
    description
      "Fixed type translation error.";
  }
  revision 2017-05-01 {
    description
      "Fixing backward compatibility error in module.";
  }
  revision 2015-11-09 {
    description
      "IOS XR 6.0 revision.";
  }

  typedef Threshold-relation {
    type enumeration {
      enum "less-than" {
        value 1;
        description
          "Sensor value is less than threshold";
      }
      enum "less-or-equal" {
        value 2;
        description
          "Sensor value is lesser than  or equal to
           threshold";
      }
      enum "greater-than" {
        value 3;
        description
          "Sensor value is greater than threshold";
      }
      enum "greater-or-equal" {
        value 4;
        description
          "Sensor value is greater than or equal to
           threshold";
      }
      enum "equal" {
        value 5;
        description
          "Sensor value is equal to threshold";
      }
      enum "not-equal" {
        value 6;
        description
          "Sensor value is not equal to threshold";
      }
    }
    description
      "Threshold relation";
  }

  typedef Threshold-severity {
    type enumeration {
      enum "other" {
        value 1;
        description
          "Other";
      }
      enum "minor" {
        value 10;
        description
          "Minor";
      }
      enum "major" {
        value 20;
        description
          "Major";
      }
      enum "critical" {
        value 30;
        description
          "Critical";
      }
    }
    description
      "Threshold severity";
  }

  typedef Sensor-status {
    type enumeration {
      enum "ok" {
        value 1;
        description
          "State ok";
      }
      enum "unavailable" {
        value 2;
        description
          "State Unavailable";
      }
      enum "non-operational" {
        value 3;
        description
          "State no operational";
      }
    }
    description
      "Sensor status";
  }

  typedef Sensor-data {
    type enumeration {
      enum "unknown" {
        value 2;
        description
          "Datatype unknown";
      }
      enum "ac-volts" {
        value 3;
        description
          "AC volts";
      }
      enum "dc-volts" {
        value 4;
        description
          "DC volts";
      }
      enum "amperes" {
        value 5;
        description
          "Amperes";
      }
      enum "watts" {
        value 6;
        description
          "Power in watts";
      }
      enum "hertz" {
        value 7;
        description
          "Frequency in hertz";
      }
      enum "celsius" {
        value 8;
        description
          "Celsius";
      }
      enum "rpm" {
        value 10;
        description
          "Rotations per minute";
      }
      enum "dbm" {
        value 14;
        description
          "Power in dBm";
      }
      enum "db" {
        value 15;
        description
          "Power in dB";
      }
    }
    description
      "Sensor measurement data types";
  }

  typedef Unit {
    type enumeration {
      enum "celsius" {
        description
          "Degree in celsius";
      }
      enum "milli-volts" {
        description
          "Milli volts";
      }
      enum "milli-amperes" {
        description
          "Milli amperes";
      }
      enum "rpm" {
        description
          "Rotations per minute";
      }
      enum "watts" {
        description
          "Watts";
      }
      enum "dbm" {
        description
          "dBm";
      }
      enum "db" {
        description
          "dB";
      }
    }
    description
      "Unit information";
  }

  grouping ENVMON-THRESHOLD-TYPE {
    description
      "Threshold information of a specific type";
    leaf threshold-severity {
      type Threshold-severity;
      description
        "Indicates minor, major, critical severities";
    }
    leaf threshold-relation {
      type Threshold-relation;
      description
        "Indicates relation between sensor value and
         threshold";
    }
    leaf threshold-value {
      type int32;
      description
        "Value of the configured threshold";
    }
    leaf threshold-name {
      type string {
        length "0..50";
      }
      description
        "Indicates the Threshold name";
    }
  }

  grouping ENVMON-THRESHOLD-INFO-XML {
    description
      "Threshold information";
    list threshold-array {
      description
        "Array of threshold";
      uses ENVMON-THRESHOLD-TYPE;
    }
  }

  grouping ENVMON-SENSOR-INFO-XML {
    description
      "Environment monitoring sensor information";
    container threshold {
      description
        "Threshold information";
      uses ENVMON-THRESHOLD-INFO-XML;
    }
    leaf description {
      type string {
        length "0..50";
      }
      description
        "Device Name";
    }
    leaf units {
      type Unit;
      description
        "Units of variable being read";
    }
    leaf value {
      type string {
        length "0..50";
      }
      description
        "Current reading of sensor Displays in decimal(ex
         1.234) for powersupply sensor type";
    }
    leaf data-type {
      type Sensor-data;
      description
        "Sensor data type";
    }
    leaf status {
      type Sensor-status;
      description
        "Sensor operation state";
    }
    leaf update-rate {
      type uint32;
      description
        "Sensor value update rate; set to 0 if sensor
         value is updated and evaluated immediately";
    }
  }
}
