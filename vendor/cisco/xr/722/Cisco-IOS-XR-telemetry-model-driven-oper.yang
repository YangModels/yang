module Cisco-IOS-XR-telemetry-model-driven-oper {
  namespace "http://cisco.com/ns/yang/Cisco-IOS-XR-telemetry-model-driven-oper";
  prefix telemetry-model-driven-oper;

  import ietf-inet-types {
    prefix inet;
  }
  import Cisco-IOS-XR-types {
    prefix xr;
  }
  import cisco-semver {
    prefix semver;
  }
  include Cisco-IOS-XR-telemetry-model-driven-oper-sub2 {
    revision-date 2020-03-11;
  }
  include Cisco-IOS-XR-telemetry-model-driven-oper-sub1 {
    revision-date 2020-03-11;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR telemetry-model-driven package operational data.
     
     This module contains definitions
     for the following management objects:
       telemetry-model-driven: Telemetry operational data
     
     Copyright (c) 2013-2020 by Cisco Systems, Inc.
     All rights reserved.";

  revision 2020-03-11 {
    description
      "Updated the encodings supported";
    semver:module-version "1.1.0";
  }
  revision 2019-04-05 {
    description
      "Establish semantic version baseline.";
    semver:module-version "1.0.1";
  }
  revision 2017-09-27 {
    description
      "Summary container added";
  }
  revision 2017-05-05 {
    description
      "Modified the type for the state variables";
  }
  revision 2017-05-01 {
    description
      "Fixing backward compatibility error in module.";
  }
  revision 2017-02-09 {
    description
      "Added DSCP";
  }
  revision 2017-01-30 {
    description
      "Initial 6.2.1 revision";
  }
  revision 2015-11-09 {
    description
      "IOS XR 6.0 revision.";
  }

  container telemetry-model-driven {
    config false;
    description
      "Telemetry operational data";
    container destinations {
      description
        "Telemetry Destinations";
      list destination {
        key "destination-id";
        description
          "Telemetry Destination";
        leaf destination-id {
          type xr:Cisco-ios-xr-string;
          description
            "Id of the destination";
        }
        uses MDT-DESTINATION-GROUP-DETAIL;
      }
    }
    container subscriptions {
      description
        "Telemetry Subscriptions";
      list subscription {
        key "subscription-id";
        description
          "Telemetry Subscription";
        leaf subscription-id {
          type xr:Cisco-ios-xr-string;
          description
            "Id of the subscription";
        }
        uses MDT-SUBSCRIPTION-DETAILS;
      }
    }
    container channel-statistics {
      description
        "GRPC channel statistics";
      list channel-statistic {
        description
          "GRPC channel details";
        leaf subscription-id {
          type xr:Cisco-ios-xr-string;
          description
            "Id of the subscription";
        }
        leaf destination-address {
          type inet:ip-address-no-zone;
          description
            "Destination IP address";
        }
        leaf destination-port {
          type xr:Cisco-ios-xr-port-number;
          description
            "Destination port number";
        }
        uses MDT-DESTINATION-CHAN-STATS;
      }
    }
    container sensor-groups {
      description
        "Telemetry Sensor Groups";
      list sensor-group {
        key "sensor-group-id";
        description
          "Telemetry Sensor Groups";
        leaf sensor-group-id {
          type xr:Cisco-ios-xr-string;
          description
            "Id of the sensor group";
        }
        uses MDT-SENSOR-GROUP;
      }
    }
    container summary {
      description
        "Telemetry Summary info";
      uses TELEMETRY-SHOW-SUMMARY;
    }
  }
}
