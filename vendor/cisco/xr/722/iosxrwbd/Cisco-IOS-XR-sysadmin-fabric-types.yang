module Cisco-IOS-XR-sysadmin-fabric-types {
  namespace "http://www.cisco.com/ns/yang/Cisco-IOS-XR-sysadmin-fabric-types";
  prefix fabric-types;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains definitions
     for the Calvados model objects.
     
     Copyright (c) 2012-2020 by Cisco Systems, Inc.
     All rights reserved.";

  revision 2020-04-30 {
    description
      "Removed the usage of retimer_id_type, asic_location_oldcastle_type and few string edited";
    semver:module-version "3.0.0";
  }
  revision 2019-12-13 {
    description
      "fabric_fgid_elements_type range changed to 120832 after reducing the fgid scale for fretta platforms";
    semver:module-version "2.0.0";
  }
  revision 2019-04-15 {
    description
      "Establish semantic version baseline.";
    semver:module-version "1.0.0";
  }
  revision 2018-10-23 {
    description
      "sfe_link_type range changed to 215 after spitfire code merge";
  }
  revision 2017-05-01 {
    description
      "Namespace change to comply with Cisco guidelines on namespace";
  }
  revision 2017-04-07 {
    description
      "Fabric types for NCS5500 platforms";
  }

  typedef instance_type {
    type string {
      pattern "[0-2]|all";
    }
  }

  typedef sfe_instance_type {
    type string {
      pattern "[0-5]|all";
    }
  }

  typedef sfe_link_type {
    type int32 {
      range "0 .. 215";
    }
  }

  typedef sfe_start_link_type {
    type int32 {
      range "0 .. 215";
    }
  }

  typedef sfe_end_link_type {
    type int32 {
      range "0 .. 215";
    }
  }

  typedef plane_type {
    type string {
      pattern "all|[0-12]";
    }
  }

  typedef plane_zermatt_type {
    type string {
      pattern "all|0";
    }
  }

  typedef conf_plane_type {
    type string {
      pattern "[0-12]";
    }
  }

  typedef conf_plane_zermatt_type {
    type string {
      pattern "0";
    }
  }

  typedef conf_instance_type {
    type int32 {
      range "0..7";
    }
  }

  typedef conf_folded_instance_type {
    type int32;
    default "0";
  }

  typedef conf_location_type {
    type string {
      pattern "(0?[F|f][0-3])/[F|f][C|c](0?[0-9]|1[0-1])";
    }
  }

  typedef link_port_type {
    type string {
      pattern "fia|s1|s2|s3";
    }
  }

  typedef asic_stage_type {
    type string {
      pattern "fia|s123|s13|s2|b2b";
    }
  }

  typedef sfe_stage_type {
    type string {
      pattern "s1|s2|s3|s123";
    }
  }

  typedef asic_location_type {
    type string {
      pattern "((0?[0-9]|1[0-5])/([F|f][C|c](0?[0-5]))/(0?[0-5]))|((0?[0-9]|1[0-5])/(0?[0-7])/(0?[0-5]))|(([F|f][0-3])/([F|f][C|c](0?[0-9]|1[0-1]))/(0?[0-2]))";
    }
  }

  typedef asic_location_zermatt_type {
    type string {
      pattern "((0)/([R|r][P|p](0))/(0?[0-1]))|((0)/(0)/(0?[0-7]))";
    }
  }

  typedef link_port_location_type {
    type string {
      pattern "((0?[0-9]|1[0-5])/([F|f][C|c](0?[0-5]))/(0?[0-5])/(0?[0-9]|[1-9][0-9]|1[0-3][0-9]|14[0-3]))|((0?[0-9]|1[0-5])/(0?[0-7])/(0?[0-5])/(0?[0-9]|[1-2][0-9]|3[0-5]))|(([F|f][0-3])/([F|f][C|c](0?[0-9]|1[0-1]))/(0?[0-2])/(0?[0-9]|[1-9][0-9]|1[0-3][0-9]|14[0-3]))";
    }
  }

  typedef link_port_location_zermatt_type_for_yang {
    type string {
      pattern "((0)/([R|r][P|p](0))/(0?[0-1])/(0?[0-9]|[1-9][0-9]|1[0-3][0-9]|14[0-3]))|((0)/(0)/(0?[0-7])/(0?[0-9]|[1-3][0-9]|4[0-7]))";
    }
  }

  typedef link_port_location_zermatt_type {
    type string {
      pattern "((0)/([R|r][P|p](0))/(0?[0-1])/(0?[0-9]|[1-9][0-9]|1[0-3][0-9]|14[0-3]))|((0)/(0)/(0?[0-7])/(0?[0-9]|[1-2][0-9]|3[0-5]))";
    }
  }

  typedef link_port_location_oldcastle_type {
    type string {
      pattern "((0)/([R|r][P|p](0))/(0)/(0?[0-9]|[1-9][0-9]|1[0-3][0-9]|14[0-3]))|((0)/(0)/(0?[0-3])/(0?[0-9]|[1-3][0-9]|4[0-7]))";
    }
  }

  typedef bundle_location_type {
    type string {
      pattern "((0?[0-9]|1[0-5])/([F|f][C|c](0?[0-5]))/((0?[0-9])|(1[0-5])))|(([F|f][0-3])/([F|f][C|c](0?[0-9]|1[0-1]))/((0?[0-9])|([1-2][0-9])|(3[0-1])))";
    }
  }

  typedef fabric_fgid_id_type {
    type int32 {
      range "0..524287";
    }
  }

  typedef fabric_fgid_elements_type {
    type int32 {
      range "0..524288";
    }
  }

  typedef fabric_fgid_start_id_type {
    type int32 {
      range "0..524287";
    }
  }

  typedef fabric_fgid_end_id_type {
    type int32 {
      range "0..524287";
    }
  }

  typedef fabric_nc55_fixed_fgid_id_type {
    type int32 {
      range "0..524287";
    }
  }

  typedef fabric_nc55_fixed_fgid_elements_type {
    type int32 {
      range "0..524288";
    }
  }

  typedef fabric_nc55_fixed_fgid_start_id_type {
    type int32 {
      range "0..524287";
    }
  }

  typedef fabric_nc55_fixed_fgid_end_id_type {
    type int32 {
      range "0..524287";
    }
  }

  typedef fabric_dump_file_name_type {
    type string;
  }

  typedef fabric_diag_shell_cmd_type {
    type string;
  }

  typedef fabric_diag_shell_instance_num_type {
    type int32 {
      range "0..5";
    }
  }

  typedef fabric_rack_num_type {
    type string {
      pattern "(0?[0-9])|(1[0-5])|([F|f][0-3])";
    }
  }

  typedef fabric_fabid_type {
    type string {
      pattern "(0?[0-9]|1[0-5])/(0?[0-7])/(0?[0-5])|([0-9]|[1-9][0-9]|[1-9][0-9][0-9]|10[0-1][0-9]|102[0-3])";
    }
  }

  typedef sfe_location_type {
    type string {
      pattern "((0?[0-9]|1[0-5])/([F|f][C|c](0?[0-5])))|(([F|f][0-3])/([F|f][C|c](0?[0-9]|1[0-1])))";
    }
  }

  typedef sfe_location_zermatt_type {
    type string {
      pattern "((0?[0-9]|1[0-5])/([F|f][C|c](0?[0-5])))|(0/([R|r][P|p]0))";
    }
  }

  typedef cxp_port_type {
    type uint32 {
      range "0..31";
    }
  }
}
