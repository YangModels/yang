module Cisco-IOS-XR-fia-hw-profile-cfg {
  namespace "http://cisco.com/ns/yang/Cisco-IOS-XR-fia-hw-profile-cfg";
  prefix fia-hw-profile-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR fia-hw-profile package configuration.
     
     This module contains definitions
     for the following management objects:
       hw-module-profile-config: none
     
     Copyright (c) 2013-2020 by Cisco Systems, Inc.
     All rights reserved.";

  revision 2020-07-31 {
    description
      "Schema updated.
       2020-07-20
         Schema added.";
    semver:module-version "2.1.0";
  }
  revision 2020-04-30 {
    description
      "ACL UDK config changes: Added Common-ACL, replaced ProtType with NextHdr and Precedence with TraffClass
       2020-04-22
       SRV6 leaf deprecated and replaced by SRv6 Mode leaf
       2020-01-07
       Schema added.
       2020-01-05
       MGBL Sync config missmatch.";
    semver:module-version "2.0.0";
  }
  revision 2019-04-05 {
    description
      "Establish semantic version baseline.";
    semver:module-version "1.1.0";
  }
  revision 2016-06-22 {
    description
      "Schema added.";
  }
  revision 2015-11-09 {
    description
      "IOS XR 6.0 revision.";
  }

  typedef Srv6-mode {
    type enumeration {
      enum "base" {
        value 3;
        description
          "SRv6 base mode";
      }
    }
    description
      "Srv6 mode";
  }

  typedef Srv6-profile {
    type enumeration {
      enum "enable" {
        value 1;
        description
          "Enable with default behavior for traffic-class";
      }
      enum "enable-with-traffic-class-propagation" {
        value 2;
        description
          "Enable with traffic-class propagation";
      }
      enum "enable-with-traffic-class-value" {
        value 3;
        description
          "Enable with traffic-class set";
      }
    }
    description
      "Srv6 profile";
  }

  typedef Plane-rack {
    type uint32 {
      range "0..15";
    }
    description
      "Plane rack";
  }

  typedef Srv6-traffic-class-value {
    type uint32 {
      range "0..255";
    }
    description
      "Srv6 traffic class value";
  }

  container hw-module-profile-config {
    description
      "none";
    container profile {
      description
        "Configure profile.";
      container tcam-table {
        description
          "Configure profile for TCAM LC cards";
        container fib-table {
          description
            "FIB table for TCAM LC cards";
          container ipv4-address {
            description
              "IPv4 table for TCAM LC cards";
            container ipv4-unicast {
              description
                "Unicast table for TCAM LC cards";
              container ipv4-unicast-prefix-lengths {
                description
                  "IPv4 Unicast prefix ";
                list ipv4-unicast-prefix-length {
                  key "prefix-length";
                  description
                    "IPv4 Unicast prefix length";
                  leaf ipv4-unicast-prefix-percent {
                    type string;
                    units "percentage";
                    description
                      "curve out percentage of TCAM table
                       entries";
                  }
                  leaf prefix-length {
                    type uint32 {
                      range "0..32";
                    }
                    description
                      "prefix length";
                  }
                }
              }
              leaf ipv4-unicast-percent {
                type uint32 {
                  range "0..100";
                }
                units "percentage";
                description
                  "curve out percentage of TCAM table entries";
              }
            }
          }
          container ipv6-address {
            description
              "IPv6 table for TCAM LC cards";
            container ipv6-unicast {
              description
                "Unicast table for TCAM LC cards";
              container ipv6-unicast-prefix-lengths {
                description
                  "IPv6 Unicast prefix ";
                list ipv6-unicast-prefix-length {
                  key "prefix-length";
                  description
                    "IPv6 Unicast prefix length";
                  leaf ipv6-unicast-prefix-percent {
                    type string;
                    units "percentage";
                    description
                      "curve out percentage of TCAM table
                       entries";
                  }
                  leaf prefix-length {
                    type uint32 {
                      range "0..128";
                    }
                    description
                      "prefix length";
                  }
                }
              }
              leaf ipv6-unicast-percent {
                type uint32 {
                  range "0..100";
                }
                units "percentage";
                description
                  "curve out percentage of TCAM table entries";
              }
            }
          }
        }
        container acl-prefix {
          description
            "ACL table to configure";
          leaf acl-prefix-percent {
            type uint32 {
              range "0..100";
            }
            units "percentage";
            description
              "Percent to configure";
          }
        }
      }
      container netflow {
        description
          "Configure Netflow profile.";
        container ipfix-location-all {
          description
            "IPFIX315 Location All";
          leaf ipfix-location-all-leaf {
            type uint32;
            description
              "If Enabled set value to 65535";
          }
        }
        container fpc-netflow-locations {
          description
            "none";
          list fpc-netflow-location {
            key "location-string";
            description
              "none";
            leaf location-string {
              type xr:Cisco-ios-xr-string;
              description
                "Location of NETFLOW config";
            }
            list fpc-netflow-location-leaf {
              key "location-id";
              description
                "none";
              leaf location-id {
                type uint32;
                description
                  "Location ID";
              }
              leaf enable-val {
                type uint32;
                mandatory true;
                description
                  "If Enabled set value to 65535";
              }
            }
          }
        }
        container ipfix-netflow-locations {
          description
            "none";
          list ipfix-netflow-location {
            key "location-string";
            description
              "none";
            leaf location-string {
              type xr:Cisco-ios-xr-string;
              description
                "Location of NETFLOW config";
            }
            list ipfix-netflow-location-leaf {
              key "location-id";
              description
                "none";
              leaf location-id {
                type uint32;
                description
                  "Location ID";
              }
              leaf enable-val {
                type uint32;
                mandatory true;
                description
                  "If Enabled set value to 65535";
              }
            }
          }
        }
        container fpc-location-all {
          description
            "FPC Location All";
          leaf fpc-location-all-leaf {
            type uint32;
            description
              "If Enabled set value to 65535";
          }
        }
      }
      container flowspec-table {
        description
          "Configure Flowspec profile.";
        container flowspecs {
          description
            "Configure v6 enable on Flowspec profile.";
          list flowspec {
            key "location-string location-id";
            description
              "none";
            leaf location-string {
              type xr:Cisco-ios-xr-string;
              description
                "Location of FLOWSPEC config";
            }
            leaf location-id {
              type uint32;
              description
                "Location ID hex to Decimal 65535";
            }
            leaf enable-val {
              type uint32;
              mandatory true;
              description
                "If Enabled set value to 1";
            }
          }
        }
      }
      container bundle-hash {
        description
          "Configure Bundle Hash related parameters";
        container hash-index-locations {
          description
            "Bundle hash polynomial config";
          list hash-index-location {
            key "node-name";
            description
              "Bundle hash polynomial config location";
            leaf node-name {
              type xr:Cisco-ios-xr-string;
              description
                "NodeName";
            }
            list hash-index-location-leaf {
              key "location";
              description
                "Bundle hash polynomial config location leaf";
              leaf hash-index-location-leaf {
                type uint32;
                mandatory true;
                description
                  "Hash Index Location Leaf";
              }
              leaf location {
                type uint32;
                description
                  "Location";
              }
            }
          }
        }
        leaf per-pkt-round-robin {
          type boolean;
          description
            "bundlehash global per_pkt_round_robin mode";
        }
        leaf ignore-ing-port {
          type boolean;
          description
            "bundlehash ignore_ingress_port flag";
        }
      }
      container bgp-mp-pic {
        description
          "Configure bgp-mp-pic";
        leaf enable {
          type boolean;
          description
            "Enabled or disabled";
        }
      }
      container load-balance {
        description
          "Configure load balance parameters";
        leaf load-balance-profile {
          type uint32;
          description
            "Configure load balance parameters";
        }
      }
      container stats {
        description
          "Configure stats";
        container stats-profile-modes {
          description
            "Configure stats for qos-enhanced, acl-permit
             and ingress-sr";
          list stats-profile-mode {
            key "counter-profile";
            description
              "Stats mode";
            leaf mode {
              type uint32;
              mandatory true;
              description
                "Stats Mode";
            }
            leaf counter-profile {
              type uint32;
              description
                "none";
            }
          }
        }
      }
      container segment-routing {
        description
          "Configure Segment Routing profile.";
        container srv6 {
          description
            "Configure SRv6 profile.";
          container mode {
            description
              "Enable SRv6 mode/profile";
            leaf mode-type {
              when "../profile-type = 'enable' or ../profile-type = 'enable-with-traffic-class-propagation' or ../profile-type = 'enable-with-traffic-class-value'" {
                description
                  "../ProfileType = Enable or ../ProfileType
                   = EnableWithTrafficClassPropagation or .
                   ./ProfileType =
                   EnableWithTrafficClassValue";
              }
              type Srv6-mode;
              default "base";
              description
                "Mode type";
            }
            leaf profile-type {
              type Srv6-profile;
              default "enable";
              description
                "Profile type";
            }
            leaf traffic-class-value {
              when "../profile-type = 'enable-with-traffic-class-value'" {
                description
                  "../ProfileType =
                   EnableWithTrafficClassValue";
              }
              type Srv6-traffic-class-value;
              default "0";
              description
                "Traffic-class value";
            }
          }
        }
      }
      container profile-acl {
        description
          "Configure acl profile";
        container acl-ingress-compress-enable-locations {
          description
            "ingress compress enable";
          list acl-ingress-compress-enable-location {
            key "location-string";
            description
              "none";
            leaf location-string {
              type xr:Cisco-ios-xr-string;
              description
                "Location of ACL config";
            }
            list acl-ingress-compress-enable-location-leaf {
              key "location-id";
              description
                "none";
              leaf location-id {
                type uint32;
                description
                  "Location ID";
              }
              leaf enable-val {
                type uint32;
                mandatory true;
                description
                  "If Enabled set value to 65535";
              }
            }
          }
        }
        container ipv6-etcam-acl-rif-based-locations {
          description
            "ingress ipv6 etcam acl rif based";
          list ipv6-etcam-acl-rif-based-location {
            key "location-string";
            description
              "none";
            leaf location-string {
              type xr:Cisco-ios-xr-string;
              description
                "Location of ACL config";
            }
            list ipv6-etcam-acl-rif-based-location-leaf {
              key "location-id";
              description
                "none";
              leaf location-id {
                type uint32;
                description
                  "Location ID";
              }
              leaf enable-val {
                type uint32;
                mandatory true;
                description
                  "If Enabled set value to 65535";
              }
            }
          }
        }
        container ipv6-etcam-acl-rif-based-location-all {
          description
            "ipv6 etcam acl rif based location all";
          leaf ipv6-etcam-acl-rif-based-location-all-leaf {
            type uint32;
            description
              "ipv6 etcam acl rif based location all";
          }
        }
        container ipv4-etcam-acl-rif-based-location-all {
          description
            "ipv4 etcam acl rif based location all";
          leaf ipv4-etcam-acl-rif-based-location-all-leaf {
            type uint32;
            description
              "ipv4 etcam acl rif based location all";
          }
        }
        container ipv4-etcam-acl-rif-based-locations {
          description
            "ingress ipv4 etcam acl rif based";
          list ipv4-etcam-acl-rif-based-location {
            key "location-string";
            description
              "none";
            leaf location-string {
              type xr:Cisco-ios-xr-string;
              description
                "Location of ACL config";
            }
            list ipv4-etcam-acl-rif-based-location-leaf {
              key "location-id";
              description
                "none";
              leaf location-id {
                type uint32;
                description
                  "Location ID";
              }
              leaf enable-val {
                type uint32;
                mandatory true;
                description
                  "If Enabled set value to 65535";
              }
            }
          }
        }
        container acl-ingress-compress-enable-location-all {
          description
            "ingress compress enable location all";
          leaf acl-ingress-compress-enable-location-all-leaf {
            type uint32;
            description
              "ingress compress enable location all";
          }
        }
        leaf egress {
          type boolean;
          description
            "Enabled or disabled";
        }
        leaf ipv6-ext-hdr {
          type boolean;
          description
            "IPv6 Extension Hdr Permit";
        }
      }
      container sr-policies {
        description
          "Configure IPV6 NULL label autopush for SR
           policy.";
        list sr-policy {
          key "null-label-autopush";
          description
            "none";
          leaf null-label-autopush {
            type xr:Cisco-ios-xr-string;
            description
              "none";
          }
          leaf enable-val {
            type uint32;
            mandatory true;
            description
              "If Enabled set value to 1";
          }
        }
      }
      container npu-native-mode-enable {
        description
          "Configure NPU to work in Native Mode.";
        leaf enable {
          type boolean;
          description
            "NPU Native Mode Enable value";
        }
      }
      container bundle-scale {
        description
          "Configure Bundle profile.";
        leaf trunk-size {
          type uint32;
          description
            "Configure Max Trunk Size";
        }
      }
      container profile-tcam {
        description
          "Configure Tcam Profile";
        container key-format {
          description
            "none";
          container key-format-acl-table {
            description
              "Configure acl profile";
            container ipv6-acl-tables {
              description
                "Configure ipv6 acl profile";
              list ipv6-acl-table {
                key "location-string location-id";
                description
                  "Configure format for ipv6 acl profile";
                leaf location-string {
                  type xr:Cisco-ios-xr-string;
                  description
                    "Location string (all) if for all LCs";
                }
                leaf location-id {
                  type uint32;
                  description
                    "Location ID hex to Decimal 0xffff for all";
                }
                leaf source-addr {
                  type uint32;
                  description
                    "Source Address";
                }
                leaf source-port {
                  type uint32;
                  description
                    "Source Port";
                }
                leaf destination-addr {
                  type uint32;
                  description
                    "Destination Address";
                }
                leaf dest-port {
                  type uint32;
                  description
                    "Destination Port";
                }
                leaf next-hdr {
                  type uint32;
                  description
                    "Next Header Type";
                }
                leaf tcp-flag {
                  type uint32;
                  description
                    "TCP Flags";
                }
                leaf payload-len {
                  type uint32;
                  description
                    "Payload Length";
                }
                leaf traff-class {
                  type uint32;
                  description
                    "Traffic Class";
                }
                leaf udf1 {
                  type string;
                  description
                    "UDF name";
                }
                leaf udf2 {
                  type string;
                  description
                    "UDF name";
                }
                leaf udf3 {
                  type string;
                  description
                    "UDF name";
                }
                leaf udf4 {
                  type string;
                  description
                    "UDF name";
                }
                leaf udf5 {
                  type string;
                  description
                    "UDF name";
                }
                leaf udf6 {
                  type string;
                  description
                    "UDF name";
                }
                leaf udf7 {
                  type string;
                  description
                    "UDF name";
                }
                leaf udf8 {
                  type string;
                  description
                    "UDF name";
                }
                leaf en-capture {
                  type uint32;
                  description
                    "Enable Capture";
                }
                leaf en-ttl {
                  type uint32;
                  description
                    "Enable Setting TTL";
                }
                leaf en-match {
                  type uint32;
                  description
                    "Enable Matching TTL";
                }
                leaf en-share-acl {
                  type uint32;
                  description
                    "Enable Non Shared Interface ACL";
                }
                leaf common-acl {
                  type uint32;
                  description
                    "Enable Common-ACL";
                }
              }
            }
            container ipv4-acl-tables {
              description
                "Configure ipv4 acl profile";
              list ipv4-acl-table {
                key "location-string location-id";
                description
                  "Configure format for ipv4 acl profile";
                leaf location-string {
                  type xr:Cisco-ios-xr-string;
                  description
                    "Location string (all) if for all LCs";
                }
                leaf location-id {
                  type uint32;
                  description
                    "Location ID hex to Decimal 0xffff for all";
                }
                leaf source-addr {
                  type uint32;
                  description
                    "Source Address";
                }
                leaf destination-addr {
                  type uint32;
                  description
                    "Destination Address";
                }
                leaf source-port {
                  type uint32;
                  description
                    "Source Port";
                }
                leaf dest-port {
                  type uint32;
                  description
                    "Destination Port";
                }
                leaf prot-type {
                  type uint32;
                  description
                    "Protocol Type";
                }
                leaf tcp-flag {
                  type uint32;
                  description
                    "TCP Flags";
                }
                leaf pack-len {
                  type uint32;
                  description
                    "Packet Length";
                }
                leaf frag-bit {
                  type uint32;
                  description
                    "Fragment Bit";
                }
                leaf precedence {
                  type uint32;
                  description
                    "Precedence";
                }
                leaf port-range {
                  type uint32;
                  description
                    "PortRange";
                }
                leaf udf1 {
                  type string;
                  description
                    "UDF name";
                }
                leaf udf2 {
                  type string;
                  description
                    "UDF name";
                }
                leaf udf3 {
                  type string;
                  description
                    "UDF name";
                }
                leaf udf4 {
                  type string;
                  description
                    "UDF name";
                }
                leaf udf5 {
                  type string;
                  description
                    "UDF name";
                }
                leaf udf6 {
                  type string;
                  description
                    "UDF name";
                }
                leaf udf7 {
                  type string;
                  description
                    "UDF name";
                }
                leaf udf8 {
                  type string;
                  description
                    "UDF name";
                }
                leaf en-capture {
                  type uint32;
                  description
                    "Enable Capture";
                }
                leaf en-ttl {
                  type uint32;
                  description
                    "Enable Setting TTL";
                }
                leaf en-match {
                  type uint32;
                  description
                    "Enable Matching TTL";
                }
                leaf en-share-acl {
                  type uint32;
                  description
                    "Enable Non Shared Interface ACL";
                }
                leaf common-acl {
                  type uint32;
                  description
                    "Enable Common-ACL";
                }
              }
            }
          }
        }
      }
      container offload {
        description
          "Configure offload profile for NCS5501-SE";
        leaf offload-profile {
          type uint32;
          description
            "Configure offload profile for NCS5501-SE";
        }
      }
      container igp-dlb {
        description
          "configure igp_dlb";
        leaf enable {
          type boolean;
          description
            "fib dlb level-1 value";
        }
      }
      container qos {
        description
          "Configure profile.";
        container hqos-enable-all {
          description
            "Configure Hqos profile";
          leaf hqos-enable {
            type uint32;
            description
              " Hqos profile value";
          }
        }
        container ingress-model-root-def {
          description
            "Configure Ingress Model Default";
          leaf ingress-model-leaf-def {
            type uint32;
            description
              "Ingress Model Default";
          }
        }
        container ingress-models {
          description
            "Configure Ingress Model Root";
          list ingress-model {
            key "node-name";
            description
              "Configure Ingress Model";
            leaf node-name {
              type xr:Cisco-ios-xr-string;
              description
                "NodeName";
            }
            list ingress-model-leaf {
              key "location";
              description
                "Configure Ingress Model Leaf";
              leaf ingress-model-leaf {
                type uint32;
                mandatory true;
                description
                  "IngressModelLeaf";
              }
              leaf location {
                type uint32;
                description
                  "Location";
              }
            }
          }
        }
        container class-maps-root-def {
          description
            "Configure Class Maps Default";
          leaf class-map-size-def {
            type uint32;
            description
              "Class Map Size Default";
          }
        }
        container physical-hqos-enable-all {
          description
            "Configure physical intf Hqos profile";
          leaf physical-hqos-enable {
            type boolean;
            description
              " Physical Hqos profile value";
          }
        }
        container class-maps {
          description
            "Configure Class Map Root";
          list class-map {
            key "node-name";
            description
              "Configure Class Maps";
            leaf node-name {
              type xr:Cisco-ios-xr-string;
              description
                "NodeName";
            }
            list class-map-size {
              key "location";
              description
                "Class Map Size";
              leaf class-map-size {
                type uint32;
                mandatory true;
                description
                  "ClassMapSize";
              }
              leaf location {
                type uint32;
                description
                  "Location";
              }
            }
          }
        }
      }
      container oam {
        description
          "Configure oam sat profile.";
        leaf sat-enable {
          type boolean;
          description
            "Oam SAT enable value";
        }
      }
    }
    container fib-scale {
      description
        "Configure Fib for Scale for noTcam LC.";
      container ipv6-unicast-scale-no-tcam {
        description
          "IPv6 table for NOTCAM LC Scale.";
        container scale-ipv6-no-tcam {
          description
            "Scale for IPv6 table for NoTCAM LC.";
          leaf internet-optimized-ipv6-no-tcam {
            type string;
            description
              "Internet-optimized Scale for IPv6 table for
               NoTCAM LC.";
          }
        }
      }
      container ipv4-unicast-scale-no-tcam {
        description
          "IPv4 table for NOTCAM LC Scale.";
        container scale-ipv4-no-tcam {
          description
            "Scale for IPv4 table for NoTCAM LC.";
          leaf optimized-ipv4-no-tcam {
            type string;
            description
              "Optimized Scale for IPv4 table for NoTCAM LC.";
          }
        }
      }
    }
    container orchestrated-linecard-reload {
      description
        "Configure OLR.";
      container plane-table-entries {
        description
          "Plane type";
        list plane-table-entry {
          key "plane-name";
          description
            "Plane : A or B";
          container rack-table-entries {
            description
              "Rack Information";
            list rack-table-entry {
              key "rack-num";
              description
                "Rack Number";
              leaf nodes-list {
                type string;
                description
                  "Please enter linecards separated via comma
                   eg 0,3,6,11,13";
              }
              leaf rack-num {
                type Plane-rack;
                description
                  "Rack Number";
              }
            }
          }
          leaf plane-name {
            type xr:Cisco-ios-xr-string;
            description
              "Plane Name";
          }
        }
      }
    }
    container tcam {
      description
        "Configure Tcam.";
      container fib-tcam-scale {
        description
          "Configure Fib scale for Tcam.";
        container ipv4-unicast-scale {
          description
            "IPv4 table for TCAM LC Scale.";
          leaf ipv4-scale {
            type boolean;
            description
              "Scale for IPv4 table for TCAM LC.";
          }
        }
      }
    }
    container vrrp-scale {
      description
        "Configure vrrpscale profile.";
      leaf enable {
        type boolean;
        description
          "vrrpscale profile value";
      }
    }
    container qosqppb {
      description
        "Configure profile.";
      container ipv6-scale {
        description
          "Configure IPv6 destination short profile";
        leaf ipv6-short {
          type boolean;
          description
            "ipv6 short profile value";
        }
      }
      leaf conform-aware-policer {
        type boolean;
        description
          "Configure Conform Aware Policer mode";
      }
    }
  }
}
