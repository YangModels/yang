module Cisco-IOS-XR-sysadmin-fabric-groups {
  namespace "http://www.cisco.com/ns/yang/Cisco-IOS-XR-sysadmin-fabric-groups";
  prefix fabric-groups;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains definitions
     for the Calvados model objects.
     
     Copyright (c) 2012-2020 by Cisco Systems, Inc.
     All rights reserved.";

  revision 2019-04-15 {
    description
      "Establish semantic version baseline.";
    semver:module-version "1.0.1";
  }
  revision 2017-05-01 {
    description
      "Namespace change to comply with Cisco guidelines on namespace";
  }

  grouping location {
    list location {
      key "loc_str";
      leaf loc_str {
        type string;
      }
    }
  }

  grouping asic_instance {
    list instance {
      key "instance-id";
      leaf instance-id {
        type string {
          pattern "[0-2]|all";
        }
      }
    }
  }

  grouping link_stats_instance {
    container stats {
      container data {
        uses asic_instance;
      }
      container ctrl {
        uses asic_instance;
      }
      container all {
        uses asic_instance;
      }
    }
  }

  grouping fabric_instance_location {
    list instance {
      key "instance-id";
      leaf instance-id {
        type string {
          pattern "[0-2]|all";
        }
      }
      uses location;
    }
  }
}
