module Cisco-IOS-XR-roe-oper {
  namespace "http://cisco.com/ns/yang/Cisco-IOS-XR-roe-oper";
  prefix roe-oper;

  import cisco-semver {
    prefix semver;
  }
  include Cisco-IOS-XR-roe-oper-sub1 {
    revision-date 2020-02-27;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR roe package operational data.
     
     This module contains definitions
     for the following management objects:
       roe: ROE Operational Data
     
     Copyright (c) 2013-2020 by Cisco Systems, Inc.
     All rights reserved.";

  revision 2020-02-27 {
    description
      "Show command subtype added for ROE";
    semver:module-version "1.0.0";
  }
  revision 2019-04-05 {
    description
      "Establish semantic version baseline.";
  }
  revision 2015-11-09 {
    description
      "IOS XR 6.0 revision.";
  }

  container roe {
    config false;
    description
      "ROE Operational Data";
    container profiles {
      description
        "List of ROE profiles configured";
      list profile {
        key "profile-id";
        description
          "ROE profile parameters";
        leaf profile-id {
          type uint32;
          description
            "Profile identifier";
        }
        uses ROE-PROFILE-INFO;
      }
    }
    container ethlinks {
      description
        "List of ROE ethlink profiles configured";
      list ethlink {
        key "ethlink-id";
        description
          "ROE Eth link profile parameters";
        leaf ethlink-id {
          type uint32;
          description
            "Ethlink identifier";
        }
        uses ROE-ETHLINK-INFO;
      }
    }
    container protocol-stats {
      description
        "ROE management plane protocol statistics";
      uses ROE-PROTOCOL-STATS;
    }
  }
}
