module Cisco-IOS-XR-pbr-oper {

  /*** NAMESPACE / PREFIX DEFINITION ***/

  namespace "http://cisco.com/ns/yang/Cisco-IOS-XR-pbr-oper";


  prefix "pbr-oper";

  /*** LINKAGE (IMPORTS / INCLUDES) ***/

  import Cisco-IOS-XR-types { prefix "xr"; }

  include Cisco-IOS-XR-pbr-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR pbr package operational data.

     This module contains definitions
     for the following management objects:
       pbr: PBR operational data

     Copyright (c) 2013-2015 by Cisco Systems, Inc.
     All rights reserved.";

  revision "2015-11-09" {
    description
      "IOS XR 6.0 revision.";
  }


  container pbr {
    xr:xr-xml-map "pbr_ma_oper:PBR";
    config false;
    description "PBR operational data";

    container nodes {
      xr:xr-xml-map "pbr_ma_oper:NodeTable";
      description "Node-specific PBR operational data";

      list node {
        xr:xr-xml-map "pbr_ma_oper:Node";
        key "node-name";
        description "PBR operational data for a particular node";

        container policy-map {
          xr:xr-xml-map "pbr_ma_oper:PolicyMap";
          description "Operational data for policymaps";

          container interfaces {
            xr:xr-xml-map "pbr_ma_oper:InterfaceTable";
            description "Operational data for all interfaces";

            list interface {
              xr:xr-xml-map "pbr_ma_oper:Interface";
              key "interface-name";
              description
                "PBR action data for a particular interface";

              container direction {
                xr:xr-xml-map "pbr_ma_oper:Direction";
                description "PBR direction";

                container input {
                  xr:xr-xml-map "pbr_ma_oper:Input";
                  description "PBR policy statistics";
                  uses PBR-STATS;
                }
              }
              leaf interface-name {
                xr:xr-xml-map "pbr_ma_oper:InterfaceName";
                type xr:Interface-name;
                description "Name of the interface";
              }
            }
          }
        }
        leaf node-name {
          xr:xr-xml-map "pbr_ma_oper:NodeName";
          type xr:Node-id;
          description "The node";
        }
      }
    }
  }
}
