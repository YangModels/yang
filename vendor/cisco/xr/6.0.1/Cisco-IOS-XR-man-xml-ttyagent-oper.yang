module Cisco-IOS-XR-man-xml-ttyagent-oper {

  /*** NAMESPACE / PREFIX DEFINITION ***/

  namespace "http://cisco.com/ns/yang"+
    "/Cisco-IOS-XR-man-xml-ttyagent-oper";


  prefix "man-xml-ttyagent-oper";

  /*** LINKAGE (IMPORTS / INCLUDES) ***/

  import Cisco-IOS-XR-types { prefix "xr"; }

  include Cisco-IOS-XR-man-xml-ttyagent-oper-sub1 {
    revision-date 2015-07-30;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR man-xml-ttyagent package operational data.

     This module contains definitions
     for the following management objects:
       netconf: NETCONF operational information
       xr-xml: xr xml

     Copyright (c) 2013-2015 by Cisco Systems, Inc.
     All rights reserved.";

  revision "2015-07-30" {
    description
      "Descriptions updated.";
  }

  revision "2015-01-07" {
    description
      "IOS XR 5.3.1 revision.";
  }


  grouping SESSION-TABLE {
    description "Common node of default, tty, ssl";

    container sessions {
      xr:xr-xml-map "xml_oper:SessionTable";
      description "sessions information";

      list session {
        xr:xr-xml-map "xml_oper:Session";
        key "session-id";
        description "xml sessions information";
        leaf session-id {
          xr:xr-xml-map "xml_oper:SessionID";
          type int32;
          description "Session Id";
        }
        uses XR-XML-SESSION-INFO;
      }
    }
  }

  container netconf {
    xr:xr-xml-map "netconf_agent_oper:NETCONF";
    config false;
    description "NETCONF operational information";

    container agent {
      xr:xr-xml-map "netconf_agent_oper:Agent";
      description "NETCONF agent operational information";

      container tty {
        xr:xr-xml-map "netconf_agent_oper:TTY";
        description "NETCONF agent over TTY";

        container sessions {
          xr:xr-xml-map "netconf_agent_oper:SessionTable";
          description "Session information";

          list session {
            xr:xr-xml-map "netconf_agent_oper:Session";
            key "session-id";
            description "Session information";
            leaf session-id {
              xr:xr-xml-map "netconf_agent_oper:SessionID";
              type int32;
              description "Session ID";
            }
            uses XR-XML-SESSION-INFO;
          }
        }
      }
    }
  }

  container xr-xml {
    xr:xr-xml-map "xml_oper:XML";
    config false;
    description "xr xml";

    container agent {
      xr:xr-xml-map "xml_oper:Agent";
      description "XML agents";

      container tty {
        xr:xr-xml-map "xml_oper:TTY";
        description "TTY sessions information";
        uses SESSION-TABLE;
      }

      container default {
        xr:xr-xml-map "xml_oper:Default";
        description "Default sessions information";
        uses SESSION-TABLE;
      }

      container ssl {
        xr:xr-xml-map "xml_oper:SSL";
        description "SSL sessions information";
        uses SESSION-TABLE;
      }
    }
  }
}
