submodule Cisco-IOS-XR-mpls-ldp-oper-sub1 {

  belongs-to Cisco-IOS-XR-mpls-ldp-oper {
    prefix Cisco-IOS-XR-mpls-ldp-oper;
  }

  /*** LINKAGE (IMPORTS / INCLUDES) ***/

  import ietf-inet-types { prefix "inet"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR mpls-ldp package operational data.

     Copyright (c) 2013-2015 by Cisco Systems, Inc.
     All rights reserved.";

  revision "2015-11-09" {
    description
      "IOS XR 6.0 revision.";
  }

  typedef Mgmt-ldp-nbr-bgp-advt-state {
    type enumeration {
      enum not-applicable {
        value 0;
        description "Not applicable";
      }
      enum permit {
        value 1;
        description "Advertisement permitted";
      }
      enum deny {
        value 2;
        description "Advertisement denied";
      }
    }
    description
      "MPLS LDP Neighbor BGP Label Advertisement State
      Type";
  }
  typedef Mgmt-ldp-nsr-peer-ldp-sync-nack-rsn {
    type enumeration {
      enum mgmt-ldp-nsr-peer-ldp-sync-nack-rsn-none {
        description "mgmt ldp nsr peer ldp sync nack rsn none";
      }
      enum mgmt-ldp-nsr-peer-ldp-sync-nack-rsn-tbl-id-mismatch {
        description
          "mgmt ldp nsr peer ldp sync nack rsn tbl id
          mismatch";
      }
      enum mgmt-ldp-nsr-peer-ldp-sync-nack-rsn-pp-exists {
        description "mgmt ldp nsr peer ldp sync nack rsn pp exists";
      }
      enum mgmt-ldp-nsr-peer-ldp-sync-nack-rsn-missing-elem {
        description
          "mgmt ldp nsr peer ldp sync nack rsn missing
          elem";
      }
      enum mgmt-ldp-nsr-peer-ldp-sync-nack-rsn-no-p-end-sock {
        description
          "mgmt ldp nsr peer ldp sync nack rsn no p end
          sock";
      }
      enum "mgmt-ldp-nsr-peer-ldp-sync-nack-rsn-p-end-sock-not"+
        "-synced" {
        description
          "mgmt ldp nsr peer ldp sync nack rsn p end sock
          not synced";
      }
      enum mgmt-ldp-nsr-peer-ldp-sync-nack-rsn-err-adj-add {
        description
          "mgmt ldp nsr peer ldp sync nack rsn err adj add";
      }
      enum mgmt-ldp-nsr-peer-ldp-sync-nack-rsn-err-dhcb-add {
        description
          "mgmt ldp nsr peer ldp sync nack rsn err dhcb
          add";
      }
      enum mgmt-ldp-nsr-peer-ldp-sync-nack-rsn-enomem {
        description "mgmt ldp nsr peer ldp sync nack rsn enomem";
      }
      enum mgmt-ldp-nsr-peer-ldp-sync-nack-rsn-err-tp-create {
        description
          "mgmt ldp nsr peer ldp sync nack rsn err tp
          create";
      }
      enum mgmt-ldp-nsr-peer-ldp-sync-nack-rsn-err-pp-create {
        description
          "mgmt ldp nsr peer ldp sync nack rsn err pp
          create";
      }
      enum mgmt-ldp-nsr-peer-ldp-sync-nack-rsn-err-addr-bind {
        description
          "mgmt ldp nsr peer ldp sync nack rsn err addr
          bind";
      }
      enum mgmt-ldp-nsr-peer-ldp-sync-nack-rsn-err-rx-bad-pie {
        description
          "mgmt ldp nsr peer ldp sync nack rsn err rx bad
          pie";
      }
      enum mgmt-ldp-nsr-peer-ldp-sync-nack-rsn-err-rx-notif {
        description
          "mgmt ldp nsr peer ldp sync nack rsn err rx
          notif";
      }
      enum mgmt-ldp-nsr-peer-ldp-sync-nack-rsn-err-rx-unexp-open {
        description
          "mgmt ldp nsr peer ldp sync nack rsn err rx
          unexp open";
      }
      enum mgmt-ldp-nsr-peer-ldp-sync-nack-rsn-err-unexp-peer-down {
        description
          "mgmt ldp nsr peer ldp sync nack rsn err unexp
          peer down";
      }
      enum mgmt-ldp-nsr-peer-ldp-sync-nack-rsn-err-app-not-found {
        description
          "mgmt ldp nsr peer ldp sync nack rsn err app not
          found";
      }
      enum mgmt-ldp-nsr-peer-ldp-sync-nack-rsn-err-app-invalid {
        description
          "mgmt ldp nsr peer ldp sync nack rsn err app
          invalid";
      }
      enum "mgmt-ldp-nsr-peer-ldp-sync-nack-rsn-err-adj-grp-not"+
        "-found" {
        description
          "mgmt ldp nsr peer ldp sync nack rsn err adj grp
          not found";
      }
      enum mgmt-ldp-nsr-peer-ldp-sync-nack-rsn-invalid-elem {
        description
          "mgmt ldp nsr peer ldp sync nack rsn invalid
          elem";
      }
      enum "mgmt-ldp-nsr-peer-ldp-sync-nack-rsn-err-app-data"+
        "-invalid" {
        description
          "mgmt ldp nsr peer ldp sync nack rsn err app
          data invalid";
      }
      enum mgmt-ldp-nsr-peer-ldp-sync-nack-rsn-err-invalid-per-idx {
        description
          "mgmt ldp nsr peer ldp sync nack rsn err invalid
          per idx";
      }
      enum mgmt-ldp-nsr-peer-ldp-sync-nack-rsn-err-pfx-not-found {
        description
          "mgmt ldp nsr peer ldp sync nack rsn err pfx not
          found";
      }
      enum mgmt-ldp-nsr-peer-ldp-sync-nack-rsn-err-bm-size-invalid {
        description
          "mgmt ldp nsr peer ldp sync nack rsn err bm size
          invalid";
      }
      enum mgmt-ldp-nsr-peer-ldp-sync-nack-rsn-err-adv-bm-clear {
        description
          "mgmt ldp nsr peer ldp sync nack rsn err adv bm
          clear";
      }
      enum "mgmt-ldp-nsr-peer-ldp-sync-nack-rsn-err-tcp-struct"+
        "-create" {
        description
          "mgmt ldp nsr peer ldp sync nack rsn err tcp
          struct create";
      }
      enum mgmt-ldp-nsr-peer-ldp-sync-nack-rsn-no-ctx {
        description "mgmt ldp nsr peer ldp sync nack rsn no ctx";
      }
    }
    description "Mgmt ldp nsr peer ldp sync nack rsn";
  }
  typedef Mgmt-ldp-nsr-peer-sync-err {
    type enumeration {
      enum mgmt-ldp-nsr-peer-sync-err-none {
        description "mgmt ldp nsr peer sync err none";
      }
      enum mgmt-ldp-nsr-peer-sync-err-ldp-sync-nack {
        description "mgmt ldp nsr peer sync err ldp sync nack";
      }
      enum mgmt-ldp-nsr-peer-sync-err-sync-prep {
        description "mgmt ldp nsr peer sync err sync prep";
      }
      enum mgmt-ldp-nsr-peer-sync-err-tcp-peer {
        description "mgmt ldp nsr peer sync err tcp peer";
      }
      enum mgmt-ldp-nsr-peer-sync-err-tcp-gbl {
        description "mgmt ldp nsr peer sync err tcp gbl";
      }
      enum mgmt-ldp-nsr-peer-sync-err-ldp-peer {
        description "mgmt ldp nsr peer sync err ldp peer";
      }
      enum mgmt-ldp-nsr-peer-sync-err-ldp-gbl {
        description "mgmt ldp nsr peer sync err ldp gbl";
      }
      enum mgmt-ldp-nsr-peer-sync-err-app-fail {
        description "mgmt ldp nsr peer sync err app fail";
      }
      enum mgmt-ldp-nsr-peer-sync-err-sync-tcp-phase1 {
        description "mgmt ldp nsr peer sync err sync tcp phase1";
      }
      enum mgmt-ldp-nsr-peer-sync-err-sync-tcp-phase2 {
        description "mgmt ldp nsr peer sync err sync tcp phase2";
      }
    }
    description "Mgmt ldp nsr peer sync err";
  }
  typedef Mgmt-ldp-nsr-peer-sync-state {
    type enumeration {
      enum mgmt-ldp-nsr-peer-sync-st-none {
        description "mgmt ldp nsr peer sync st none";
      }
      enum mgmt-ldp-nsr-peer-sync-st-wait {
        description "mgmt ldp nsr peer sync st wait";
      }
      enum mgmt-ldp-nsr-peer-sync-st-ready {
        description "mgmt ldp nsr peer sync st ready";
      }
      enum mgmt-ldp-nsr-peer-sync-st-prep {
        description "mgmt ldp nsr peer sync st prep";
      }
      enum mgmt-ldp-nsr-peer-sync-st-app-wait {
        description "mgmt ldp nsr peer sync st app wait";
      }
      enum mgmt-ldp-nsr-peer-sync-st-oper {
        description "mgmt ldp nsr peer sync st oper";
      }
      enum mgmt-ldp-nsr-peer-sync-st-tcp-phase1 {
        description "mgmt ldp nsr peer sync st tcp phase1";
      }
      enum mgmt-ldp-nsr-peer-sync-st-tcp-phase2 {
        description "mgmt ldp nsr peer sync st tcp phase2";
      }
    }
    description "Mgmt ldp nsr peer sync state";
  }
  typedef Ldp-adj-union-discrim {
    type enumeration {
      enum link-hello {
        description "Link hello";
      }
      enum targeted-hello {
        description "Targeted hello";
      }
    }
    description "MPLS LDP Hello Type";
  }
  typedef Show-nsr-state {
    type enumeration {
      enum nsr-ready {
        description "NSR ready";
      }
      enum nsr-not-ready {
        description "NSR not ready";
      }
      enum nsr-na {
        description "NSR not applicable";
      }
    }
    description "NSR State Type";
  }
  typedef Ldp-route-path-lbl-owner {
    type enumeration {
      enum ip-path-lbl-owner-none {
        value 0;
        description "No label and no owner";
      }
      enum ip-path-lbl-owner-ldp {
        value 1;
        description "Path outgoing label owned by LDP";
      }
      enum ip-path-lbl-owner-bgp {
        value 2;
        description "Path outgoing label owned by BGP";
      }
    }
    description "Route path label owner";
  }
  typedef Label-value {
    type enumeration {
      enum mpls-label {
        description "MPLS Label";
      }
      enum un-labelled {
        description "Unlabelled";
      }
      enum unknown {
        description "Unknown label";
      }
    }
    description "Label Value Type";
  }
  typedef Ldp-fwd-unlbl-rsn {
    type enumeration {
      enum ldp-fwd-labelled {
        description "ldp fwd labelled";
      }
      enum ldp-fwd-un-labelled-vrf-down {
        description "ldp fwd un labelled vrf down";
      }
      enum ldp-fwd-un-labelled-no-nh {
        description "ldp fwd un labelled no nh";
      }
      enum ldp-fwd-un-labelled-recursive-path {
        description "ldp fwd un labelled recursive path";
      }
      enum ldp-fwd-un-labelled-intf-not-ldp {
        description "ldp fwd un labelled intf not ldp";
      }
      enum ldp-fwd-un-labelled-no-rmt {
        description "ldp fwd un labelled no rmt";
      }
      enum ldp-fwd-un-labelled-no-ldp-adj {
        description "ldp fwd un labelled no ldp adj";
      }
      enum ldp-fwd-un-labelled-no-session {
        description "ldp fwd un labelled no session";
      }
      enum ldp-fwd-un-labelled-unknown {
        description "ldp fwd un labelled unknown";
      }
    }
    description "Ldp fwd unlbl rsn";
  }
  typedef Ldp-route-path-flags {
    type enumeration {
      enum ip-path-no-flag {
        value 0;
        description "A primary path with no special flag/attribute";
      }
      enum ip-path-protected {
        value 1;
        description "A primary path with LFA FRR protection";
      }
      enum ip-path-backup {
        value 2;
        description
          "A non-primary local LFA FRR (pure) backup path";
      }
      enum ip-path-backup-remote {
        value 3;
        description
          "A non-primary remote LFA FRR (pure) backup path";
      }
      enum ip-path-bgp-backup {
        value 4;
        description "A non-primary BGP backup path";
      }
    }
    description "Route path flags";
  }
  typedef Dhcb-state {
    type enumeration {
      enum none {
        description "None";
      }
      enum dhcb-active {
        description "Active";
      }
      enum dhcb-passive {
        description "Passive";
      }
      enum dhcb-active-passive {
        description "Active and Passive";
      }
    }
    description "DHCB State Type";
  }
  typedef Ldp-igp-sync-down-reason {
    type enumeration {
      enum igp-sync-down-reason-not-applicable {
        description "Not Applicable";
      }
      enum no-hello-adjacency {
        description "No hello adjacency";
      }
      enum no-peer-session {
        description "No peer session";
      }
      enum initial-update-to-peer-not-done {
        description "Initial update to peer not done yet";
      }
      enum initial-update-from-peer-not-received {
        description "Initial update from peer not received yet";
      }
      enum internal-reason {
        description "Internal reason";
      }
    }
    description "Reason IGP Sync Not Achieved";
  }
  typedef String-td2 {
    type string;
    description "String td2";
  }
  typedef Ldp-igp-sync-state {
    type enumeration {
      enum isync-ready {
        description "Acheived";
      }
      enum isync-not-ready {
        description "Not acheived";
      }
      enum isync-deferred {
        description
          "Deferred due to interface delay or global
          restart delay";
      }
    }
    description "IGP Sync State";
  }
  typedef Local-label-state {
    type enumeration {
      enum local-label-state-none {
        value 1;
        description "None";
      }
      enum local-label-state-assigned {
        value 2;
        description "Assigned";
      }
      enum local-label-state-withdrawn {
        value 3;
        description "Withdrawn";
      }
    }
    description "MPLS LDP Local Label State Type";
  }
  typedef Ldp-af {
    type enumeration {
      enum ldp-show-af-none {
        value 0;
        description "No Address Family";
      }
      enum ldp-show-af-ipv4 {
        value 1;
        description "IPv4 AFI";
      }
      enum ldp-show-af-ipv6 {
        value 2;
        description "IPv6 AFI";
      }
      enum ldp-show-af-ipv4-ipv6 {
        value 3;
        description "Both IPv4/IPv6 AFIs";
      }
    }
    description "Ldp af";
  }
  typedef Ldp-in6-addr {
    type inet:ipv6-address;
    description "Ldp in6 addr";
  }
  typedef Ldp-in-addr {
    type inet:ipv4-address;
    description "Ldp in addr";
  }
  typedef Ldp-af-id {
    type enumeration {
      enum ldp-af-id-none {
        value 0;
        description "No Address Family";
      }
      enum ldp-af-id-ipv4 {
        value 2;
        description "IPv4 AFI";
      }
      enum ldp-af-id-ipv6 {
        value 10;
        description "IPv6 AFI";
      }
    }
    description "Ldp af id";
  }

  grouping LDP-SUMMARY {
    description "MPLS LDP Summarized Information";

    container common {
      description "Common Summary information";
      uses LDP-SUMMARY-COMMON;
    }
    leaf number-of-vrf {
      xr:xr-xml-map "mpls_ldp_oper_data:NumberOfVRF";
      type uint32;
      description "Number of configured VRFs (including default)";
    }
    leaf number-of-vrf-oper {
      xr:xr-xml-map "mpls_ldp_oper_data:NumberOfVRFOper";
      type uint32;
      description
        "Number of configured operational VRFs (including
        default)";
    }
    leaf number-of-interfaces {
      xr:xr-xml-map "mpls_ldp_oper_data:NumberOfInterfaces";
      type uint32;
      description "Number of known interfaces";
    }
    leaf number-of-fwd-ref-interfaces {
      xr:xr-xml-map "mpls_ldp_oper_data:NumberOfFwdRefInterfaces";
      type uint32;
      description "Number of Forward Referenc interfaces";
    }
    leaf number-of-autocfg-interfaces {
      xr:xr-xml-map "mpls_ldp_oper_data:NumberOfAutocfgInterfaces";
      type uint32;
      description "Number of auto-configured interfaces";
    }
    leaf is-bound-with-sysdb {
      xr:xr-xml-map "mpls_ldp_oper_data:IsBoundWithSysdb";
      type boolean;
      description "Bound status with sysdb";
    }
    leaf is-registered-with-sysdb {
      xr:xr-xml-map "mpls_ldp_oper_data:IsRegisteredWithSysdb";
      type boolean;
      description "Registration status with Sysdb";
    }
    leaf is-bound-with-rsi {
      xr:xr-xml-map "mpls_ldp_oper_data:IsBoundWithRsi";
      type boolean;
      description "Bound status with rsi";
    }
    leaf is-bound-with-interface-manager {
      xr:xr-xml-map "mpls_ldp_oper_data:IsBoundWithInterfaceManager";
      type boolean;
      description "Bound status with Interface Manager";
    }
    leaf is-registered-with-interface-manager {
      xr:xr-xml-map "mpls_ldp_oper_data:IsRegisteredWithInterfaceMa"+
        "nager";
      type boolean;
      description "Registration status with Interface Manager";
    }
    leaf is-bound-with-ip-arm {
      xr:xr-xml-map "mpls_ldp_oper_data:IsBoundWithIPArm";
      type boolean;
      description "Bound status with IP Arm";
    }
    leaf is-bound-with-lsd {
      xr:xr-xml-map "mpls_ldp_oper_data:IsBoundWithLSD";
      type boolean;
      description "Bound status with LSD";
    }
    leaf is-registered-with-lsd {
      xr:xr-xml-map "mpls_ldp_oper_data:IsRegisteredWithLSD";
      type boolean;
      description "Registration status with LSD";
    }
    leaf is-bound-with-ipv4-rib {
      xr:xr-xml-map "mpls_ldp_oper_data:IsBoundWithIPv4_RIB";
      type boolean;
      description "Bound status with IPv4 RIB";
    }
    leaf is-registered-with-ipv4-rib {
      xr:xr-xml-map "mpls_ldp_oper_data:IsRegisteredWithIPv4_RIB";
      type boolean;
      description "Registration status with IPv4 RIB";
    }
    leaf number-of-ipv4rib-tables {
      xr:xr-xml-map "mpls_ldp_oper_data:NumberOfIPv4RIBTables";
      type uint32;
      description "Total number of ipv4 RIB tables";
    }
    leaf number-of-registered-ipv4rib-tables {
      xr:xr-xml-map "mpls_ldp_oper_data:NumberOfRegisteredIPv4RIBTa"+
        "bles";
      type uint32;
      description "Number of ipv4 RIB tables registered";
    }
    leaf is-bound-with-ipv6-rib {
      xr:xr-xml-map "mpls_ldp_oper_data:IsBoundWithIPv6_RIB";
      type boolean;
      description "Bound status with IPv6 RIB";
    }
    leaf is-registered-with-ipv6-rib {
      xr:xr-xml-map "mpls_ldp_oper_data:IsRegisteredWithIPv6_RIB";
      type boolean;
      description "Registration status with IPv6 RIB";
    }
    leaf number-of-ipv6rib-tables {
      xr:xr-xml-map "mpls_ldp_oper_data:NumberOfIPv6RIBTables";
      type uint32;
      description "Total number of ipv6 RIB tables";
    }
    leaf number-of-registered-ipv6rib-tables {
      xr:xr-xml-map "mpls_ldp_oper_data:NumberOfRegisteredIPv6RIBTa"+
        "bles";
      type uint32;
      description "Number of ipv6 RIB tables registered";
    }
    leaf is-bound-with-atom {
      xr:xr-xml-map "mpls_ldp_oper_data:IsBoundWithATOM";
      type boolean;
      description "Bound status with L2VPN ATOM";
    }
    leaf is-bound-with-nsr-mate {
      xr:xr-xml-map "mpls_ldp_oper_data:IsBoundWithNSRMate";
      type boolean;
      description "Bound status with NSR Mate";
    }
    leaf is-nsr-configured {
      xr:xr-xml-map "mpls_ldp_oper_data:IsNSRConfigured";
      type boolean;
      description "NSR configured";
    }
    leaf is-mldp-registered {
      xr:xr-xml-map "mpls_ldp_oper_data:IsMLDPRegistered";
      type boolean;
      description "mLDP registration status";
    }
  }

  grouping LDP-MSG-COUNTERS {
    description "MPLS LDP Session Message Counters Information";
    leaf total-count {
      xr:xr-xml-map "mpls_ldp_oper_data:TotalCount";
      type uint32;
      description "Total message count";
    }
    leaf init-count {
      xr:xr-xml-map "mpls_ldp_oper_data:InitCount";
      type uint32;
      description "Init message count";
    }
    leaf address-count {
      xr:xr-xml-map "mpls_ldp_oper_data:AddressCount";
      type uint32;
      description "Address message count";
    }
    leaf address-withdraw-count {
      xr:xr-xml-map "mpls_ldp_oper_data:AddressWithdrawCount";
      type uint32;
      description "Address withdraw count";
    }
    leaf label-map-count {
      xr:xr-xml-map "mpls_ldp_oper_data:LabelMapCount";
      type uint32;
      description "Label map count";
    }
    leaf label-withdraw-count {
      xr:xr-xml-map "mpls_ldp_oper_data:LabelWithdrawCount";
      type uint32;
      description "Label withdraw count";
    }
    leaf label-release-count {
      xr:xr-xml-map "mpls_ldp_oper_data:LabelReleaseCount";
      type uint32;
      description "Label release count";
    }
    leaf label-request-count {
      xr:xr-xml-map "mpls_ldp_oper_data:LabelRequestCount";
      type uint32;
      description "Label request count";
    }
    leaf label-abort-request-count {
      xr:xr-xml-map "mpls_ldp_oper_data:LabelAbortRequestCount";
      type uint32;
      description "Label abort request count";
    }
    leaf notification-count {
      xr:xr-xml-map "mpls_ldp_oper_data:NotificationCount";
      type uint32;
      description "Notification count";
    }
    leaf keep-alive-count {
      xr:xr-xml-map "mpls_ldp_oper_data:KeepAliveCount";
      type uint32;
      description "Keepalive count";
    }
    leaf iccp-rg-conn-count {
      xr:xr-xml-map "mpls_ldp_oper_data:ICCP_RGConn_Count";
      type uint32;
      description "ICCP RG Connect count";
    }
    leaf iccp-rg-disconn-count {
      xr:xr-xml-map "mpls_ldp_oper_data:ICCP_RGDisconn_Count";
      type uint32;
      description "ICCP RG Disconnect count";
    }
    leaf iccp-rg-notif-count {
      xr:xr-xml-map "mpls_ldp_oper_data:ICCP_RGNotif_Count";
      type uint32;
      description "ICCP RG Notif count";
    }
    leaf iccp-rg-app-data-count {
      xr:xr-xml-map "mpls_ldp_oper_data:ICCP_RGAppData_Count";
      type uint32;
      description "ICCP RG App Data count";
    }
  }

  grouping LDP-STATS-INFO {
    description "MPLS LDP Statistics Information";

    container message-out {
      description "Message out count";
      uses LDP-MSG-COUNTERS;
    }

    container message-in {
      description "Message in count";
      uses LDP-MSG-COUNTERS;
    }
    leaf iccp-enabled {
      xr:xr-xml-map "mpls_ldp_oper_data:ICCPEnabled";
      type boolean;
      description "Is session ICCP enabled?";
    }
  }

  grouping LDP-NBR-CLIENTS-INFO {
    description "MPLS LDP Session client Information";
    leaf name {
      xr:xr-xml-map "mpls_ldp_oper_data:Name";
      type string;
      description "Client's name";
    }
  }

  grouping LDP-NBR-DETAILED-INFO {
    description "MPLS LDP Neighbor Detailed Information";

    container capabilities {
      description "Capabilities sent to and received from neighbor";
      uses LDP-NBR-CAP-INFO;
    }
    leaf peer-holdtime {
      xr:xr-xml-map "mpls_ldp_oper_data:PeerHoldtime";
      type uint32;
      units "second";
      description "Session holdtime value in seconds from the peer";
    }
    leaf keep-alive-interval {
      xr:xr-xml-map "mpls_ldp_oper_data:KeepAliveInterval";
      type uint32;
      units "second";
      description "Session keepalive interval in seconds";
    }
    leaf peer-state {
      xr:xr-xml-map "mpls_ldp_oper_data:PeerState";
      type string {
        length "0..80";
      }
      description "Peer state";
    }
    leaf has-ipv4-inbound {
      xr:xr-xml-map "mpls_ldp_oper_data:HasIPv4Inbound";
      type boolean;
      description "IPv4 Inbound label filtering present";
    }
    leaf inbound-ipv4acl {
      xr:xr-xml-map "mpls_ldp_oper_data:InboundIPv4ACL";
      type string {
        length "0..80";
      }
      description "IPv4 Inbound accept ACL";
    }
    leaf has-ipv6-inbound {
      xr:xr-xml-map "mpls_ldp_oper_data:HasIPv6Inbound";
      type boolean;
      description "IPv6 Inbound label filtering present";
    }
    leaf inbound-ipv6acl {
      xr:xr-xml-map "mpls_ldp_oper_data:InboundIPv6ACL";
      type string {
        length "0..80";
      }
      description "IPv6 Inbound accept ACL";
    }
    leaf has-ipv4-outbound {
      xr:xr-xml-map "mpls_ldp_oper_data:HasIPv4Outbound";
      type boolean;
      description "IPv4 Outbound label filtering present";
    }
    leaf outbound-ipv4acl {
      xr:xr-xml-map "mpls_ldp_oper_data:OutboundIPv4ACL";
      type string {
        length "0..80";
      }
      description "IPv4 Outbound advertise ACL";
    }
    leaf has-ipv6-outbound {
      xr:xr-xml-map "mpls_ldp_oper_data:HasIPv6Outbound";
      type boolean;
      description "IPv6 Outbound label filtering present";
    }
    leaf outbound-ipv6acl {
      xr:xr-xml-map "mpls_ldp_oper_data:OutboundIPv6ACL";
      type string {
        length "0..80";
      }
      description "IPv6 Outbound advertise ACL";
    }
    leaf has-sp {
      xr:xr-xml-map "mpls_ldp_oper_data:HasSP";
      type boolean;
      description "Session Protection enabled";
    }
    leaf sp-state {
      xr:xr-xml-map "mpls_ldp_oper_data:SPState";
      type string {
        length "0..80";
      }
      description "Session Protection state";
    }
    leaf sp-has-acl {
      xr:xr-xml-map "mpls_ldp_oper_data:SPHasACL";
      type boolean;
      description "Session protection ACL is present";
    }
    leaf spacl {
      xr:xr-xml-map "mpls_ldp_oper_data:SPACL";
      type string {
        length "0..80";
      }
      description "Session Protection ACL";
    }
    leaf sp-has-duration {
      xr:xr-xml-map "mpls_ldp_oper_data:SPHasDuration";
      type boolean;
      description "Session Protection has non-default duration";
    }
    leaf sp-duration {
      xr:xr-xml-map "mpls_ldp_oper_data:SPDuration";
      type uint32;
      units "second";
      description
        "Session protection holdup time duration in
        seconds";
    }
    leaf spht-running {
      xr:xr-xml-map "mpls_ldp_oper_data:SPHTRunning";
      type boolean;
      description "Session Protection holdup timer is running";
    }
    leaf spht-remaining {
      xr:xr-xml-map "mpls_ldp_oper_data:SPHTRemaining";
      type uint32;
      units "second";
      description
        "Session Protection holdup time remaining value
        in seconds";
    }
    leaf nsr-sync-state {
      xr:xr-xml-map "mpls_ldp_oper_data:NSRSyncState";
      type Mgmt-ldp-nsr-peer-sync-state;
      description "NSR Sync State";
    }
    leaf nsr-last-sync-error {
      xr:xr-xml-map "mpls_ldp_oper_data:NSRLastSyncError";
      type Mgmt-ldp-nsr-peer-sync-err;
      description "Last NSR sync error";
    }
    leaf nsr-last-sync-nack-reason {
      xr:xr-xml-map "mpls_ldp_oper_data:NSRLastSyncNackReason";
      type Mgmt-ldp-nsr-peer-ldp-sync-nack-rsn;
      description "Last NSR sync NACK reaston";
    }
    leaf bgp-advertisement-state {
      xr:xr-xml-map "mpls_ldp_oper_data:BGPAdvertisementState";
      type Mgmt-ldp-nbr-bgp-advt-state;
      description "BGP labelled prefixes advertisement state";
    }
    leaf advertise-bgp-prefixes {
      xr:xr-xml-map "mpls_ldp_oper_data:AdvertiseBGPPrefixes";
      type boolean;
      description
        "Is BGP labelled prefixes advertised to the
        neighbor";
    }

    list client {
      description "Targeted Session clients";
      uses LDP-NBR-CLIENTS-INFO;
    }

    list ipv4-duplicate-address {
      description "Duplicate IPv4 address bound to this peer";
      uses LDP-NBR-ADDR-INFO;
    }

    list ipv6-duplicate-address {
      description "Duplicate IPv6 address bound to this peer";
      uses LDP-NBR-ADDR-INFO;
    }
  }

  grouping TARGETED-HELLO {
    description "MPLS LDP Targeted Hello Information";

    container local-address {
      description "Local Address";
      uses LDP-IP-ADDR-T-UNION;
    }

    container target-address {
      description "Target Address";
      uses LDP-IP-ADDR-T-UNION;
    }
    leaf state {
      xr:xr-xml-map "mpls_ldp_oper_data:State";
      type Dhcb-state;
      description "State";
    }
  }

  grouping LINK-HELLO {
    description "MPLS LDP Link Hello Information";
    leaf interface {
      xr:xr-xml-map "mpls_ldp_oper_data:Interface";
      type xr:Interface-name;
      description "Interface name";
    }
    leaf interface-name {
      xr:xr-xml-map "mpls_ldp_oper_data:InterfaceName";
      type string;
      description "Interface name";
    }
  }

  grouping LDP-ADJ-UNION {
    description "LDP ADJ UNION";

    container link-hello-data {
      when "../hello-type = 'link-hello'" {
        description "../HelloType = 'LinkHello'";
      }
      description "Link hello";
      uses LINK-HELLO;
    }

    container target-hello-data {
      when "../hello-type = 'targeted-hello'" {
        description "../HelloType = 'TargetedHello'";
      }
      description "Target Hello";
      uses TARGETED-HELLO;
    }
    leaf hello-type {
      xr:xr-xml-map "mpls_ldp_oper_data:HelloType";
      type Ldp-adj-union-discrim;
      description "HelloType";
    }
  }

  grouping LDP-NBR-ADJ-INFO {
    description "MPLS LDP Neighbor Adjacency Information";

    container adjacency-group {
      description "Adjacency group";
      uses LDP-ADJ-UNION;
    }
  }

  grouping LDP-NBR-ADDR-INFO {
    description "MPLS LDP Neighbor Bound Address Information";

    container address {
      description "Neighbor Address";
      uses LDP-IP-ADDR-T-UNION;
    }
  }

  grouping LDP-TCP-INFO {
    description "MPLS LDP Neighbor TCP Information";

    container foreign-host {
      description "Foreign host address";
      uses LDP-IP-ADDR-T-UNION;
    }

    container local-host {
      description "Local host address";
      uses LDP-IP-ADDR-T-UNION;
    }
    leaf foreign-port {
      xr:xr-xml-map "mpls_ldp_oper_data:ForeignPort";
      type uint16;
      description "Foreign port number";
    }
    leaf local-port {
      xr:xr-xml-map "mpls_ldp_oper_data:LocalPort";
      type uint16;
      description "Local port number";
    }
    leaf is-md5-on {
      xr:xr-xml-map "mpls_ldp_oper_data:IsMD5On";
      type boolean;
      description "Is MD5 Digest on";
    }
  }

  grouping LDP-GR-ADJ-INFO {
    description
      "MPLS LDP Neighbor Graceful Restart Adjacency
      Information";
    leaf is-graceful-restartable {
      xr:xr-xml-map "mpls_ldp_oper_data:IsGracefulRestartable";
      type boolean;
      description "Is graceful restartable";
    }
    leaf reconnect-timeout {
      xr:xr-xml-map "mpls_ldp_oper_data:ReconnectTimeout";
      type uint32;
      description "Reconnect timeout";
    }
    leaf recovery-time {
      xr:xr-xml-map "mpls_ldp_oper_data:RecoveryTime";
      type uint32;
      description "Recovery time";
    }
  }

  grouping LDP-PTCL-ADJ-INFO {
    description "MPLS LDP PTCL Adjacency Information";

    container ta-graceful-restart-adjacency {
      description "Graceful restart information";
      uses LDP-GR-ADJ-INFO;
    }
    leaf ta-holdtime {
      xr:xr-xml-map "mpls_ldp_oper_data:TAHoldtime";
      type uint32;
      description "Session holdtime in sec";
    }
    leaf ta-state {
      xr:xr-xml-map "mpls_ldp_oper_data:TAState";
      type string;
      description "State";
    }
    leaf ta-pies-sent {
      xr:xr-xml-map "mpls_ldp_oper_data:TAPiesSent";
      type uint32;
      description "Number of pies sent";
    }
    leaf ta-pies-rcvd {
      xr:xr-xml-map "mpls_ldp_oper_data:TAPiesRcvd";
      type uint32;
      description "Number of pies received";
    }
    leaf ta-up-time-seconds {
      xr:xr-xml-map "mpls_ldp_oper_data:TAUpTimeSeconds";
      type uint32;
      units "second";
      description "Up time in seconds";
    }
    leaf downstream-on-demand {
      xr:xr-xml-map "mpls_ldp_oper_data:DownstreamOnDemand";
      type boolean;
      description
        "Is Label advertisment mode in Downstream On
        Demand mode or Not";
    }
  }

  grouping LDP-NEIGHBOR-INFO {
    description "MPLS LDP Neighbor Information";

    container protocol-information {
      description "Protocol Information";
      uses LDP-PTCL-ADJ-INFO;
    }

    container tcp-information {
      description "TCP Information";
      uses LDP-TCP-INFO;
    }

    container detailed-information {
      description
        "Detailed information with regards to holdtime,
        KA, inbound filtering, and Session protection";
      uses LDP-NBR-DETAILED-INFO;
    }

    list ldp-nbr-bound-ipv4-address-info {
      description "Neighbor IPv4 Address Info";
      uses LDP-NBR-ADDR-INFO;
    }

    list ldp-nbr-bound-ipv6-address-info {
      description "Neighbor IPv6 Address Info";
      uses LDP-NBR-ADDR-INFO;
    }

    list ldp-nbr-ipv4-adj-info {
      description "Neighbor's IPv4 Adjacency Information";
      uses LDP-NBR-ADJ-INFO;
    }

    list ldp-nbr-ipv6-adj-info {
      description "Neighbor's IPv6 Adjacency Information";
      uses LDP-NBR-ADJ-INFO;
    }
  }

  grouping LDP-NBR-CAP-INFO {
    description "MPLS LDP Neighbor Capability Information";

    list sent {
      description "List of sent capabilities";
      uses LDP-CAP-DESC;
    }

    list received {
      description "List of received capabilities";
      uses LDP-CAP-DESC;
    }
  }

  grouping LDP-PARAMETERS-AF {
    description "MPLS LDP per AF Parameters Information";

    container discovery-transport-address {
      description "Discovery transport address";
      uses LDP-IP-ADDR-T-UNION;
    }
    leaf address-family {
      xr:xr-xml-map "mpls_ldp_oper_data:AddressFamily";
      type Ldp-af;
      description "Address Family";
    }
    leaf null-label {
      xr:xr-xml-map "mpls_ldp_oper_data:NullLabel";
      type string;
      description "Null label";
    }
    leaf label-imp-null-override-acl {
      xr:xr-xml-map "mpls_ldp_oper_data:LabelImpNullOverrideACL";
      type string;
      description
        "ACL to override local label to use implicit-null";
    }
    leaf is-accepting-targeted-hellos {
      xr:xr-xml-map "mpls_ldp_oper_data:IsAcceptingTargetedHellos";
      type boolean;
      description "Accepting targeted Hellos";
    }
    leaf targeted-hello-acl {
      xr:xr-xml-map "mpls_ldp_oper_data:TargetedHelloACL";
      type string;
      description "Targeted Hello ACL";
    }
  }

  grouping LDP-GRACEFUL-RESTART-INFO {
    description "MPLS LDP Global Graceful Restart Information";
    leaf is-graceful-restart-configured {
      xr:xr-xml-map "mpls_ldp_oper_data:IsGracefulRestartConfigured";
      type boolean;
      description "Is graceful restart configured";
    }
    leaf graceful-restart-reconnect-timeout {
      xr:xr-xml-map "mpls_ldp_oper_data:GracefulRestartReconnectTim"+
        "eout";
      type uint32;
      description "Reconnect timeout value";
    }
    leaf graceful-restart-forwarding-state-hold-time {
      xr:xr-xml-map "mpls_ldp_oper_data:GracefulRestartForwardingSt"+
        "ateHoldTime";
      type uint32;
      description "Graceful restart forward state hold time";
    }
  }

  grouping LDP-PARAMETERS {
    description "MPLS LDP Global Parameters";

    container graceful-restart-information {
      description "Graceful restart information";
      uses LDP-GRACEFUL-RESTART-INFO;
    }
    leaf role-is-active {
      xr:xr-xml-map "mpls_ldp_oper_data:RoleIsActive";
      type boolean;
      description "Is process role active or standby";
    }
    leaf global-md5-password-enabled {
      xr:xr-xml-map "mpls_ldp_oper_data:GlobalMD5PasswordEnabled";
      type boolean;
      description "Global MD5 password enabled";
    }
    leaf protocol-version {
      xr:xr-xml-map "mpls_ldp_oper_data:ProtocolVersion";
      type uint32;
      description "Protocol version";
    }
    leaf router-id {
      xr:xr-xml-map "mpls_ldp_oper_data:RouterID";
      type inet:ipv4-address;
      description "Router ID";
    }
    leaf keepalive-interval {
      xr:xr-xml-map "mpls_ldp_oper_data:KeepaliveInterval";
      type uint32;
      description "Keepalive interval";
    }
    leaf hello-hold-time {
      xr:xr-xml-map "mpls_ldp_oper_data:HelloHoldTime";
      type uint32;
      description "Hello hold time";
    }
    leaf hello-interval {
      xr:xr-xml-map "mpls_ldp_oper_data:HelloInterval";
      type uint32;
      description "Hello interval";
    }
    leaf targeted-hello-hold-time {
      xr:xr-xml-map "mpls_ldp_oper_data:TargetedHelloHoldTime";
      type uint32;
      description "Targeted hello hold time";
    }
    leaf targeted-hello-interval {
      xr:xr-xml-map "mpls_ldp_oper_data:TargetedHelloInterval";
      type uint32;
      description "Targeted hello interval";
    }
    leaf session-hold-time {
      xr:xr-xml-map "mpls_ldp_oper_data:SessionHoldTime";
      type uint32;
      description "Session hold time";
    }
    leaf housekeeping-timer-interval {
      xr:xr-xml-map "mpls_ldp_oper_data:HousekeepingTimerInterval";
      type uint32;
      description "Housekeeping periodic timer interval";
    }
    leaf le-no-route-timeout {
      xr:xr-xml-map "mpls_ldp_oper_data:LENoRouteTimeout";
      type uint32;
      description "LIB entry no route timeout";
    }
    leaf ldp-recovery-timeout {
      xr:xr-xml-map "mpls_ldp_oper_data:LDPRecoveryTimeout";
      type uint32;
      description "LDP recovery timeout with LSD";
    }
    leaf af-binding-withdraw-delay {
      xr:xr-xml-map "mpls_ldp_oper_data:AfBindingWithdrawDelay";
      type uint32;
      description
        "Delay (sec) in Binding Withdrawal for an Address
        Family";
    }
    leaf max-intf-attached {
      xr:xr-xml-map "mpls_ldp_oper_data:MaxIntfAttached";
      type uint32;
      description
        "Maximum number of LDP enabled attached
        interfaces";
    }
    leaf max-intf-te {
      xr:xr-xml-map "mpls_ldp_oper_data:MaxIntfTE";
      type uint32;
      description "Maximum number of LDP enabled TE interfaces";
    }
    leaf max-peer {
      xr:xr-xml-map "mpls_ldp_oper_data:MaxPeer";
      type uint32;
      description "Maximum number of LDP peers";
    }
    leaf ldp-out-of-mem-state {
      xr:xr-xml-map "mpls_ldp_oper_data:LDPOutOfMemState";
      type uint32;
      description "LDP Out of memory state";
    }
    leaf nsr-enabled {
      xr:xr-xml-map "mpls_ldp_oper_data:NsrEnabled";
      type boolean;
      description "TRUE if NSR is enabled";
    }
    leaf nsr-synced {
      xr:xr-xml-map "mpls_ldp_oper_data:NsrSynced";
      type boolean;
      description
        "TRUE if LDP is standby and is NSR Sync-ed with
        active";
    }
    leaf igp-sync-delay-time-for-interface {
      xr:xr-xml-map "mpls_ldp_oper_data:IGPSyncDelayTimeForInterfac"+
        "e";
      type uint32;
      units "second";
      description "Interface IGP sync delay time in seconds";
    }
    leaf igp-sync-delay-time-on-restart {
      xr:xr-xml-map "mpls_ldp_oper_data:IGPSyncDelayTimeOnRestart";
      type uint32;
      units "second";
      description
        "IGP sync delay time on process restart in
        seconds";
    }
    leaf global-discovery-quick-start-disabled {
      xr:xr-xml-map "mpls_ldp_oper_data:GlobalDiscoveryQuickStartDi"+
        "sabled";
      type boolean;
      description "Discovery quick-start globally disabled";
    }
    leaf discovery-quick-start-disabled-on-interfaces {
      xr:xr-xml-map "mpls_ldp_oper_data:DiscoveryQuickStartDisabled"+
        "OnInterfaces";
      type boolean;
      description
        "Discovery quick-start disabled on some
        LDP-enabled interfaces";
    }

    list address-family-parameter {
      description "Per AF parameters";
      uses LDP-PARAMETERS-AF;
    }
  }

  grouping LDP-NSR-SUM-SESS {
    description "MPLS LDP NSR session summary";
    leaf total {
      xr:xr-xml-map "mpls_ldp_oper_data:Total";
      type uint32;
      description "Total sessions";
    }
    leaf nsr-eligible {
      xr:xr-xml-map "mpls_ldp_oper_data:NSREligible";
      type uint32;
      description "NSR eligible sessions";
    }
    leaf nsr-state-none {
      xr:xr-xml-map "mpls_ldp_oper_data:NSRStateNone";
      type uint32;
      description "Number of sessions in NSR none state";
    }
    leaf nsr-state-wait {
      xr:xr-xml-map "mpls_ldp_oper_data:NSRStateWait";
      type uint32;
      description "Number of sessions in NSR wait state";
    }
    leaf nsr-state-ready {
      xr:xr-xml-map "mpls_ldp_oper_data:NSRStateReady";
      type uint32;
      description "Number of sessions in NSR ready state";
    }
    leaf nsr-state-prepare {
      xr:xr-xml-map "mpls_ldp_oper_data:NSRStatePrepare";
      type uint32;
      description "Number of sessions in NSR prepare state";
    }
    leaf nsr-state-app-wait {
      xr:xr-xml-map "mpls_ldp_oper_data:NSRStateAppWait";
      type uint32;
      description "Number of sessions in NSR app-wait state";
    }
    leaf nsr-state-operational {
      xr:xr-xml-map "mpls_ldp_oper_data:NSRStateOperational";
      type uint32;
      description "Number of sessions in NSR operational state";
    }
    leaf nsr-state-tcp-phase1 {
      xr:xr-xml-map "mpls_ldp_oper_data:NSRStateTCPPhase1";
      type uint32;
      description "Number of sessions in NSR TCP phase 1 state";
    }
    leaf nsr-state-tcp-phase2 {
      xr:xr-xml-map "mpls_ldp_oper_data:NSRStateTCPPhase2";
      type uint32;
      description "Number of sessions in NSR TCP phase 2 state";
    }
  }

  grouping LDP-NSR-SUM {
    description "MPLS LDP NSR summary";

    container vrf {
      description "VRF information";
      uses LDP-VRF-INFO;
    }

    container sessions {
      description "Session summary";
      uses LDP-NSR-SUM-SESS;
    }
  }

  grouping LDP-BACKOFF-ENTRY-INFO {
    description "MPLS LDP Session Backoff Entry Information";
    leaf backoff-seconds {
      xr:xr-xml-map "mpls_ldp_oper_data:BackoffSeconds";
      type uint32;
      units "second";
      description "Backoff seconds";
    }
    leaf waiting-seconds {
      xr:xr-xml-map "mpls_ldp_oper_data:WaitingSeconds";
      type uint32;
      units "second";
      description "Backoff waiting seconds";
    }
  }

  grouping LDP-BACKOFF-INFO {
    description "MPLS LDP Session Backoff Information";
    leaf initial-seconds {
      xr:xr-xml-map "mpls_ldp_oper_data:InitialSeconds";
      type uint32;
      units "second";
      description "Initial backoff value in seconds";
    }
    leaf maximum-seconds {
      xr:xr-xml-map "mpls_ldp_oper_data:MaximumSeconds";
      type uint32;
      units "second";
      description "Maximum backoff value in seconds";
    }
  }

  grouping LDP-NEIGHBOR-BRIEF-AF-INFO {
    description "MPLS LDP Neighbor Brief AF information";
    leaf address-family {
      xr:xr-xml-map "mpls_ldp_oper_data:AddressFamily";
      type Ldp-af;
      description "Neighbor Brief Address Family";
    }
    leaf num-of-nbr-discovery {
      xr:xr-xml-map "mpls_ldp_oper_data:NumOfNbrDiscovery";
      type uint32;
      description "Number of neighbor discovery sources";
    }
    leaf num-of-nbr-addresses {
      xr:xr-xml-map "mpls_ldp_oper_data:NumOfNbrAddresses";
      type uint32;
      description "Number of neighbor addresses";
    }
    leaf num-of-nbr-lbl {
      xr:xr-xml-map "mpls_ldp_oper_data:NumOfNbrLbl";
      type uint32;
      description "Number of neighbor labels";
    }
  }

  grouping LDP-NEIGHBOR-BRIEF-INFO {
    description "MPLS LDP Neighbor Brief Information";

    container vrf {
      description "VRF information";
      uses LDP-VRF-INFO;
    }
    leaf is-graceful-restartable {
      xr:xr-xml-map "mpls_ldp_oper_data:IsGracefulRestartable";
      type boolean;
      description "Is graceful restartable";
    }
    leaf nsr-state {
      xr:xr-xml-map "mpls_ldp_oper_data:NSRState";
      type Show-nsr-state;
      description "NSR readiness state";
    }
    leaf up-time-seconds {
      xr:xr-xml-map "mpls_ldp_oper_data:UpTimeSeconds";
      type uint32;
      units "second";
      description "Up time in seconds";
    }

    list nbr-br-af-info {
      max-elements "2";
      description "Neighbor Brief AF Info";
      uses LDP-NEIGHBOR-BRIEF-AF-INFO;
    }
  }

  grouping LDP-FWD-RW-PATH-SUMM {
    description "MPLS LDP fowarding rewrite nexthop/path summary";
    leaf total-paths {
      xr:xr-xml-map "mpls_ldp_oper_data:TotalPaths";
      type uint32;
      description "Total path count";
    }
    leaf protected-paths {
      xr:xr-xml-map "mpls_ldp_oper_data:ProtectedPaths";
      type uint32;
      description "Count of FRR protected paths";
    }
    leaf backup-paths {
      xr:xr-xml-map "mpls_ldp_oper_data:BackupPaths";
      type uint32;
      description "Count of non-primary backup paths";
    }
    leaf remote-backup-paths {
      xr:xr-xml-map "mpls_ldp_oper_data:RemoteBackupPaths";
      type uint32;
      description "Count of non-primary remote backup paths";
    }
    leaf labeled-paths {
      xr:xr-xml-map "mpls_ldp_oper_data:LabeledPaths";
      type uint32;
      description "Count of all labeled paths";
    }
    leaf labeled-backup-paths {
      xr:xr-xml-map "mpls_ldp_oper_data:LabeledBackupPaths";
      type uint32;
      description "Count of labeled backup paths";
    }
  }

  grouping LDP-FWD-RW-PFX-LBL-SUMM {
    description
      "MPLS LDP forwarding rewrite prefix nexthops
      labeled summary";
    leaf labeled-pfxs {
      xr:xr-xml-map "mpls_ldp_oper_data:LabeledPfxs";
      type uint16;
      description
        "Count of labeled prefixes with 1 or more paths
        labeled";
    }
    leaf labeled-pfxs-partial {
      xr:xr-xml-map "mpls_ldp_oper_data:LabeledPfxsPartial";
      type uint16;
      description
        "Count of labeled prefixes with some (but not
        ALL) paths labeled";
    }
    leaf unlabeled-pfxs {
      xr:xr-xml-map "mpls_ldp_oper_data:UnlabeledPfxs";
      type uint16;
      description
        "Count of labeled prefixes with ALL paths
        unlabeled";
    }
  }

  grouping LDP-FWD-RW-PFX-SUMM {
    description "MPLS LDP fowarding rewrite prefix summary";

    container labeled-pfxs-aggr {
      description "Labeled prefix count for all paths";
      uses LDP-FWD-RW-PFX-LBL-SUMM;
    }

    container labeled-pfxs-primary {
      description
        "Labeled prefix count related to primary paths
        only";
      uses LDP-FWD-RW-PFX-LBL-SUMM;
    }

    container labeled-pfxs-backup {
      description
        "Labeled prefix count related to backup paths
        only";
      uses LDP-FWD-RW-PFX-LBL-SUMM;
    }
    leaf total-pfxs {
      xr:xr-xml-map "mpls_ldp_oper_data:TotalPfxs";
      type uint16;
      description "Total Prefix count";
    }
    leaf ecmp-pfxs {
      xr:xr-xml-map "mpls_ldp_oper_data:ECMPPfxs";
      type uint16;
      description "Count of prefixes with ECMP";
    }
    leaf protected-pfxs {
      xr:xr-xml-map "mpls_ldp_oper_data:ProtectedPfxs";
      type uint16;
      description "Count of FRR protected prefixes";
    }
  }

  grouping LDP-FWD-RW-SUMM {
    description "MPLS LDP fowarding rewrite summary";

    container pfxs {
      description "Forwarding rewrites prefix summary";
      uses LDP-FWD-RW-PFX-SUMM;
    }

    container nhs {
      description "Forwarding rewrites nexthops (paths) summary";
      uses LDP-FWD-RW-PATH-SUMM;
    }
  }

  grouping LDP-FWD-SUMM-INFO {
    description "MPLS LDP fowarding summary";

    container vrf {
      description "VRF information";
      uses LDP-VRF-INFO;
    }

    container rws {
      description "Forwarding rewrites summary";
      uses LDP-FWD-RW-SUMM;
    }
    leaf is-lsd-bound {
      xr:xr-xml-map "mpls_ldp_oper_data:IsLSDBound";
      type boolean;
      description "LDP is connected to LSD server";
    }
    leaf fsht {
      xr:xr-xml-map "mpls_ldp_oper_data:FSHT";
      type uint16;
      description "Forwarding state hold time registered with LSD";
    }
    leaf intfs {
      xr:xr-xml-map "mpls_ldp_oper_data:Intfs";
      type uint16;
      description "MPLS forwarding enabled interface count";
    }
    leaf lbls {
      xr:xr-xml-map "mpls_ldp_oper_data:Lbls";
      type uint16;
      description "Local label allocated count";
    }
  }

  grouping LDP-BINDING-ALLOC {
    description "MPLS LDP Binding local label allocation filter";
    leaf has-acl {
      xr:xr-xml-map "mpls_ldp_oper_data:HasACL";
      type boolean;
      description "Has ACL filter?";
    }
    leaf prefix-acl {
      xr:xr-xml-map "mpls_ldp_oper_data:PrefixACL";
      type string {
        length "0..64";
      }
      description "Prefix ACL";
    }
    leaf is-host-route-only {
      xr:xr-xml-map "mpls_ldp_oper_data:IsHostRouteOnly";
      type boolean;
      description "Host-routes only?";
    }
  }

  grouping LDP-BINDING-ADVT-ACL-PAIR {
    description "MPLS LDP Binding advertisement ACL pair";
    leaf prefix-acl {
      xr:xr-xml-map "mpls_ldp_oper_data:PrefixACL";
      type string {
        length "0..64";
      }
      description "Prefix ACL";
    }
    leaf peer-acl {
      xr:xr-xml-map "mpls_ldp_oper_data:PeerACL";
      type string {
        length "0..64";
      }
      description "Peer ACL";
    }
  }

  grouping LDP-BINDING-ADVT-SPEC {
    description "MPLS LDP Binding advertisement specification ACLs";

    container allocation-acl {
      description "Local label Allocation filter";
      uses LDP-BINDING-ALLOC;
    }

    list advt-acl {
      description "Advertisement ACLs";
      uses LDP-BINDING-ADVT-ACL-PAIR;
    }
  }

  grouping LDP-FWD-PATH-RLFA-MOI-INFO {
    description
      "MPLS LDP Forwarding Path Remote LFA-FRR backup
      MPLS MOI info";

    list stack {
      description "Inner label stack info";
      uses LDP-FWD-PATH-MPLS-NH-INFO;
    }
  }

  grouping LDP-FWD-PATH-RLFA-MPLS-INFO {
    description
      "MPLS LDP Forwarding Path Remote LFA-FRR backup
      MPLS info";

    container mpls-outgoing-info {
      description "Remote LFA MPLS nexthop(s_ info";
      uses LDP-FWD-PATH-RLFA-MOI-INFO;
    }
    leaf has-remote-lfa-bkup {
      xr:xr-xml-map "mpls_ldp_oper_data:HasRemoteLFABkup";
      type boolean;
      description "Whether path has remote LFA backup";
    }
  }

  grouping LDP-FWD-PATH-MPLS-NH-INFO {
    description "Forwarding Path MPLS nexthop info";

    container nexthop-peer-ldp-ident {
      description "Nexthop LDP peer";
      uses LDP-LDPID-INFO;
    }
    leaf out-label {
      xr:xr-xml-map "mpls_ldp_oper_data:OutLabel";
      type uint32;
      description "Outgoing label";
    }
    leaf out-label-rsn {
      xr:xr-xml-map "mpls_ldp_oper_data:OutLabelRsn";
      type Ldp-fwd-unlbl-rsn;
      description "Outgoing label reason";
    }
    leaf out-label-type {
      xr:xr-xml-map "mpls_ldp_oper_data:OutLabelType";
      type Label-value;
      description "Outgoing Label Type";
    }
    leaf out-label-owner {
      xr:xr-xml-map "mpls_ldp_oper_data:OutLabelOwner";
      type Ldp-route-path-lbl-owner;
      description "Outgoing label owner";
    }
    leaf is-from-graceful-restartable-neighbor {
      xr:xr-xml-map "mpls_ldp_oper_data:IsFromGracefulRestartableNe"+
        "ighbor";
      type boolean;
      description "Is from a GR neighbor";
    }
    leaf is-stale {
      xr:xr-xml-map "mpls_ldp_oper_data:IsStale";
      type boolean;
      description "Is the entry stale";
    }
  }

  grouping LDP-FWD-PATH-MPLS-INFO {
    description "MPLS LDP Forwarding Path MPLS information";

    container mpls-outgoing-info {
      description "MPLS nexthop info";
      uses LDP-FWD-PATH-MPLS-NH-INFO;
    }

    container remote-lfa {
      description "Remote LFA-FRR backup info";
      uses LDP-FWD-PATH-RLFA-MPLS-INFO;
    }
  }

  grouping LDP-FWD-PATH-RLFA-ROUTING-INFO {
    description
      "MPLS LDP Forwarding Path Remote LFA-FRR backup
      routing info";

    container remote-p-node-id {
      description "Remote/P node address";
      uses LDP-IP-ADDR-T-UNION;
    }

    container remote-q-node-id {
      description "Remote/Q node address";
      uses LDP-IP-ADDR-T-UNION;
    }
    leaf has-remote-lfa-bkup {
      xr:xr-xml-map "mpls_ldp_oper_data:HasRemoteLFABkup";
      type boolean;
      description "Whether path has remote LFA backup";
    }
    leaf needs-tldp {
      xr:xr-xml-map "mpls_ldp_oper_data:NeedsTLDP";
      type boolean;
      description "Whether TLDP is needed with remote PQ node";
    }
    leaf has-q-node {
      xr:xr-xml-map "mpls_ldp_oper_data:HasQNode";
      type boolean;
      description "Whether remote LFA path has a Q node associated";
    }
  }

  grouping LDP-FWD-PATH-ROUTING-INFO {
    description "MPLS LDP Forwarding Path IP Routing information";

    container next-hop {
      description "Next Hop";
      uses LDP-IP-ADDR-T-UNION;
    }

    container remote-lfa {
      description "Remote LFA-FRR backup info";
      uses LDP-FWD-PATH-RLFA-ROUTING-INFO;
    }
    leaf interface {
      xr:xr-xml-map "mpls_ldp_oper_data:Interface";
      type xr:Interface-name;
      description "Interface name";
    }
    leaf interface-name {
      xr:xr-xml-map "mpls_ldp_oper_data:InterfaceName";
      type string;
      description "Interface Name";
    }
    leaf nh-is-overriden {
      xr:xr-xml-map "mpls_ldp_oper_data:NHIsOverriden";
      type boolean;
      description "Nexthop is overriden by LDP";
    }
    leaf nexthop-id {
      xr:xr-xml-map "mpls_ldp_oper_data:NexthopID";
      type uint32;
      description "Nexthop Identifier";
    }
    leaf next-hop-table-id {
      xr:xr-xml-map "mpls_ldp_oper_data:NextHopTableID";
      type uint32;
      description "Table ID for nexthop address";
    }
    leaf flags {
      xr:xr-xml-map "mpls_ldp_oper_data:Flags";
      type uint32;
      description "Route path flags";
    }
    leaf load-metric {
      xr:xr-xml-map "mpls_ldp_oper_data:LoadMetric";
      type uint32;
      description "Path's load metric for load balancing";
    }
    leaf path-id {
      xr:xr-xml-map "mpls_ldp_oper_data:PathID";
      type uint8;
      description "path Id";
    }
    leaf bkup-path-id {
      xr:xr-xml-map "mpls_ldp_oper_data:BkupPathID";
      type uint8;
      description "Backup path Id";
    }
    leaf path-flags {
      xr:xr-xml-map "mpls_ldp_oper_data:PathFlags";
      type Ldp-route-path-flags;
      description "Routing path flags decoded";
    }
  }

  grouping LDP-FWD-PATH-INFO {
    description "MPLS LDP Forwarding Path info";

    container routing {
      description "IP routing information";
      uses LDP-FWD-PATH-ROUTING-INFO;
    }

    container mpls {
      description "MPLS information";
      uses LDP-FWD-PATH-MPLS-INFO;
    }
  }

  grouping LDP-FWD-ROUTE-MPLS-INFO {
    description "MPLS LDP Forwarding Route LDP information";
    leaf local-label {
      xr:xr-xml-map "mpls_ldp_oper_data:LocalLabel";
      type uint32;
      description "Local label";
    }
    leaf forwarding-update-count {
      xr:xr-xml-map "mpls_ldp_oper_data:ForwardingUpdateCount";
      type uint32;
      description "Number of forwarding updates";
    }
    leaf forwarding-update-timestamp {
      xr:xr-xml-map "mpls_ldp_oper_data:ForwardingUpdateTimestamp";
      type uint64;
      description "Last Forwarding update nanosec timestamp";
    }
    leaf forwarding-update-age {
      xr:xr-xml-map "mpls_ldp_oper_data:ForwardingUpdateAge";
      type uint64;
      description "Last Forwarding update nanosec age";
    }
  }

  grouping LDP-FWD-ROUTE-ROUTING-INFO {
    description "MPLS LDP Forwarding Route IP Routing information";
    leaf version {
      xr:xr-xml-map "mpls_ldp_oper_data:Version";
      type uint32;
      description "Route RIB ersion";
    }
    leaf priority {
      xr:xr-xml-map "mpls_ldp_oper_data:Priority";
      type uint8;
      description "Route priority";
    }
    leaf source {
      xr:xr-xml-map "mpls_ldp_oper_data:Source";
      type uint16;
      description "Route source protol Id";
    }
    leaf type {
      xr:xr-xml-map "mpls_ldp_oper_data:Type";
      type uint16;
      description "Route type";
    }
    leaf flags {
      xr:xr-xml-map "mpls_ldp_oper_data:Flags";
      type uint32;
      description "Route RIB flags";
    }
    leaf metric {
      xr:xr-xml-map "mpls_ldp_oper_data:Metric";
      type uint32;
      description "Route metric";
    }
    leaf is-local-vrf-leaked {
      xr:xr-xml-map "mpls_ldp_oper_data:IsLocalVRFLeaked";
      type boolean;
      description "Is route leaked across local VRFs?";
    }
    leaf routing-update-count {
      xr:xr-xml-map "mpls_ldp_oper_data:RoutingUpdateCount";
      type uint32;
      description "Number of routing updates";
    }
    leaf routing-update-timestamp {
      xr:xr-xml-map "mpls_ldp_oper_data:RoutingUpdateTimestamp";
      type uint64;
      description "Last Routing update nanosec timestamp";
    }
    leaf routing-update-age {
      xr:xr-xml-map "mpls_ldp_oper_data:RoutingUpdateAge";
      type uint64;
      description "Last Routing update nanosec age";
    }
  }

  grouping LDP-FWD-ROUTE-INFO {
    description "MPLS LDP Forwarding Route information";

    container routing {
      description "IP routing information";
      uses LDP-FWD-ROUTE-ROUTING-INFO;
    }

    container mpls {
      description "MPLS information";
      uses LDP-FWD-ROUTE-MPLS-INFO;
    }
  }

  grouping LDP-FWD-PFX-INFO {
    description "MPLS LDP Forwarding Prefix Information";

    container vrf {
      description "VRF information";
      uses LDP-VRF-INFO;
    }

    container prefix-xr {
      description "IP Prefix";
      uses LDP-IP-ADDR-T-UNION;
    }

    container route {
      description "Route";
      uses LDP-FWD-ROUTE-INFO;
    }
    leaf table-id {
      xr:xr-xml-map "mpls_ldp_oper_data:TableID";
      type uint32;
      description "Table ID associated with IP prefix";
    }
    leaf prefix-length {
      xr:xr-xml-map "mpls_ldp_oper_data:PrefixLength";
      type uint8;
      description "Prefix length";
    }

    list paths {
      description "Paths";
      uses LDP-FWD-PATH-INFO;
    }
  }

  grouping LDP-DISCOVERY-ADJ-GRP-INFO {
    description "MPLS LDP Discovery Adjacency Group Information";
    leaf adjacency-group-up-time {
      xr:xr-xml-map "mpls_ldp_oper_data:AdjacencyGroupUpTime";
      type uint32;
      units "second";
      description "Adjacency group up time in seconds";
    }
    leaf tcp-open-count {
      xr:xr-xml-map "mpls_ldp_oper_data:TCPOpenCount";
      type uint32;
      description "Count of attempted TCP opens";
    }
    leaf tcp-arb-chg-count {
      xr:xr-xml-map "mpls_ldp_oper_data:TCPArbChgCount";
      type uint32;
      description "Count of changes in TCP arbitration";
    }
    leaf tcp-role {
      xr:xr-xml-map "mpls_ldp_oper_data:TCPRole";
      type uint32;
      description "TCP Role";
    }
  }

  grouping LDP-TARGETED-HELLO-BRIEF-INFO {
    description "MPLS LDP Discovery Targeted Brief Information";

    container vrf {
      description "VRF information";
      uses LDP-VRF-INFO;
    }

    container dhcb-target-address {
      description "DHCB target address";
      uses LDP-IP-ADDR-T-UNION;
    }
    leaf address-family {
      xr:xr-xml-map "mpls_ldp_oper_data:AddressFamily";
      type Ldp-af;
      description "Targeted Discovery Address Family";
    }

    list hello-information {
      description "LDP hello info";
      uses LDP-HELLO-BRIEF-INFO;
    }
  }

  grouping LDP-HELLO-BRIEF-INFO {
    description "MPLS LDP Hello Brief Information";
    leaf neighbor-ldp-identifier {
      xr:xr-xml-map "mpls_ldp_oper_data:NeighborLDPIdentifier";
      type string;
      description "Neighbor LDP Identifier";
    }
    leaf hold-time {
      xr:xr-xml-map "mpls_ldp_oper_data:HoldTime";
      type uint32;
      description "Session hold time in sec";
    }
    leaf session-up {
      xr:xr-xml-map "mpls_ldp_oper_data:SessionUp";
      type boolean;
      description "Is session up for this adj";
    }
  }

  grouping LDP-DISCOVERY-LINK-BRIEF-INFO {
    description "MPLS LDP Discovery Link Brief Information";

    container vrf {
      description "VRF information";
      uses LDP-VRF-INFO;
    }
    leaf address-family {
      xr:xr-xml-map "mpls_ldp_oper_data:AddressFamily";
      type Ldp-af;
      description "Discovery Brief Address Family";
    }
    leaf address-family-set {
      xr:xr-xml-map "mpls_ldp_oper_data:AddressFamilySet";
      type Ldp-af;
      description "Discovery Brief Address Family Set";
    }
    leaf interface {
      xr:xr-xml-map "mpls_ldp_oper_data:Interface";
      type xr:Interface-name;
      description "Interface name";
    }
    leaf interface-name-xr {
      xr:xr-xml-map "mpls_ldp_oper_data:interface-name-xr";
      type string;
      description "Interface name";
    }

    list hello-information {
      description "LDP hello info";
      uses LDP-HELLO-BRIEF-INFO;
    }
  }

  grouping LDP-TARGETED-HELLO-INFO {
    description "MPLS LDP Targeted Hello Information";

    container dhcb-local-address {
      description "DHCB local address";
      uses LDP-IP-ADDR-T-UNION;
    }

    container dhcb-target-address {
      description "DHCB target address";
      uses LDP-IP-ADDR-T-UNION;
    }
    leaf state {
      xr:xr-xml-map "mpls_ldp_oper_data:State";
      type Dhcb-state;
      description "Targeted hello state";
    }
    leaf adjacency-ldp-identifier {
      xr:xr-xml-map "mpls_ldp_oper_data:AdjacencyLDPIdentifier";
      type string;
      description "Adjacency LDP Identifier";
    }
    leaf interval {
      xr:xr-xml-map "mpls_ldp_oper_data:Interval";
      type uint32;
      description "Hello interval in sec";
    }
    leaf next-hello {
      xr:xr-xml-map "mpls_ldp_oper_data:NextHello";
      type uint32;
      description "Next hello due time in msec";
    }
    leaf hold-time {
      xr:xr-xml-map "mpls_ldp_oper_data:HoldTime";
      type uint32;
      description "Targeted hello hold time";
    }
    leaf local-hold-time {
      xr:xr-xml-map "mpls_ldp_oper_data:LocalHoldTime";
      type uint32;
      description "Local hold time";
    }
    leaf neighbor-hold-time {
      xr:xr-xml-map "mpls_ldp_oper_data:NeighborHoldTime";
      type uint32;
      description "Neighbor hold time";
    }
    leaf disc-expiry {
      xr:xr-xml-map "mpls_ldp_oper_data:DiscExpiry";
      type uint32;
      description "Discovery expiry time in msec";
    }
    leaf quick-start-disabled {
      xr:xr-xml-map "mpls_ldp_oper_data:QuickStartDisabled";
      type boolean;
      description "Quick-start disabled";
    }
    leaf established-time {
      xr:xr-xml-map "mpls_ldp_oper_data:EstablishedTime";
      type uint64;
      description "Hello adjacency estabished time in nanosec";
    }
    leaf established-age {
      xr:xr-xml-map "mpls_ldp_oper_data:EstablishedAge";
      type uint64;
      description "Hello adjacency estabished age in nanosec";
    }
    leaf session-up {
      xr:xr-xml-map "mpls_ldp_oper_data:SessionUp";
      type boolean;
      description "Is session up for this adj";
    }
    leaf session-bringup-failure-reason {
      xr:xr-xml-map "mpls_ldp_oper_data:SessionBringupFailureReason";
      type string;
      description "session bringup failure reason";
    }

    list last-session-down-info {
      description "Last session down information";
      uses LDP-LAST-SESS-INFO;
    }
  }

  grouping LDP-DISCOVERY-SUMMARY-INFO {
    description "MPLS LDP Discovery Summary Information";

    container vrf {
      description "VRF information";
      uses LDP-VRF-INFO;
    }
    leaf local-ldp-id {
      xr:xr-xml-map "mpls_ldp_oper_data:LocalLDPId";
      type string;
      description "Local LDP identifier";
    }
    leaf num-of-ldp-interfaces {
      xr:xr-xml-map "mpls_ldp_oper_data:NumOfLDPInterfaces";
      type uint32;
      description "Total Number of LDP configured interfaces";
    }
    leaf num-of-active-ldp-interfaces {
      xr:xr-xml-map "mpls_ldp_oper_data:NumOfActiveLDPInterfaces";
      type uint32;
      description "Number of active LDP enabled interfaces";
    }
    leaf num-of-lnk-disc-xmit {
      xr:xr-xml-map "mpls_ldp_oper_data:NumOfLnkDiscXmit";
      type uint32;
      description "Number of link hello discoveries in xmit state";
    }
    leaf num-of-tgt-disc-xmit {
      xr:xr-xml-map "mpls_ldp_oper_data:NumOfTgtDiscXmit";
      type uint32;
      description
        "Number of targeted hello discoveries in xmit
        state";
    }
    leaf num-of-lnk-disc-recv {
      xr:xr-xml-map "mpls_ldp_oper_data:NumOfLnkDiscRecv";
      type uint32;
      description "Number of link hello discoveries in recv state";
    }
    leaf num-of-tgt-disc-recv {
      xr:xr-xml-map "mpls_ldp_oper_data:NumOfTgtDiscRecv";
      type uint32;
      description
        "Number of targeted hello discoveries in recv
        state";
    }
    leaf num-of-disc-with-bad-addr-recv {
      xr:xr-xml-map "mpls_ldp_oper_data:NumOfDiscWithBadAddrRecv";
      type uint32;
      description
        "Number of hello discoveries received with bad
        source address";
    }
    leaf num-of-disc-with-bad-hello-pdu {
      xr:xr-xml-map "mpls_ldp_oper_data:NumOfDiscWithBadHelloPdu";
      type uint32;
      description
        "Number of hello discoveries received with bad
        hello PDU";
    }
    leaf num-of-disc-with-bad-xport-addr {
      xr:xr-xml-map "mpls_ldp_oper_data:NumOfDiscWithBadXportAddr";
      type uint32;
      description
        "Number of hello discoveries received with bad
        export address";
    }
    leaf num-of-disc-with-same-router-id {
      xr:xr-xml-map "mpls_ldp_oper_data:NumOfDiscWithSameRouterId";
      type uint32;
      description
        "Number of hello discoveries received with the
        same router id as this router";
    }
    leaf num-of-disc-with-wrong-router-id {
      xr:xr-xml-map "mpls_ldp_oper_data:NumOfDiscWithWrongRouterId";
      type uint32;
      description
        "Number of hello discoveries received with the
        router id that is not destined for this router";
    }
  }

  grouping LDP-DISCOVERY-LINK-AF-INFO {
    description
      "MPLS LDP Discovery Link Address Family
      Information";

    container local-src-address {
      description "Local source address";
      uses LDP-IP-ADDR-T-UNION;
    }

    container local-transport-address {
      description "Local transport address";
      uses LDP-IP-ADDR-T-UNION;
    }
    leaf interval {
      xr:xr-xml-map "mpls_ldp_oper_data:Interval";
      type uint32;
      description "Hello interval in sec";
    }
  }

  grouping LDP-LAST-SESS-INFO {
    description "LDP last down session information";
    leaf last-session-down-reason {
      xr:xr-xml-map "mpls_ldp_oper_data:LastSessionDownReason";
      type string;
      description "The reason of last socket failure";
    }
    leaf last-session-down-time {
      xr:xr-xml-map "mpls_ldp_oper_data:LastSessionDownTime";
      type uint64;
      description "Timestamp of when the last session went down";
    }
    leaf last-session-up-time {
      xr:xr-xml-map "mpls_ldp_oper_data:LastSessionUpTime";
      type uint32;
      description "The time duration the last session was up";
    }
  }

  grouping LDP-HELLO-INFO {
    description "MPLS LDP Hello Information";

    container neighbor-src-address {
      description "Neighbor source address";
      uses LDP-IP-ADDR-T-UNION;
    }

    container neighbor-transport-address {
      description "Neighbor transport address";
      uses LDP-IP-ADDR-T-UNION;
    }

    container target {
      description "Target address";
      uses LDP-IP-ADDR-T-UNION;
    }
    leaf neighbor-ldp-identifier {
      xr:xr-xml-map "mpls_ldp_oper_data:NeighborLDPIdentifier";
      type string;
      description "Neighbor LDP Identifier";
    }
    leaf is-no-route {
      xr:xr-xml-map "mpls_ldp_oper_data:IsNoRoute";
      type boolean;
      description "Is route valid";
    }
    leaf hold-time {
      xr:xr-xml-map "mpls_ldp_oper_data:HoldTime";
      type uint32;
      units "second";
      description "Session hold time in seconds";
    }
    leaf local-hold-time {
      xr:xr-xml-map "mpls_ldp_oper_data:LocalHoldTime";
      type uint32;
      units "second";
      description "Local hold time in seconds";
    }
    leaf neighbor-hold-time {
      xr:xr-xml-map "mpls_ldp_oper_data:NeighborHoldTime";
      type uint32;
      units "second";
      description "Neighbor hold time in seconds";
    }
    leaf disc-expiry {
      xr:xr-xml-map "mpls_ldp_oper_data:DiscExpiry";
      type uint32;
      description "Discovery expiry time in sec";
    }
    leaf is-targeted {
      xr:xr-xml-map "mpls_ldp_oper_data:IsTargeted";
      type boolean;
      description "Is session a targeted session";
    }
    leaf session-up {
      xr:xr-xml-map "mpls_ldp_oper_data:SessionUp";
      type boolean;
      description "Is session up for this adj";
    }
    leaf established-time {
      xr:xr-xml-map "mpls_ldp_oper_data:EstablishedTime";
      type uint64;
      description "Hello adjacency estabished time in nanosec";
    }
    leaf established-age {
      xr:xr-xml-map "mpls_ldp_oper_data:EstablishedAge";
      type uint64;
      description "Hello adjacency estabished age in nanosec";
    }
    leaf session-bringup-failure-reason {
      xr:xr-xml-map "mpls_ldp_oper_data:SessionBringupFailureReason";
      type string;
      description "session bringup failure reason";
    }

    list last-session-down-info {
      description "Last session down information";
      uses LDP-LAST-SESS-INFO;
    }
  }

  grouping LDP-DISCOVERY-LINK-INFO {
    description "MPLS LDP Discovery Link Information";

    container vrf {
      description "VRF information";
      uses LDP-VRF-INFO;
    }
    leaf next-hello {
      xr:xr-xml-map "mpls_ldp_oper_data:NextHello";
      type uint32;
      description "Next hello due time in msec";
    }
    leaf interface {
      xr:xr-xml-map "mpls_ldp_oper_data:Interface";
      type xr:Interface-name;
      description "Interface name";
    }
    leaf interface-name-xr {
      xr:xr-xml-map "mpls_ldp_oper_data:interface-name-xr";
      type string;
      description "Interface name";
    }
    leaf quick-start-disabled {
      xr:xr-xml-map "mpls_ldp_oper_data:QuickStartDisabled";
      type boolean;
      description "Quick-start disabled";
    }

    list hello-information {
      description "LDP hello info";
      uses LDP-HELLO-INFO;
    }

    list discovery-link-af {
      max-elements "2";
      description "LDP hello AF info";
      uses LDP-DISCOVERY-LINK-AF-INFO;
    }
  }

  grouping LDP-INTF-AUTOCFG {
    description "MPLS LDP auto configure";
    leaf tuple {
      xr:xr-xml-map "mpls_ldp_oper_data:Tuple";
      type string;
      description "Tuple";
    }
  }

  grouping LDP-INTF-TE-MESH-GRP {
    description "MPLS LDP interface tunnel mesh group";
    leaf ldp-te-mesh-group-all-cfgd {
      xr:xr-xml-map "mpls_ldp_oper_data:LDPTeMeshGroupAllCfgd";
      type boolean;
      description "LDP has enabled all TE mesh-groups";
    }
    leaf ldp-mesh-group-enabled {
      xr:xr-xml-map "mpls_ldp_oper_data:LDPMeshGroupEnabled";
      type boolean;
      description "LDP has enabled this TE mesh-group";
    }
    leaf te-mesh-group-id {
      xr:xr-xml-map "mpls_ldp_oper_data:TEMeshGroupID";
      type uint32;
      description "TE tunnel Mesh Group ID";
    }
  }

  grouping LDP-INTF {
    description "MPLS LDP interface information";

    container vrf {
      description "VRF information";
      uses LDP-VRF-INFO;
    }
    leaf interface {
      xr:xr-xml-map "mpls_ldp_oper_data:Interface";
      type xr:Interface-name;
      description "Interface name";
    }
    leaf interface-name-xr {
      xr:xr-xml-map "mpls_ldp_oper_data:interface-name-xr";
      type string;
      description "Interface name";
    }
    leaf ldp-enabled {
      xr:xr-xml-map "mpls_ldp_oper_data:LDPEnabled";
      type boolean;
      description "LDP enabled";
    }
    leaf is-im-stale {
      xr:xr-xml-map "mpls_ldp_oper_data:IsIMStale";
      type boolean;
      description "Is IM information stale";
    }
    leaf ldp-config-mode {
      xr:xr-xml-map "mpls_ldp_oper_data:LDPConfigMode";
      type boolean;
      description "LDP config mode";
    }
    leaf ldp-autoconfig-disable {
      xr:xr-xml-map "mpls_ldp_oper_data:LDPAutoconfigDisable";
      type boolean;
      description "LDP autoconfig disable";
    }

    list te-mesh-grp {
      description "TE tunnel mesh-group";
      uses LDP-INTF-TE-MESH-GRP;
    }

    list auto-config {
      description "Auto config";
      uses LDP-INTF-AUTOCFG;
    }
  }

  grouping LDP-BINDING-SUMMARY-AF {
    description "MPLS LDP Binding Summary AF Information";
    leaf address-family {
      xr:xr-xml-map "mpls_ldp_oper_data:AddressFamily";
      type Ldp-af;
      description "Binding Summary Address Family";
    }
    leaf last-lib-update {
      xr:xr-xml-map "mpls_ldp_oper_data:LastLIBUpdate";
      type uint32;
      description "Last update to LIB local binding";
    }
    leaf lib-minimum-revision-sent-all {
      xr:xr-xml-map "mpls_ldp_oper_data:LIBMinimumRevisionSentAll";
      type uint32;
      description "Last update sent to all peers";
    }
    leaf binding-total {
      xr:xr-xml-map "mpls_ldp_oper_data:BindingTotal";
      type uint32;
      description "Total bindings";
    }
    leaf binding-local {
      xr:xr-xml-map "mpls_ldp_oper_data:BindingLocal";
      type uint32;
      description "Number of local bindings";
    }
    leaf binding-remote {
      xr:xr-xml-map "mpls_ldp_oper_data:BindingRemote";
      type uint32;
      description "Number of remote bindings";
    }
  }

  grouping LDP-BINDING-SUMMARY {
    description "MPLS LDP Binding Summary Information";

    container vrf {
      description "VRF information";
      uses LDP-VRF-INFO;
    }
    leaf address-family {
      xr:xr-xml-map "mpls_ldp_oper_data:AddressFamily";
      type Ldp-af;
      description "Address Family";
    }
    leaf binding-no-route {
      xr:xr-xml-map "mpls_ldp_oper_data:BindingNoRoute";
      type uint32;
      description "Bindings with no route";
    }
    leaf binding-local-no-route {
      xr:xr-xml-map "mpls_ldp_oper_data:BindingLocalNoRoute";
      type uint32;
      description "Local bindings with no route";
    }
    leaf binding-local-null {
      xr:xr-xml-map "mpls_ldp_oper_data:BindingLocalNull";
      type uint32;
      description "Number of local null bindings";
    }
    leaf binding-local-implicit-null {
      xr:xr-xml-map "mpls_ldp_oper_data:BindingLocalImplicitNull";
      type uint32;
      description "Number of local implicit null bindings";
    }
    leaf binding-local-explicit-null {
      xr:xr-xml-map "mpls_ldp_oper_data:BindingLocalExplicitNull";
      type uint32;
      description "Number of local explicit null bindings";
    }
    leaf binding-local-non-null {
      xr:xr-xml-map "mpls_ldp_oper_data:BindingLocalNonNull";
      type uint32;
      description "Number of local non-null bindings";
    }
    leaf binding-local-oor {
      xr:xr-xml-map "mpls_ldp_oper_data:BindingLocalOOR";
      type uint32;
      description
        "Number of local bindings        needing label -
        OOR";
    }
    leaf lowest-allocated-label {
      xr:xr-xml-map "mpls_ldp_oper_data:LowestAllocatedLabel";
      type uint32;
      description "Lowest allocated label";
    }
    leaf highest-allocated-label {
      xr:xr-xml-map "mpls_ldp_oper_data:HighestAllocatedLabel";
      type uint32;
      description "Highest allocated label";
    }

    list bind-af {
      max-elements "2";
      description "bind af";
      uses LDP-BINDING-SUMMARY-AF;
    }
  }

  grouping LDP-IGP-SYNC-DELAY-RESTART-INFO {
    description "MPLS LDP IGP Sync Restart Delay Information";
    leaf configured {
      xr:xr-xml-map "mpls_ldp_oper_data:Configured";
      type boolean;
      description "Is restart delay configured";
    }
    leaf delay-secs {
      xr:xr-xml-map "mpls_ldp_oper_data:DelaySecs";
      type uint32;
      description "Delay time";
    }
    leaf timer-running {
      xr:xr-xml-map "mpls_ldp_oper_data:TimerRunning";
      type boolean;
      description "Is restart delay timer running";
    }
    leaf remaining-secs {
      xr:xr-xml-map "mpls_ldp_oper_data:RemainingSecs";
      type uint32;
      description "Delay timer remaining time";
    }
  }

  grouping LDP-IGP-SYNC-INTF-GR-ONLY {
    description
      "MPLS LDP IGP Sync Interface GR-only reachable
      Peer Information";
    leaf peer-id {
      xr:xr-xml-map "mpls_ldp_oper_data:PeerID";
      type String-td2;
      description "Peer Identifier";
    }
    leaf is-chkpt-created {
      xr:xr-xml-map "mpls_ldp_oper_data:IsChkptCreated";
      type boolean;
      description "Is created due to checkpointing";
    }
  }

  grouping LDP-IGP-SYNC-INTF-PEER {
    description "MPLS LDP IGP Sync Interface Peer Information";
    leaf peer-id {
      xr:xr-xml-map "mpls_ldp_oper_data:PeerID";
      type String-td2;
      description "Peer Identifier";
    }
    leaf is-gr-enabled {
      xr:xr-xml-map "mpls_ldp_oper_data:IsGREnabled";
      type boolean;
      description "Is GR enabled session";
    }
  }

  grouping LDP-IGP-SYNC-INFO {
    description "MPLS LDP IGP Sync Information";

    container vrf {
      description "VRF information";
      uses LDP-VRF-INFO;
    }
    leaf interface-name-xr {
      xr:xr-xml-map "mpls_ldp_oper_data:interface-name-xr";
      type string;
      description "Interface name";
    }
    leaf igp-sync-state {
      xr:xr-xml-map "mpls_ldp_oper_data:IGPSyncState";
      type Ldp-igp-sync-state;
      description "IGP Sync state";
    }
    leaf igp-sync-delay {
      xr:xr-xml-map "mpls_ldp_oper_data:IGPSyncDelay";
      type uint32;
      units "second";
      description "IGP sync delay in seconds";
    }
    leaf is-delay-timer-running {
      xr:xr-xml-map "mpls_ldp_oper_data:IsDelayTimerRunning";
      type boolean;
      description "Is sync delay timer running";
    }
    leaf delay-timer-remaining {
      xr:xr-xml-map "mpls_ldp_oper_data:DelayTimerRemaining";
      type uint32;
      units "second";
      description
        "Remaining timer (seconds) till expiry of sync
        delay timer";
    }
    leaf igp-sync-down-reason {
      xr:xr-xml-map "mpls_ldp_oper_data:IGPSyncDownReason";
      type Ldp-igp-sync-down-reason;
      description "Reason IGP Sync Not Achieved";
    }

    list peers {
      description "Interface Peers";
      uses LDP-IGP-SYNC-INTF-PEER;
    }

    list gr-only-peer {
      description "Interface GR-only reachable peers";
      uses LDP-IGP-SYNC-INTF-GR-ONLY;
    }
  }

  grouping LDP-TIB-ENTRY-REMOTE {
    description "MPLS LDP Remote Binding Information";

    container assigning-peer-ldp-ident {
      description "Assigning peer";
      uses LDP-LDPID-INFO;
    }
    leaf remote-label {
      xr:xr-xml-map "mpls_ldp_oper_data:RemoteLabel";
      type uint32;
      description "Remote Label";
    }
    leaf is-stale {
      xr:xr-xml-map "mpls_ldp_oper_data:IsStale";
      type boolean;
      description "Is the entry stale";
    }
    leaf is-elc {
      xr:xr-xml-map "mpls_ldp_oper_data:IsElc";
      type boolean;
      description "Is the entry entropy label capable";
    }
  }

  grouping LDP-TIB-ENTRY-DETAIL {
    description "MPLS LDP Binding Detail Information";

    container vrf {
      description "VRF information";
      uses LDP-VRF-INFO;
    }

    container prefix-xr {
      description "IP Prefix";
      uses LDP-IP-ADDR-T-UNION;
    }
    leaf prefix-length {
      xr:xr-xml-map "mpls_ldp_oper_data:PrefixLength";
      type uint8;
      description "Prefix Length";
    }
    leaf local-label {
      xr:xr-xml-map "mpls_ldp_oper_data:LocalLabel";
      type uint32;
      description "Local label";
    }
    leaf le-local-binding-revision {
      xr:xr-xml-map "mpls_ldp_oper_data:LELocalBindingRevision";
      type uint32;
      description "Local Binding revision";
    }
    leaf le-local-label-state {
      xr:xr-xml-map "mpls_ldp_oper_data:LELocalLabelState";
      type Local-label-state;
      description "Local label state";
    }
    leaf is-no-route {
      xr:xr-xml-map "mpls_ldp_oper_data:IsNoRoute";
      type boolean;
      description "No route";
    }
    leaf label-oor {
      xr:xr-xml-map "mpls_ldp_oper_data:LabelOOR";
      type boolean;
      description "Label space depletion OOR";
    }
    leaf advertise-prefix-acl {
      xr:xr-xml-map "mpls_ldp_oper_data:AdvertisePrefixACL";
      type string;
      description "Advertise Prerfix ACL";
    }
    leaf advertise-tsr-acl {
      xr:xr-xml-map "mpls_ldp_oper_data:AdvertiseTsrACL";
      type string;
      description "Advertise TSR ACL";
    }
    leaf config-enforced-local-label-value {
      xr:xr-xml-map "mpls_ldp_oper_data:ConfigEnforcedLocalLabelVal"+
        "ue";
      type boolean;
      description "Config/User enforced local label value";
    }
    leaf is-elc {
      xr:xr-xml-map "mpls_ldp_oper_data:IsElc";
      type boolean;
      description "Is the entry entropy label capable";
    }

    list remote-binding {
      description "Remote binding";
      uses LDP-TIB-ENTRY-REMOTE;
    }

    list peers-advertised-to {
      description "Peers this entry is advertised to";
      uses LDP-LDPID-INFO;
    }

    list peers-acked {
      description "Peers that have ACKed this entry";
      uses LDP-LDPID-INFO;
    }
  }

  grouping LDP-INTF-SUM {
    description "MPLS LDP interface summary";
    leaf known-ip-interface-count {
      xr:xr-xml-map "mpls_ldp_oper_data:KnownIpInterfaceCount";
      type uint32;
      description "Number of known IP Interfaces";
    }
    leaf known-ip-interface-ldp-enabled {
      xr:xr-xml-map "mpls_ldp_oper_data:KnownIpInterfaceLDPEnabled";
      type uint32;
      description "Number of known IP Interfaces with LDP Enabled";
    }
    leaf ldp-configured-attached-interface {
      xr:xr-xml-map "mpls_ldp_oper_data:LDPConfiguredAttachedInterf"+
        "ace";
      type uint32;
      description "Number of attached interfaces configured in LDP";
    }
    leaf ldp-configured-te-interface {
      xr:xr-xml-map "mpls_ldp_oper_data:LDPConfiguredTEInterface";
      type uint32;
      description
        "Number of TE tunnel interfaces configured in LDP";
    }
    leaf forward-references {
      xr:xr-xml-map "mpls_ldp_oper_data:ForwardReferences";
      type uint32;
      description "Number of forward referenced interfaces";
    }
    leaf auto-config-disabled {
      xr:xr-xml-map "mpls_ldp_oper_data:AutoConfigDisabled";
      type uint32;
      description "Autoconfigure disabled";
    }
    leaf auto-config {
      xr:xr-xml-map "mpls_ldp_oper_data:AutoConfig";
      type uint32;
      description "Auto-configured interfaces";
    }
    leaf auto-config-forward-reference-interfaces {
      xr:xr-xml-map "mpls_ldp_oper_data:AutoConfigForwardReferenceI"+
        "nterfaces";
      type uint32;
      description "Auto-configured forward references";
    }
  }

  grouping LDP-SUMMARY-COMMON {
    description "MPLS LDP common summary Information";
    leaf address-families {
      xr:xr-xml-map "mpls_ldp_oper_data:AddressFamilies";
      type Ldp-af;
      description "Address Families enabled";
    }
    leaf number-of-ipv4af {
      xr:xr-xml-map "mpls_ldp_oper_data:NumberOfIPv4AF";
      type uint32;
      description "Number of IPv4 address-families enabled";
    }
    leaf number-of-ipv6af {
      xr:xr-xml-map "mpls_ldp_oper_data:NumberOfIPv6AF";
      type uint32;
      description "Number of IPv6 address-families enabled";
    }
    leaf number-of-neighbors {
      xr:xr-xml-map "mpls_ldp_oper_data:NumberOfNeighbors";
      type uint32;
      description "Number of neighbors";
    }
    leaf number-of-nsr-synced-neighbors {
      xr:xr-xml-map "mpls_ldp_oper_data:NumberOfNSRSyncedNeighbors";
      type uint32;
      description "Number of NSR-synced/operational neighbors";
    }
    leaf number-of-graceful-restart-neighbors {
      xr:xr-xml-map "mpls_ldp_oper_data:NumberOfGracefulRestartNeig"+
        "hbors";
      type uint32;
      description "Number of Graceful Restart neighbors";
    }
    leaf number-of-downstream-on-demand-neighbors {
      xr:xr-xml-map "mpls_ldp_oper_data:NumberOfDownstreamOnDemandN"+
        "eighbors";
      type uint32;
      description "Number of Downstream-On-Demand neighbors";
    }
    leaf number-of-ipv4-hello-adj {
      xr:xr-xml-map "mpls_ldp_oper_data:NumberOfIPv4HelloAdj";
      type uint32;
      description "Number of LDP discovery IPv4 hello adjacencies";
    }
    leaf number-of-ipv6-hello-adj {
      xr:xr-xml-map "mpls_ldp_oper_data:NumberOfIPv6HelloAdj";
      type uint32;
      description "Number of LDP discovery IPv6 hello adjacencies";
    }
    leaf number-of-ipv4-routes {
      xr:xr-xml-map "mpls_ldp_oper_data:NumberOfIPv4Routes";
      type uint32;
      description "Number of resolved IPv4 routes";
    }
    leaf number-of-ipv6-routes {
      xr:xr-xml-map "mpls_ldp_oper_data:NumberOfIPv6Routes";
      type uint32;
      description "Number of resolved IPv6 routes";
    }
    leaf number-of-ipv4-local-addresses {
      xr:xr-xml-map "mpls_ldp_oper_data:NumberOfIPv4LocalAddresses";
      type uint32;
      description "Number of IPv4 local addresses";
    }
    leaf number-of-ipv6-local-addresses {
      xr:xr-xml-map "mpls_ldp_oper_data:NumberOfIPv6LocalAddresses";
      type uint32;
      description "Number of IPv6 local addresses";
    }
    leaf number-of-ldp-interfaces {
      xr:xr-xml-map "mpls_ldp_oper_data:NumberOfLDPInterfaces";
      type uint32;
      description "Number of LDP configured interfaces";
    }
    leaf number-of-ipv4ldp-interfaces {
      xr:xr-xml-map "mpls_ldp_oper_data:NumberOfIPv4LDPInterfaces";
      type uint32;
      description "Number of LDP IPv4 configured interfaces";
    }
    leaf number-of-ipv6ldp-interfaces {
      xr:xr-xml-map "mpls_ldp_oper_data:NumberOfIPv6LDPInterfaces";
      type uint32;
      description "Number of LDP IPv6 configured interfaces";
    }
    leaf number-of-bindings-ipv4 {
      xr:xr-xml-map "mpls_ldp_oper_data:NumberOfBindingsIPv4";
      type uint32;
      description "Total number of ipv4 bindings";
    }
    leaf number-of-bindings-ipv6 {
      xr:xr-xml-map "mpls_ldp_oper_data:NumberOfBindingsIPv6";
      type uint32;
      description "Total number of ipv6 bindings";
    }
    leaf number-of-local-bindings-ipv4 {
      xr:xr-xml-map "mpls_ldp_oper_data:NumberOfLocalBindingsIPv4";
      type uint32;
      description "Total number of ipv4 local label bindings";
    }
    leaf number-of-local-bindings-ipv6 {
      xr:xr-xml-map "mpls_ldp_oper_data:NumberOfLocalBindingsIPv6";
      type uint32;
      description "Total number of ipv6 local label bindings";
    }
    leaf number-of-remote-bindings-ipv4 {
      xr:xr-xml-map "mpls_ldp_oper_data:NumberOfRemoteBindingsIPv4";
      type uint32;
      description "Total number of ipv4 remote label bindings";
    }
    leaf number-of-remote-bindings-ipv6 {
      xr:xr-xml-map "mpls_ldp_oper_data:NumberOfRemoteBindingsIPv6";
      type uint32;
      description "Total number of ipv6 remote label bindings";
    }
  }

  grouping LDP-SUMMARY-VRF {
    description "MPLS LDP per VRF summarized Information";

    container vrf {
      description "VRF information";
      uses LDP-VRF-INFO;
    }

    container common {
      description "Common Summary information";
      uses LDP-SUMMARY-COMMON;
    }
  }

  grouping LDP-CAP-DESC {
    description "MPLS LDP Capability Description";
    leaf type {
      xr:xr-xml-map "mpls_ldp_oper_data:Type";
      type uint16;
      description "Capability type (IANA assigned)";
    }
    leaf description {
      xr:xr-xml-map "mpls_ldp_oper_data:Description";
      type string {
        length "0..80";
      }
      description "Capability description";
    }
    leaf capability-data-length {
      xr:xr-xml-map "mpls_ldp_oper_data:CapabilityDataLength";
      type uint16;
      description "Capability data length";
    }
    leaf capability-data {
      xr:xr-xml-map "mpls_ldp_oper_data:CapabilityData";
      type string;
      description "Capability data";
    }
  }

  grouping LDP-CAP-INFO {
    description "MPLS LDP Capability Information";

    container capability {
      description "Capability information";
      uses LDP-CAP-DESC;
    }
    leaf capability-owner {
      xr:xr-xml-map "mpls_ldp_oper_data:CapabilityOwner";
      type string;
      description "Capability owner";
    }
  }

  grouping LDP-IP-ADDR-T-UNION {
    description "LDP IP ADDR T UNION";
    leaf afi {
      xr:xr-xml-map "mpls_ldp_oper_data:AFI";
      type Ldp-af-id;
      description "AFI";
    }
    leaf dummy {
      xr:xr-xml-map "mpls_ldp_oper_data:Dummy";
      when "../afi = 'ldp-af-id-none'" {
        description "../AFI = 'LDP_AF_ID_NONE'";
      }
      type uint8;
      description "No Address";
    }
    leaf ipv4 {
      xr:xr-xml-map "mpls_ldp_oper_data:IPV4";
      when "../afi = 'ldp-af-id-ipv4'" {
        description "../AFI = 'LDP_AF_ID_IPV4'";
      }
      type Ldp-in-addr;
      description "IPv4 address type";
    }
    leaf ipv6 {
      xr:xr-xml-map "mpls_ldp_oper_data:IPV6";
      when "../afi = 'ldp-af-id-ipv6'" {
        description "../AFI = 'LDP_AF_ID_IPV6'";
      }
      type Ldp-in6-addr;
      description "IPv6 address type";
    }
  }

  grouping LDP-GR-DNBR-INTF-INFO {
    description "MPLS LDP GR DownNbr Interface Info";
    leaf address-family {
      xr:xr-xml-map "mpls_ldp_oper_data:AddressFamily";
      type Ldp-af-id;
      description "Interface adj Address Family";
    }
    leaf interface-handle {
      xr:xr-xml-map "mpls_ldp_oper_data:InterfaceHandle";
      type xr:Interface-name;
      description "Interfaces handle";
    }
  }

  grouping LDP-LDPID-INFO {
    description "MPLS LDP Identifier Information";
    leaf lsr-id {
      xr:xr-xml-map "mpls_ldp_oper_data:LSR_ID";
      type inet:ipv4-address;
      description "LSR identifier";
    }
    leaf label-space-id {
      xr:xr-xml-map "mpls_ldp_oper_data:LabelSpaceID";
      type uint16;
      description "Label space identifier";
    }
    leaf ldp-id {
      xr:xr-xml-map "mpls_ldp_oper_data:LDP_ID";
      type string;
      description "LDP identifier";
    }
  }

  grouping LDP-GR-NBR-INFO {
    description "MPLS LDP Graceful Restart Neighbor Information";

    container gr-peer {
      description "GR peer LDP Id";
      uses LDP-LDPID-INFO;
    }
    leaf connect-count {
      xr:xr-xml-map "mpls_ldp_oper_data:ConnectCount";
      type uint32;
      description "ConnectCount";
    }
    leaf is-neighbor-up {
      xr:xr-xml-map "mpls_ldp_oper_data:IsNeighborUp";
      type boolean;
      description "Is neighbor up";
    }
    leaf is-liveness-timer-running {
      xr:xr-xml-map "mpls_ldp_oper_data:IsLivenessTimerRunning";
      type boolean;
      description "Is liveness timer running";
    }
    leaf liveness-timer-remaining-seconds {
      xr:xr-xml-map "mpls_ldp_oper_data:LivenessTimerRemainingSecon"+
        "ds";
      type uint32;
      description "Remaining time from liveness timer";
    }
    leaf is-recovery-timer-running {
      xr:xr-xml-map "mpls_ldp_oper_data:IsRecoveryTimerRunning";
      type boolean;
      description "Is recovery timer running";
    }
    leaf recovery-timer-remaining-seconds {
      xr:xr-xml-map "mpls_ldp_oper_data:RecoveryTimerRemainingSecon"+
        "ds";
      type uint32;
      description "Recovery timer remining time";
    }
    leaf down-nbr-flap-count {
      xr:xr-xml-map "mpls_ldp_oper_data:DownNbrFlapCount";
      type uint8;
      description "Count of back2back flaps";
    }
    leaf down-nbr-flags {
      xr:xr-xml-map "mpls_ldp_oper_data:DownNbrFlags";
      type uint32;
      description "Flags";
    }
    leaf down-nbr-down-reason {
      xr:xr-xml-map "mpls_ldp_oper_data:DownNbrDownReason";
      type uint32;
      description "Session down reason code";
    }

    list down-nbr-interface {
      description "Interfaces bound to GR down Nbr";
      uses LDP-GR-DNBR-INTF-INFO;
    }

    list down-nbr-address {
      description "Addresses bound to GR down Nbr";
      uses LDP-IP-ADDR-T-UNION;
    }
  }

  grouping LDP-VRF-INFO {
    description "MPLS LDP VRF information";
    leaf name {
      xr:xr-xml-map "mpls_ldp_oper_data:Name";
      type string;
      description "VRF Name";
    }
    leaf id {
      xr:xr-xml-map "mpls_ldp_oper_data:Id";
      type uint32;
      description "VRF Id";
    }
  }

  grouping LDP-GR-GLOBAL-INFO {
    description "MPLS LDP Graceful Restart Information";

    container vrf {
      description "VRF information";
      uses LDP-VRF-INFO;
    }
    leaf is-forwarding-state-hold-timer-running {
      xr:xr-xml-map "mpls_ldp_oper_data:IsForwardingStateHoldTimerR"+
        "unning";
      type boolean;
      description
        "Is graceful restart forwarding state hold timer
        running";
    }
    leaf forwarding-state-hold-timer-remaining-seconds {
      xr:xr-xml-map "mpls_ldp_oper_data:ForwardingStateHoldTimerRem"+
        "ainingSeconds";
      type uint32;
      units "second";
      description
        "Forwarding state hold timer remaining time in
        seconds";
    }

    list graceful-restartable-neighbor {
      description "Vector of graceful restart neighbor information";
      uses LDP-GR-NBR-INFO;
    }
  }
}
