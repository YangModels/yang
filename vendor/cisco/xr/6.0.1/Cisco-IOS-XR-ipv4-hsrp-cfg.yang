module Cisco-IOS-XR-ipv4-hsrp-cfg {

  /*** NAMESPACE / PREFIX DEFINITION ***/

  namespace "http://cisco.com/ns/yang/Cisco-IOS-XR-ipv4-hsrp-cfg";


  prefix "ipv4-hsrp-cfg";

  /*** LINKAGE (IMPORTS / INCLUDES) ***/

  import ietf-inet-types { prefix "inet"; }

  import ietf-yang-types { prefix "yang"; }

  import Cisco-IOS-XR-types { prefix "xr"; }

  import Cisco-IOS-XR-snmp-agent-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ipv4-hsrp package configuration.

     This module contains definitions
     for the following management objects:
       hsrp: HSRP configuration

     This YANG module augments the
       Cisco-IOS-XR-snmp-agent-cfg
     module with configuration data.

     Copyright (c) 2013-2015 by Cisco Systems, Inc.
     All rights reserved.";

  revision "2015-11-09" {
    description
      "IOS XR 6.0 revision.";
  }

  typedef Hsrp-linklocal {
    type enumeration {
      enum manual {
        value 0;
        description "Manual Linklocal address configuration";
      }
      enum auto {
        value 1;
        description "Automatic Linklocal address configuration";
      }
      enum legacy {
        value 2;
        description
          "Automatic legacy-compatible Linklocal address
          configuration";
      }
    }
    description "Hsrp linklocal";
  }

  container hsrp {
    xr:xr-xml-map "hsrp_cfg:HSRP";
    description "HSRP configuration";

    container interfaces {
      xr:xr-xml-map "hsrp_cfg:InterfaceTable";
      description "Interface Table for HSRP configuration";

      list interface {
        xr:xr-xml-map "hsrp_cfg:Interface";
        key "interface-name";
        description "Per-interface HSRP configuration";

        container ipv6 {
          xr:xr-xml-map "hsrp_ipv6_cfg:IPv6";
          description "IPv6 HSRP configuration";

          container version2 {
            xr:xr-xml-map "hsrp_ipv6_cfg:Version2";
            description "Version 2 HSRP configuration";

            container groups {
              xr:xr-xml-map "hsrp_ipv6_cfg:GroupTable";
              description "The HSRP group configuration table";

              list group {
                xr:xr-xml-map "hsrp_ipv6_cfg:Group";
                key "group-number";
                description "The HSRP group being configured";

                container bfd {
                  xr:xr-xml-map "hsrp_ipv6_cfg:BFD";
                  description
                    "Enable use of Bidirectional Forwarding
                    Detection";
                  leaf address {
                    xr:xr-xml-map "hsrp_ipv6_cfg:Address";
                    type inet:ipv6-address-no-zone;
                    description "Enable BFD for this remote IP";
                  }
                  leaf interface-name {
                    xr:xr-xml-map "hsrp_ipv6_cfg:InterfaceName";
                    type xr:Interface-name;
                    description "Interface name to run BFD";
                  }
                }

                container tracked-interfaces {
                  xr:xr-xml-map "hsrp_ipv6_cfg:TrackedInterfaceTabl"+
                    "e";
                  description
                    "The HSRP tracked interface configuration
                    table";

                  list tracked-interface {
                    xr:xr-xml-map "hsrp_ipv6_cfg:TrackedInterface";
                    key "interface-name";
                    description "Interface being tracked";
                    leaf interface-name {
                      xr:xr-xml-map "hsrp_ipv6_cfg:InterfaceName";
                      type xr:Interface-name;
                      description "Interface being tracked";
                    }
                    leaf priority-decrement {
                      xr:xr-xml-map "hsrp_ipv6_cfg:PriorityDecremen"+
                        "t";
                      type uint32 {
                        range "1..255";
                      }
                      mandatory true;
                      description "Priority decrement";
                    }
                  }
                }

                container tracked-objects {
                  xr:xr-xml-map "hsrp_ipv6_cfg:TrackedObjectTable";
                  description
                    "The HSRP tracked interface configuration
                    table";

                  list tracked-object {
                    xr:xr-xml-map "hsrp_ipv6_cfg:TrackedObject";
                    key "object-name";
                    description "Object being tracked";
                    leaf object-name {
                      xr:xr-xml-map "hsrp_ipv6_cfg:ObjectName";
                      type xr:Cisco-ios-xr-string;
                      description "Interface being tracked";
                    }
                    leaf priority-decrement {
                      xr:xr-xml-map "hsrp_ipv6_cfg:PriorityDecremen"+
                        "t";
                      type uint32 {
                        range "1..255";
                      }
                      mandatory true;
                      description "Priority decrement";
                    }
                  }
                }

                container timers {
                  xr:xr-xml-map "hsrp_ipv6_cfg:Timers";
                  description "Hello and hold timers";
                  leaf hello-msec-flag {
                    xr:xr-xml-map "hsrp_ipv6_cfg:HelloMsecFlag";
                    type boolean;
                    default "false";
                    description
                      "TRUE - Hello time configured in
                      milliseconds, FALSE - Hello time
                      configured in seconds";
                  }
                  leaf hello-msec {
                    xr:xr-xml-map "hsrp_ipv6_cfg:HelloMsec";
                    type uint32 {
                      range "100..3000";
                    }
                    units "millisecond";
                    description "Hello time in msecs";
                  }
                  leaf hello-sec {
                    xr:xr-xml-map "hsrp_ipv6_cfg:HelloSec";
                    type uint32 {
                      range "1..255";
                    }
                    units "second";
                    default "3";
                    description "Hello time in seconds";
                  }
                  leaf hold-msec-flag {
                    xr:xr-xml-map "hsrp_ipv6_cfg:HoldMsecFlag";
                    type boolean;
                    default "false";
                    description
                      "TRUE - Hold time configured in
                      milliseconds, FALSE - Hold time
                      configured in seconds";
                  }
                  leaf hold-msec {
                    xr:xr-xml-map "hsrp_ipv6_cfg:HoldMsec";
                    type uint32 {
                      range "100..3000";
                    }
                    units "millisecond";
                    description "Hold time in msecs";
                  }
                  leaf hold-sec {
                    xr:xr-xml-map "hsrp_ipv6_cfg:HoldSec";
                    type uint32 {
                      range "1..255";
                    }
                    units "second";
                    default "10";
                    description "Hold time in seconds";
                  }
                }

                container link-local-ipv6-address {
                  xr:xr-xml-map "hsrp_ipv6_cfg:LinkLocalIPv6Address";
                  description
                    "The HSRP IPv6 virtual linklocal address";
                  leaf address {
                    xr:xr-xml-map "hsrp_ipv6_cfg:Address";
                    when "../auto-configure = 'manual'" {
                      description "../AutoConfigure = Manual";
                    }
                    type inet:ipv6-address-no-zone;
                    description
                      "HSRP IPv6 virtual linklocal address";
                  }
                  leaf auto-configure {
                    xr:xr-xml-map "hsrp_ipv6_cfg:AutoConfigure";
                    type Hsrp-linklocal;
                    default "manual";
                    description "Linklocal Configuration Type";
                  }
                }

                container global-ipv6-addresses {
                  xr:xr-xml-map "hsrp_ipv6_cfg:GlobalIPv6AddressTab"+
                    "le";
                  description
                    "The table of HSRP virtual global IPv6
                    addresses";

                  list global-ipv6-address {
                    xr:xr-xml-map "hsrp_ipv6_cfg:GlobalIPv6Address";
                    key "address";
                    description
                      "A HSRP virtual global IPv6 IP address";
                    leaf address {
                      xr:xr-xml-map "hsrp_ipv6_cfg:Address";
                      type inet:ipv6-address-no-zone;
                      description
                        "HSRP virtual global IPv6 address";
                    }
                  }
                }
                leaf priority {
                  xr:xr-xml-map "hsrp_ipv6_cfg:Priority";
                  type uint32 {
                    range "0..255";
                  }
                  default "100";
                  description "Priority value";
                }
                leaf preempt {
                  xr:xr-xml-map "hsrp_ipv6_cfg:Preempt";
                  type int32;
                  default "0";
                  description "Force active if higher priority";
                }
                leaf session-name {
                  xr:xr-xml-map "hsrp_ipv6_cfg:SessionName";
                  type xr:Cisco-ios-xr-string {
                    length "0..16";
                  }
                  description "HSRP Session name (for MGO)";
                }
                leaf virtual-mac-address {
                  xr:xr-xml-map "hsrp_ipv6_cfg:VirtualMACAddress";
                  type yang:mac-address;
                  description "HSRP MAC address";
                }
                leaf group-number {
                  xr:xr-xml-map "hsrp_ipv6_cfg:GroupNumber";
                  type uint32 {
                    range "0..4095";
                  }
                  description "HSRP group number";
                }
              }
            }
          }

          container slave-groups {
            xr:xr-xml-map "hsrp_ipv6_slave_cfg:SlaveGroupTable";
            description "The HSRP slave group configuration table";

            list slave-group {
              xr:xr-xml-map "hsrp_ipv6_slave_cfg:SlaveGroup";
              key "slave-group-number";
              description "The HSRP slave group being configured";

              container link-local-ipv6-address {
                xr:xr-xml-map "hsrp_ipv6_slave_cfg:LinkLocalIPv6Add"+
                  "ress";
                description
                  "The HSRP IPv6 virtual linklocal address";
                leaf address {
                  xr:xr-xml-map "hsrp_ipv6_slave_cfg:Address";
                  when "../auto-configure = 'manual'" {
                    description "../AutoConfigure = Manual";
                  }
                  type inet:ipv6-address-no-zone;
                  description "HSRP IPv6 virtual linklocal address";
                }
                leaf auto-configure {
                  xr:xr-xml-map "hsrp_ipv6_slave_cfg:AutoConfigure";
                  type Hsrp-linklocal;
                  default "manual";
                  description "Linklocal Configuration Type";
                }
              }

              container global-ipv6-addresses {
                xr:xr-xml-map "hsrp_ipv6_slave_cfg:GlobalIPv6Addres"+
                  "sTable";
                description
                  "The table of HSRP virtual global IPv6
                  addresses";

                list global-ipv6-address {
                  xr:xr-xml-map "hsrp_ipv6_slave_cfg:GlobalIPv6Addr"+
                    "ess";
                  key "address";
                  description
                    "A HSRP virtual global IPv6 IP address";
                  leaf address {
                    xr:xr-xml-map "hsrp_ipv6_slave_cfg:Address";
                    type inet:ipv6-address-no-zone;
                    description "HSRP virtual global IPv6 address";
                  }
                }
              }
              leaf follow {
                xr:xr-xml-map "hsrp_ipv6_slave_cfg:Follow";
                type string;
                description
                  "HSRP Group name for this slave to follow";
              }
              leaf virtual-mac-address {
                xr:xr-xml-map "hsrp_ipv6_slave_cfg:VirtualMACAddres"+
                  "s";
                type yang:mac-address;
                description "HSRP MAC address";
              }
              leaf slave-group-number {
                xr:xr-xml-map "hsrp_ipv6_slave_cfg:SlaveGroupNumber";
                type uint32 {
                  range "0..4095";
                }
                description "HSRP group number";
              }
            }
          }
        }

        container bfd {
          xr:xr-xml-map "hsrp_cfg:BFD";
          description "BFD configuration";
          leaf detection-multiplier {
            xr:xr-xml-map "hsrp_cfg:DetectionMultiplier";
            xr:xr-cli-map "hsrp interface <interface> hsrp bfd mult"+
              "iplier <number> ";
            type uint32 {
              range "2..50";
            }
            description
              "Detection multiplier for BFD sessions created
              by hsrp";
          }
          leaf interval {
            xr:xr-xml-map "hsrp_cfg:Interval";
            xr:xr-cli-map "hsrp interface <interface> hsrp bfd mini"+
              "mum-interval <number> ";
            type uint32 {
              range "3..30000";
            }
            units "millisecond";
            description
              "Hello interval for BFD sessions created by
              hsrp";
          }
        }

        container delay {
          xr:xr-xml-map "hsrp_cfg:Delay";
          description "Minimum and Reload Delay";
          leaf minimum-delay {
            xr:xr-xml-map "hsrp_cfg:MinimumDelay";
            type uint32 {
              range "0..10000";
            }
            units "second";
            default "1";
            description "Minimum delay in seconds";
          }
          leaf reload-delay {
            xr:xr-xml-map "hsrp_cfg:ReloadDelay";
            type uint32 {
              range "0..10000";
            }
            units "second";
            default "5";
            description "Reload delay in seconds";
          }
        }

        container ipv4 {
          xr:xr-xml-map "hsrp_cfg:IPv4";
          description "IPv4 HSRP configuration";

          container slave-groups {
            xr:xr-xml-map "hsrp_slave_cfg:SlaveGroupTable";
            description "The HSRP slave group configuration table";

            list slave-group {
              xr:xr-xml-map "hsrp_slave_cfg:SlaveGroup";
              key "slave-group-number";
              description "The HSRP slave group being configured";

              container secondary-ipv4-addresses {
                xr:xr-xml-map "hsrp_slave_cfg:SecondaryIPv4AddressT"+
                  "able";
                description "Secondary HSRP IP address Table";

                list secondary-ipv4-address {
                  xr:xr-xml-map "hsrp_slave_cfg:SecondaryIPv4Addres"+
                    "s";
                  key "address";
                  description "Secondary HSRP IP address";
                  leaf address {
                    xr:xr-xml-map "hsrp_slave_cfg:Address";
                    type inet:ipv4-address-no-zone;
                    description "HSRP IP address";
                  }
                }
              }
              leaf follow {
                xr:xr-xml-map "hsrp_slave_cfg:Follow";
                type string;
                description
                  "HSRP Group name for this slave to follow";
              }
              leaf virtual-mac-address {
                xr:xr-xml-map "hsrp_slave_cfg:VirtualMACAddress";
                type yang:mac-address;
                description "HSRP MAC address";
              }
              leaf primary-ipv4-address {
                xr:xr-xml-map "hsrp_slave_cfg:PrimaryIPv4Address";
                type inet:ipv4-address-no-zone;
                description "Primary HSRP IP address";
              }
              leaf slave-group-number {
                xr:xr-xml-map "hsrp_slave_cfg:SlaveGroupNumber";
                type uint32 {
                  range "0..4095";
                }
                description "HSRP group number";
              }
            }
          }

          container version1 {
            xr:xr-xml-map "hsrp_cfg:Version1";
            description "Version 1 HSRP configuration";

            container groups {
              xr:xr-xml-map "hsrp_cfg:GroupTable";
              description "The HSRP group configuration table";

              list group {
                xr:xr-xml-map "hsrp_cfg:Group";
                key "group-number";
                description "The HSRP group being configured";

                container tracked-interfaces {
                  xr:xr-xml-map "hsrp_cfg:TrackedInterfaceTable";
                  description
                    "The HSRP tracked interface configuration
                    table";

                  list tracked-interface {
                    xr:xr-xml-map "hsrp_cfg:TrackedInterface";
                    xr:xr-cli-map "hsrp interface <interface> hsrp "+
                      "(<number>) track <interface> [<number>] ";
                    key "interface-name";
                    description "Interface being tracked";
                    leaf interface-name {
                      xr:xr-xml-map "hsrp_cfg:InterfaceName";
                      type xr:Interface-name;
                      description "Interface being tracked";
                    }
                    leaf priority-decrement {
                      xr:xr-xml-map "hsrp_cfg:PriorityDecrement";
                      type uint32 {
                        range "1..255";
                      }
                      mandatory true;
                      description "Priority decrement";
                    }
                  }
                }

                container bfd {
                  xr:xr-xml-map "hsrp_cfg:BFD";
                  description
                    "Enable use of Bidirectional Forwarding
                    Detection";
                  leaf address {
                    xr:xr-xml-map "hsrp_cfg:Address";
                    type inet:ipv4-address-no-zone;
                    description "Enable BFD for this remote IP";
                  }
                  leaf interface-name {
                    xr:xr-xml-map "hsrp_cfg:InterfaceName";
                    type xr:Interface-name;
                    description "Interface name to run BFD";
                  }
                }

                container tracked-objects {
                  xr:xr-xml-map "hsrp_cfg:TrackedObjectTable";
                  description
                    "The HSRP tracked interface configuration
                    table";

                  list tracked-object {
                    xr:xr-xml-map "hsrp_cfg:TrackedObject";
                    key "object-name";
                    description "Object being tracked";
                    leaf object-name {
                      xr:xr-xml-map "hsrp_cfg:ObjectName";
                      type xr:Cisco-ios-xr-string;
                      description "Interface being tracked";
                    }
                    leaf priority-decrement {
                      xr:xr-xml-map "hsrp_cfg:PriorityDecrement";
                      type uint32 {
                        range "1..255";
                      }
                      mandatory true;
                      description "Priority decrement";
                    }
                  }
                }

                container timers {
                  xr:xr-xml-map "hsrp_cfg:Timers";
                  description "Hello and hold timers";
                  leaf hello-msec-flag {
                    xr:xr-xml-map "hsrp_cfg:HelloMsecFlag";
                    type boolean;
                    default "false";
                    description
                      "TRUE - Hello time configured in
                      milliseconds, FALSE - Hello time
                      configured in seconds";
                  }
                  leaf hello-msec {
                    xr:xr-xml-map "hsrp_cfg:HelloMsec";
                    type uint32 {
                      range "100..3000";
                    }
                    units "millisecond";
                    description "Hello time in msecs";
                  }
                  leaf hello-sec {
                    xr:xr-xml-map "hsrp_cfg:HelloSec";
                    type uint32 {
                      range "1..255";
                    }
                    units "second";
                    default "3";
                    description "Hello time in seconds";
                  }
                  leaf hold-msec-flag {
                    xr:xr-xml-map "hsrp_cfg:HoldMsecFlag";
                    type boolean;
                    default "false";
                    description
                      "TRUE - Hold time configured in
                      milliseconds, FALSE - Hold time
                      configured in seconds";
                  }
                  leaf hold-msec {
                    xr:xr-xml-map "hsrp_cfg:HoldMsec";
                    type uint32 {
                      range "100..3000";
                    }
                    units "millisecond";
                    description "Hold time in msecs";
                  }
                  leaf hold-sec {
                    xr:xr-xml-map "hsrp_cfg:HoldSec";
                    type uint32 {
                      range "1..255";
                    }
                    units "second";
                    default "10";
                    description "Hold time in seconds";
                  }
                }

                container primary-ipv4-address {
                  xr:xr-xml-map "hsrp_cfg:PrimaryIPv4Address";
                  description "Primary HSRP IP address";
                  leaf virtual-ip-learn {
                    xr:xr-xml-map "hsrp_cfg:VirtualIPLearn";
                    type boolean;
                    description
                      "TRUE if the HSRP protocol is to learn the
                      virtual IP address it is to use";
                  }
                  leaf address {
                    xr:xr-xml-map "hsrp_cfg:Address";
                    when "../virtual-ip-learn = 0" {
                      description "../VirtualIPLearn = <expr>";
                    }
                    type inet:ipv4-address-no-zone;
                    description "HSRP IP address.";
                  }
                }

                container secondary-ipv4-addresses {
                  xr:xr-xml-map "hsrp_cfg:SecondaryIPv4AddressTable";
                  description "Secondary HSRP IP address Table";

                  list secondary-ipv4-address {
                    xr:xr-xml-map "hsrp_cfg:SecondaryIPv4Address";
                    xr:xr-cli-map "hsrp interface <interface> hsrp "+
                      "(<number>) ipv4 <IPv4 address> secondary ";
                    key "address";
                    description "Secondary HSRP IP address";
                    leaf address {
                      xr:xr-xml-map "hsrp_cfg:Address";
                      type inet:ipv4-address-no-zone;
                      description "HSRP IP address";
                    }
                  }
                }
                leaf authentication {
                  xr:xr-xml-map "hsrp_cfg:Authentication";
                  xr:xr-cli-map "hsrp interface <interface> hsrp (<"+
                    "number>) authentication <string> ";
                  type string {
                    length "0..8";
                  }
                  default "cisco";
                  description "Authentication string";
                }
                leaf session-name {
                  xr:xr-xml-map "hsrp_cfg:SessionName";
                  type xr:Cisco-ios-xr-string {
                    length "0..16";
                  }
                  description "HSRP Session name (for MGO)";
                }
                leaf priority {
                  xr:xr-xml-map "hsrp_cfg:Priority";
                  xr:xr-cli-map "hsrp interface <interface> hsrp (<"+
                    "number>) priority <number> ";
                  type uint32 {
                    range "0..255";
                  }
                  default "100";
                  description "Priority value";
                }
                leaf preempt {
                  xr:xr-xml-map "hsrp_cfg:Preempt";
                  xr:xr-cli-map "hsrp interface <interface> hsrp (<"+
                    "number>) preempt [delay <number>] ";
                  type int32;
                  default "0";
                  description "Force active if higher priority";
                }
                leaf virtual-mac-address {
                  xr:xr-xml-map "hsrp_cfg:VirtualMACAddress";
                  type yang:mac-address;
                  description "HSRP MAC address";
                }
                leaf group-number {
                  xr:xr-xml-map "hsrp_cfg:GroupNumber";
                  type uint32 {
                    range "0..255";
                  }
                  description "HSRP group number";
                }
              }
            }
          }

          container version2 {
            xr:xr-xml-map "hsrp_ipv4_v2_cfg:Version2";
            description "Version 2 HSRP configuration";

            container groups {
              xr:xr-xml-map "hsrp_ipv4_v2_cfg:GroupTable";
              description "The HSRP group configuration table";

              list group {
                xr:xr-xml-map "hsrp_ipv4_v2_cfg:Group";
                key "group-number";
                description "The HSRP group being configured";

                container secondary-ipv4-addresses {
                  xr:xr-xml-map "hsrp_ipv4_v2_cfg:SecondaryIPv4Addr"+
                    "essTable";
                  description "Secondary HSRP IP address Table";

                  list secondary-ipv4-address {
                    xr:xr-xml-map "hsrp_ipv4_v2_cfg:SecondaryIPv4Ad"+
                      "dress";
                    key "address";
                    description "Secondary HSRP IP address";
                    leaf address {
                      xr:xr-xml-map "hsrp_ipv4_v2_cfg:Address";
                      type inet:ipv4-address-no-zone;
                      description "HSRP IP address";
                    }
                  }
                }

                container bfd {
                  xr:xr-xml-map "hsrp_ipv4_v2_cfg:BFD";
                  description
                    "Enable use of Bidirectional Forwarding
                    Detection";
                  leaf address {
                    xr:xr-xml-map "hsrp_ipv4_v2_cfg:Address";
                    type inet:ipv4-address-no-zone;
                    description "Enable BFD for this remote IP";
                  }
                  leaf interface-name {
                    xr:xr-xml-map "hsrp_ipv4_v2_cfg:InterfaceName";
                    type xr:Interface-name;
                    description "Interface name to run BFD";
                  }
                }

                container primary-ipv4-address {
                  xr:xr-xml-map "hsrp_ipv4_v2_cfg:PrimaryIPv4Addres"+
                    "s";
                  description "Primary HSRP IP address";
                  leaf virtual-ip-learn {
                    xr:xr-xml-map "hsrp_ipv4_v2_cfg:VirtualIPLearn";
                    type boolean;
                    description
                      "TRUE if the HSRP protocol is to learn the
                      virtual IP address it is to use";
                  }
                  leaf address {
                    xr:xr-xml-map "hsrp_ipv4_v2_cfg:Address";
                    when "../virtual-ip-learn = 0" {
                      description "../VirtualIPLearn = <expr>";
                    }
                    type inet:ipv4-address-no-zone;
                    description "HSRP IP address.";
                  }
                }

                container tracked-objects {
                  xr:xr-xml-map "hsrp_ipv4_v2_cfg:TrackedObjectTabl"+
                    "e";
                  description
                    "The HSRP tracked interface configuration
                    table";

                  list tracked-object {
                    xr:xr-xml-map "hsrp_ipv4_v2_cfg:TrackedObject";
                    key "object-name";
                    description "Object being tracked";
                    leaf object-name {
                      xr:xr-xml-map "hsrp_ipv4_v2_cfg:ObjectName";
                      type xr:Cisco-ios-xr-string;
                      description "Interface being tracked";
                    }
                    leaf priority-decrement {
                      xr:xr-xml-map "hsrp_ipv4_v2_cfg:PriorityDecre"+
                        "ment";
                      type uint32 {
                        range "1..255";
                      }
                      mandatory true;
                      description "Priority decrement";
                    }
                  }
                }

                container tracked-interfaces {
                  xr:xr-xml-map "hsrp_ipv4_v2_cfg:TrackedInterfaceT"+
                    "able";
                  description
                    "The HSRP tracked interface configuration
                    table";

                  list tracked-interface {
                    xr:xr-xml-map "hsrp_ipv4_v2_cfg:TrackedInterfac"+
                      "e";
                    key "interface-name";
                    description "Interface being tracked";
                    leaf interface-name {
                      xr:xr-xml-map "hsrp_ipv4_v2_cfg:InterfaceName";
                      type xr:Interface-name;
                      description "Interface being tracked";
                    }
                    leaf priority-decrement {
                      xr:xr-xml-map "hsrp_ipv4_v2_cfg:PriorityDecre"+
                        "ment";
                      type uint32 {
                        range "1..255";
                      }
                      mandatory true;
                      description "Priority decrement";
                    }
                  }
                }

                container timers {
                  xr:xr-xml-map "hsrp_ipv4_v2_cfg:Timers";
                  description "Hello and hold timers";
                  leaf hello-msec-flag {
                    xr:xr-xml-map "hsrp_ipv4_v2_cfg:HelloMsecFlag";
                    type boolean;
                    default "false";
                    description
                      "TRUE - Hello time configured in
                      milliseconds, FALSE - Hello time
                      configured in seconds";
                  }
                  leaf hello-msec {
                    xr:xr-xml-map "hsrp_ipv4_v2_cfg:HelloMsec";
                    type uint32 {
                      range "100..3000";
                    }
                    units "millisecond";
                    description "Hello time in msecs";
                  }
                  leaf hello-sec {
                    xr:xr-xml-map "hsrp_ipv4_v2_cfg:HelloSec";
                    type uint32 {
                      range "1..255";
                    }
                    units "second";
                    default "3";
                    description "Hello time in seconds";
                  }
                  leaf hold-msec-flag {
                    xr:xr-xml-map "hsrp_ipv4_v2_cfg:HoldMsecFlag";
                    type boolean;
                    default "false";
                    description
                      "TRUE - Hold time configured in
                      milliseconds, FALSE - Hold time
                      configured in seconds";
                  }
                  leaf hold-msec {
                    xr:xr-xml-map "hsrp_ipv4_v2_cfg:HoldMsec";
                    type uint32 {
                      range "100..3000";
                    }
                    units "millisecond";
                    description "Hold time in msecs";
                  }
                  leaf hold-sec {
                    xr:xr-xml-map "hsrp_ipv4_v2_cfg:HoldSec";
                    type uint32 {
                      range "1..255";
                    }
                    units "second";
                    default "10";
                    description "Hold time in seconds";
                  }
                }
                leaf preempt {
                  xr:xr-xml-map "hsrp_ipv4_v2_cfg:Preempt";
                  type int32;
                  default "0";
                  description "Force active if higher priority";
                }
                leaf priority {
                  xr:xr-xml-map "hsrp_ipv4_v2_cfg:Priority";
                  type uint32 {
                    range "0..255";
                  }
                  default "100";
                  description "Priority value";
                }
                leaf virtual-mac-address {
                  xr:xr-xml-map "hsrp_ipv4_v2_cfg:VirtualMACAddress";
                  type yang:mac-address;
                  description "HSRP MAC address";
                }
                leaf session-name {
                  xr:xr-xml-map "hsrp_ipv4_v2_cfg:SessionName";
                  type xr:Cisco-ios-xr-string {
                    length "0..16";
                  }
                  description "HSRP Session name (for MGO)";
                }
                leaf group-number {
                  xr:xr-xml-map "hsrp_ipv4_v2_cfg:GroupNumber";
                  type uint32 {
                    range "0..4095";
                  }
                  description "HSRP group number";
                }
              }
            }
          }
        }
        leaf mac-refresh {
          xr:xr-xml-map "hsrp_cfg:MACRefresh";
          xr:xr-cli-map "hsrp interface <interface> hsrp mac-refres"+
            "h <number> ";
          type uint32 {
            range "0..10000";
          }
          default "60";
          description "HSRP MGO slave MAC refresh rate";
        }
        leaf use-bia {
          xr:xr-xml-map "hsrp_cfg:UseBIA";
          xr:xr-cli-map "hsrp interface <interface> hsrp use-bia ";
          type empty;
          description "Use burned-in address";
        }
        leaf redirects-disable {
          xr:xr-xml-map "hsrp_cfg:RedirectsDisable";
          xr:xr-cli-map "hsrp interface <interface> hsrp redirects "+
            "disable ";
          type empty;
          description "Disable HSRP filtered ICMP redirects";
        }
        leaf interface-name {
          xr:xr-xml-map "hsrp_cfg:InterfaceName";
          type xr:Interface-name;
          description "Interface name";
        }
      }
    }

    container logging {
      xr:xr-xml-map "hsrp_cfg:Logging";
      description "HSRP logging options";
      leaf state-change-disable {
        xr:xr-xml-map "hsrp_cfg:StateChangeDisable";
        xr:xr-cli-map "hsrp message state disable ";
        type empty;
        description "HSRP state change IOS messages disable";
      }
    }
  }

  augment "/a1:snmp/a1:notification" {

    container hsrp {
      xr:xr-xml-map "hsrpmib_cfg:HSRP";
      description "CISCO-HSRP-MIB notification configuration";
      leaf enable {
        xr:xr-xml-map "hsrpmib_cfg:Enable";
        type empty;
        description "Enable CISCO-HSRP-MIB notifications";
      }
    }
    description
      "This augment extends the configuration data of
      'Cisco-IOS-XR-snmp-agent-cfg'";
  }
}
