module Cisco-IOS-XR-ipv4-ma-subscriber-cfg {

  /*** NAMESPACE / PREFIX DEFINITION ***/

  namespace "http://cisco.com/ns/yang"+
    "/Cisco-IOS-XR-ipv4-ma-subscriber-cfg";


  prefix "ipv4-ma-subscriber-cfg";

  /*** LINKAGE (IMPORTS / INCLUDES) ***/

  import Cisco-IOS-XR-types { prefix "xr"; }

  import Cisco-IOS-XR-subscriber-infra-tmplmgr-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ipv4-ma-subscriber package configuration.

     This YANG module augments the
       Cisco-IOS-XR-subscriber-infra-tmplmgr-cfg
     module with configuration data.

     Copyright (c) 2013-2015 by Cisco Systems, Inc.
     All rights reserved.";

  revision "2015-07-30" {
    description
      "Descriptions updated.";
  }

  revision "2015-01-07" {
    description
      "IOS XR 5.3.1 revision.";
  }


  grouping IPV4-NETWORK {
    description
      "Common node of ip-subscriber, ppp,
      subscriber-service";

    container ipv4-network {
      xr:xr-xml-map "cfg_ipv4_ma_dyn_tmpl:IPV4Network";
      description "Interface IPv4 Network configuration data";
      leaf unnumbered {
        xr:xr-xml-map "cfg_ipv4_ma_dyn_tmpl:Unnumbered";
        type string;
        description
          "Enable IP processing without an explicit
          address";
      }
      leaf mtu {
        xr:xr-xml-map "cfg_ipv4_ma_dyn_tmpl:MTU";
        type uint32 {
          range "68..65535";
        }
        units "byte";
        description "The IP Maximum Transmission Unit";
      }
      leaf unreachables {
        xr:xr-xml-map "cfg_ipv4_ma_dyn_tmpl:unreachables";
        type boolean;
        default "false";
        description "TRUE if enabled, FALSE if disabled";
      }
      leaf rpf {
        xr:xr-xml-map "cfg_ipv4_ma_dyn_tmpl:RPF";
        type boolean;
        default "true";
        description "TRUE if enabled, FALSE if disabled";
      }
    }
  }

  augment "/a1:dynamic-template/a1:subscriber-services"+
    "/a1:subscriber-service" {
    description
      "This augment extends the configuration data of
      'Cisco-IOS-XR-subscriber-infra-tmplmgr-cfg'";
    uses IPV4-NETWORK;
  }

  augment "/a1:dynamic-template/a1:ppps/a1:ppp" {
    description
      "This augment extends the configuration data of
      'Cisco-IOS-XR-subscriber-infra-tmplmgr-cfg'";
    uses IPV4-NETWORK;
  }

  augment "/a1:dynamic-template/a1:ip-subscribers/a1:ip-subscriber" {
    description
      "This augment extends the configuration data of
      'Cisco-IOS-XR-subscriber-infra-tmplmgr-cfg'";
    uses IPV4-NETWORK;
  }
}
