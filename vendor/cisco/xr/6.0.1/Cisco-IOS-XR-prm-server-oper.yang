module Cisco-IOS-XR-prm-server-oper {

  /*** NAMESPACE / PREFIX DEFINITION ***/

  namespace "http://cisco.com/ns/yang/Cisco-IOS-XR-prm-server-oper";


  prefix "prm-server-oper";

  /*** LINKAGE (IMPORTS / INCLUDES) ***/

  import Cisco-IOS-XR-types { prefix "xr"; }

  include Cisco-IOS-XR-prm-server-oper-sub1 {
    revision-date 2016-02-22;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR prm-server package operational data.

     This module contains definitions
     for the following management objects:
       prm: PRM data

     Copyright (c) 2013-2015 by Cisco Systems, Inc.
     All rights reserved.";

  revision "2016-02-22" {
    description
      "Initial revision.";
  }

  revision "2015-11-09" {
    description
      "IOS XR 6.0 revision.";
  }


  container prm {
    xr:xr-xml-map "prm_server_oper:PRM";
    config false;
    description "PRM data";

    container nodes {
      xr:xr-xml-map "prm_server_oper:NodeTable";
      description "List of PRM Nodes";

      list node {
        xr:xr-xml-map "prm_server_oper:Node";
        key "node-name";
        description "Node Information";

        container server {
          xr:xr-xml-map "prm_server_oper:Server";
          description "Server specific";

          container resource {
            xr:xr-xml-map "prm_server_oper:Resource";
            description "Resource specific";

            container indexes {
              xr:xr-xml-map "prm_server_oper:Software";
              description "Data for software resource";

              list index {
                xr:xr-xml-map "prm_server_oper:Index";
                key "index";
                description "Data for software resource";
                leaf index {
                  xr:xr-xml-map "prm_server_oper:index";
                  type int32;
                  description "Index value";
                }
                uses RESOURCE-EDM-DATA;
              }
            }
          }
        }

        container np {
          xr:xr-xml-map "prm_server_np_oper:Np";
          description "Server specific";

          container cpu {
            xr:xr-xml-map "prm_server_np_oper:Cpu";
            description "Resource specific";

            container indexes {
              xr:xr-xml-map "prm_server_np_oper:Queue-stats";
              description "Data for software resource";

              list index {
                xr:xr-xml-map "prm_server_np_oper:Index";
                key "index";
                description "Queue Stats";
                leaf index {
                  xr:xr-xml-map "prm_server_np_oper:index";
                  type int32;
                  description "Index value";
                }
                uses BCM-EDM-COSQ-INFO;
              }
            }
          }
        }
        leaf node-name {
          xr:xr-xml-map "prm_server_oper:NodeName";
          type xr:Node-id;
          description "The node name";
        }
      }
    }
  }
}
