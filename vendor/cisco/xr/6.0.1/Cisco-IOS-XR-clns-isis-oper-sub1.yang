submodule Cisco-IOS-XR-clns-isis-oper-sub1 {

  belongs-to Cisco-IOS-XR-clns-isis-oper {
    prefix Cisco-IOS-XR-clns-isis-oper;
  }

  /*** LINKAGE (IMPORTS / INCLUDES) ***/

  import ietf-inet-types { prefix "inet"; }

  import ietf-yang-types { prefix "yang"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR clns-isis package operational data.

     Copyright (c) 2013-2015 by Cisco Systems, Inc.
     All rights reserved.";

  revision "2015-11-09" {
    description
      "IOS XR 6.0 revision.";
  }

  typedef Isis-metric-style {
    type enumeration {
      enum isis-metric-style-narrow {
        value 0;
        description "old-style (ISO 10589) metrics";
      }
      enum isis-metric-style-wide {
        value 1;
        description "new-style 32-bit metrics";
      }
      enum isis-metric-style-transition {
        value 2;
        description "send/accept both forms of metric";
      }
    }
    description "Isis metric style";
  }
  typedef Isis-startup-status {
    type enumeration {
      enum isis-startup-ssm-active {
        description
          "Startup-state-machine controlled restart in
          progress";
      }
      enum isis-startup-ssm-complete {
        description
          "Startup-state-machine controlled restart
          complete";
      }
      enum isis-startup-ssm-aborted {
        description
          "Startup-state-machine controlled restart
          aborted";
      }
      enum isis-startup-ssm-not-run {
        description
          "Startup-state-machine controlled not attempted";
      }
    }
    description "Isis startup status";
  }
  typedef Isis-nsf-flavor {
    type enumeration {
      enum isis-nsf-flav-or-none {
        value 0;
        description "NSF not configured";
      }
      enum isis-nsf-flav-or-cisco {
        value 1;
        description "Cisco-proprietary NSF";
      }
      enum isis-nsf-flav-or-ietf {
        value 2;
        description "IETF-standard NSF";
      }
      enum isis-nsf-flav-or-nsr {
        value 3;
        description "Cisco-proprietary NSR";
      }
    }
    description "Isis nsf flavor";
  }
  typedef Isis-err-log-level {
    type enumeration {
      enum isis-err-log-level-info {
        value 0;
        description "isis err log level info";
      }
      enum isis-err-log-level-warn {
        value 1;
        description "isis err log level warn";
      }
      enum isis-err-log-level-critical {
        value 2;
        description "isis err log level critical";
      }
    }
    description "Isis err log level";
  }
  typedef Isis-if-af-prefix-unknown-reason {
    type enumeration {
      enum isis-intf-af-prefix-unknown-adv-suppressed {
        description "isis intf af prefix unknown adv suppressed";
      }
      enum isis-intf-af-prefix-unknown-global-addr-reg-error {
        description
          "isis intf af prefix unknown global addr reg
          error";
      }
      enum isis-intf-af-prefix-unknown-internal-error {
        description "isis intf af prefix unknown internal error";
      }
    }
    description "Isis if af prefix unknown reason";
  }
  typedef Isis-if-af-fwd-addr-unknown-reason {
    type enumeration {
      enum isis-intf-af-fwd-addr-unknown-cfg-passive {
        description "isis intf af fwd addr unknown cfg passive";
      }
      enum isis-intf-af-fwd-addr-unknown-proto-doesnt-exist {
        description
          "isis intf af fwd addr unknown proto doesnt
          exist";
      }
      enum isis-intf-af-fwd-addr-unknown-next-hop-reg-error {
        description
          "isis intf af fwd addr unknown next hop reg
          error";
      }
      enum isis-intf-af-fwd-addr-unknown-no-link-local-add {
        description
          "isis intf af fwd addr unknown no link local add";
      }
      enum isis-intf-af-fwd-addr-unknown-af-not-up {
        description "isis intf af fwd addr unknown af not up";
      }
      enum isis-intf-af-fwd-addr-unknown-vrf-enabled {
        description "isis intf af fwd addr unknown vrf enabled";
      }
      enum isis-intf-af-fwd-addr-unknown-internal-error {
        description "isis intf af fwd addr unknown internal error";
      }
    }
    description "Isis if af fwd addr unknown reason";
  }
  typedef Isis-if-af-proto-down-reason {
    type enumeration {
      enum isis-intf-af-proto-down-imd-conn-fail {
        description "isis intf af proto down imd conn fail";
      }
      enum isis-intf-af-proto-down-imd-node-doesnt-exist {
        description "isis intf af proto down imd node doesnt exist";
      }
      enum isis-intf-af-proto-down-imd-exist-reg-error {
        description "isis intf af proto down imd exist reg error";
      }
      enum isis-intf-af-proto-down-imd-state-reg-error {
        description "isis intf af proto down imd state reg error";
      }
      enum isis-intf-af-proto-down-af-not-up {
        description "isis intf af proto down af not up";
      }
      enum isis-intf-af-proto-down-internal-error {
        description "isis intf af proto down internal error";
      }
    }
    description "Isis if af proto down reason";
  }
  typedef Isis-if-af-disabled-reason {
    type enumeration {
      enum isis-intf-af-disabled-no-topo-enabled {
        description "isis intf af disabled no topo enabled";
      }
      enum isis-intf-af-disabled-internal-error {
        description "isis intf af disabled internal error";
      }
    }
    description "Isis if af disabled reason";
  }
  typedef Isis-if-topo-adv-prefix-disabled-reason {
    type enumeration {
      enum isis-intf-topo-adv-prefix-disabled-intf-suppressed {
        description
          "isis intf topo adv prefix disabled intf
          suppressed";
      }
      enum isis-intf-topo-adv-prefix-disabled-af-not-up {
        description "isis intf topo adv prefix disabled af not up";
      }
      enum isis-intf-topo-adv-prefix-disabled-af-prefixes-unknown {
        description
          "isis intf topo adv prefix disabled af prefixes
          unknown";
      }
      enum isis-intf-topo-adv-prefix-disabled-internal-error {
        description
          "isis intf topo adv prefix disabled internal
          error";
      }
    }
    description "Isis if topo adv prefix disabled reason";
  }
  typedef Isis-if-topo-adj-form-disabled-reason {
    type enumeration {
      enum isis-intf-topo-adj-form-disabled-intf-passive {
        description "isis intf topo adj form disabled intf passive";
      }
      enum isis-intf-topo-adj-form-disabled-af-not-up {
        description "isis intf topo adj form disabled af not up";
      }
      enum isis-intf-topo-adj-form-disabled-af-fwd-addr-unknown {
        description
          "isis intf topo adj form disabled af fwd addr
          unknown";
      }
      enum isis-intf-topo-adj-form-disabled-topo-not-cfg {
        description "isis intf topo adj form disabled topo not cfg";
      }
      enum "isis-intf-topo-adj-form-disabled-topo-can-not"+
        "-participate" {
        description
          "isis intf topo adj form disabled topo can not
          participate";
      }
      enum isis-intf-topo-adj-form-disabled-idle {
        description "isis intf topo adj form disabled idle";
      }
      enum isis-intf-topo-adj-form-disabled-internal-error {
        description
          "isis intf topo adj form disabled internal error";
      }
      enum isis-intf-topo-adj-form-disabled-mtu {
        description "isis intf topo adj form disabled mtu";
      }
      enum isis-intf-topo-adj-form-disabled-snpa {
        description "isis intf topo adj form disabled snpa";
      }
      enum isis-intf-topo-adj-form-disabled-mcast {
        description "isis intf topo adj form disabled mcast";
      }
    }
    description "Isis if topo adj form disabled reason";
  }
  typedef Isis-if-topo-disabled-reason {
    type enumeration {
      enum isis-intf-topo-disabled-not-cfg {
        description "isis intf topo disabled not cfg";
      }
      enum isis-intf-topo-disabled-internal-error {
        description "isis intf topo disabled internal error";
      }
    }
    description "Isis if topo disabled reason";
  }
  typedef Isis-circuit-id {
    type yang:hex-string;
    description "Isis circuit id";
  }
  typedef Isis-if-mcast-invalid-reason {
    type enumeration {
      enum isis-intf-mcast-invalid-join-error {
        description
          "Error when attempting to join this multicast
          group";
      }
      enum isis-intf-mcast-invalid-internal-error {
        description "Internal error";
      }
      enum isis-intf-mcast-invalid-not-yet-needed {
        description "Multicast group membership not yet requested";
      }
    }
    description "Isis if mcast invalid reason";
  }
  typedef Isis-if-clns-snpa-unknown-reason {
    type enumeration {
      enum isis-intf-clns-snpa-unknown-access-error {
        description "isis intf clns snpa unknown access error";
      }
      enum isis-intf-clns-snpa-unknown-not-lan {
        description "isis intf clns snpa unknown not lan";
      }
      enum isis-intf-clns-snpa-unknown-internal-error {
        description "isis intf clns snpa unknown internal error";
      }
    }
    description "Isis if clns snpa unknown reason";
  }
  typedef Isis-known {
    type enumeration {
      enum isis-unknown {
        value 0;
        description "Unknown";
      }
      enum isis-known {
        value 1;
        description "Known";
      }
    }
    description "Isis known";
  }
  typedef Isis-if-clns-mtu-invalid-reason {
    type enumeration {
      enum isis-intf-clns-mtu-invalid-too-sm-all {
        description "isis intf clns mtu invalid too sm all";
      }
      enum isis-intf-clns-mtu-invalid-internal-error {
        description "isis intf clns mtu invalid internal error";
      }
    }
    description "Isis if clns mtu invalid reason";
  }
  typedef Isis-if-clns-proto-down-reason {
    type enumeration {
      enum isis-intf-clns-proto-down-add-to-intf-stack-fail {
        description
          "isis intf clns proto down add to intf stack
          fail";
      }
      enum isis-intf-clns-proto-down-no-imd-conn {
        description "isis intf clns proto down no imd conn";
      }
      enum isis-intf-clns-proto-down-imd-node-doesnt-exist {
        description
          "isis intf clns proto down imd node doesnt exist";
      }
      enum isis-intf-clns-proto-down-imd-exist-reg-error {
        description "isis intf clns proto down imd exist reg error";
      }
      enum isis-intf-clns-proto-down-imd-state-reg-error {
        description "isis intf clns proto down imd state reg error";
      }
      enum isis-intf-clns-proto-down-clns-not-up {
        description "isis intf clns proto down clns not up";
      }
    }
    description "Isis if clns proto down reason";
  }
  typedef Isis-up {
    type enumeration {
      enum isis-down {
        value 0;
        description "Down";
      }
      enum isis-up {
        value 1;
        description "Up";
      }
    }
    description "Isis up";
  }
  typedef Isis-extended-circuit-number {
    type uint32;
    description "Isis extended circuit number";
  }
  typedef Isis-circuit-number {
    type uint8;
    description "Isis circuit number";
  }
  typedef Isis-if-adv-prefix-disabled-reason {
    type enumeration {
      enum isis-intf-adv-prefix-disabled-if-cfg-suppressed {
        description
          "isis intf adv prefix disabled if cfg suppressed";
      }
      enum isis-intf-adv-prefix-disabled-no-topo-participate {
        description
          "isis intf adv prefix disabled no topo
          participate";
      }
      enum isis-intf-adv-prefix-disabled-internal-error {
        description "isis intf adv prefix disabled internal error";
      }
    }
    description "Isis if adv prefix disabled reason";
  }
  typedef Isis-if-adj-form-disabled-reason {
    type enumeration {
      enum isis-intf-adj-form-disabled-cfg-passive {
        description "isis intf adj form disabled cfg passive";
      }
      enum isis-intf-adj-form-disabled-no-topo-participate {
        description
          "isis intf adj form disabled no topo participate";
      }
      enum isis-intf-adj-form-disabled-add-to-intf-stack-fail {
        description
          "isis intf adj form disabled add to intf stack
          fail";
      }
      enum isis-intf-adj-form-disabled-clns-io {
        description "isis intf adj form disabled clns io";
      }
      enum isis-intf-adj-form-disabled-internal-error {
        description "isis intf adj form disabled internal error";
      }
    }
    description "Isis if adj form disabled reason";
  }
  typedef Isis-if-disabled-reason {
    type enumeration {
      enum isis-intf-disabled-no-net-cfg {
        description "isis intf disabled no net cfg";
      }
      enum isis-intf-disabled-area-missing {
        description "isis intf disabled area missing";
      }
      enum isis-intf-disabled-no-area-running {
        description "isis intf disabled no area running";
      }
      enum isis-intf-disabled-no-topos-cfg {
        description "isis intf disabled no topos cfg";
      }
      enum isis-intf-disabled-no-imd-conn {
        description "isis intf disabled no imd conn";
      }
      enum isis-intf-disabled-imd-reg-error {
        description "isis intf disabled imd reg error";
      }
      enum isis-intf-disabled-level-mismatch {
        description "isis intf disabled level mismatch";
      }
      enum isis-intf-disabled-base-caps-error {
        description "isis intf disabled base caps error";
      }
      enum isis-intf-disabled-intf-doesnt-exist {
        description "isis intf disabled intf doesnt exist";
      }
      enum isis-intf-disabled-intf-shutdown {
        description "isis intf disabled intf shutdown";
      }
      enum isis-intf-disabled-internal-error {
        description "isis intf disabled internal error";
      }
    }
    description "Isis if disabled reason";
  }
  typedef Isis-enabled {
    type enumeration {
      enum isis-disabled {
        value 0;
        description "Disabled";
      }
      enum isis-enabled {
        value 1;
        description "Enabled";
      }
    }
    description "Isis enabled";
  }
  typedef Isis-mesh-group-number {
    type uint32;
    description "Isis mesh group number";
  }
  typedef Isis-sh-route-adv-origin {
    type enumeration {
      enum isis-sh-route-adv-origin-interface {
        description "IS-IS interface prefix";
      }
      enum isis-sh-route-adv-origin-redistributed {
        description "Redistributed prefix";
      }
      enum isis-sh-route-adv-origin-native {
        description "Native prefix";
      }
      enum isis-sh-route-adv-origin-summary {
        description "Summary prefix";
      }
      enum isis-sh-route-adv-origin-default {
        description "Explicit origination of default prefix";
      }
    }
    description "Origin of a prefix advertisement";
  }
  typedef Isis-prefix-priority {
    type enumeration {
      enum isis-prefix-priority-critical {
        value 0;
        description "Critical priority prefixes";
      }
      enum isis-prefix-priority-high {
        value 1;
        description "High priority prefixes";
      }
      enum isis-prefix-priority-med {
        value 2;
        description "Medium priority prefixes";
      }
      enum isis-prefix-priority-low {
        value 3;
        description "Low priority prefixes";
      }
    }
    description "Isis prefix priority";
  }
  typedef Isis-prefix-origin {
    type enumeration {
      enum isis-prefix-origin-l1-summary-null {
        value 0;
        description "Level 1 Summary Null Route";
      }
      enum isis-prefix-origin-l1 {
        value 1;
        description "Level 1 Route";
      }
      enum isis-prefix-origin-l2-summary-null {
        value 2;
        description "Level 2 Summary Null Route";
      }
      enum isis-prefix-origin-l2 {
        value 3;
        description "Level 2 Route";
      }
      enum isis-prefix-origin-inter-area-summary-null {
        value 4;
        description "Level 1 Interarea Summary Null Route";
      }
      enum isis-prefix-origin-inter-area {
        value 5;
        description "Level 1 Interarea Route";
      }
      enum isis-prefix-origin-default-nearest-attached {
        value 6;
        description "Nearest Attached Default Route";
      }
    }
    description "Isis prefix origin";
  }
  typedef Isis-string {
    type string;
    description "Isis string";
  }
  typedef Isis-redist-proto {
    type enumeration {
      enum isis-redist-connected {
        value 0;
        description "Redistributed protocol is Connected";
      }
      enum isis-redist-static {
        value 1;
        description "Redistributed protocol is Static";
      }
      enum isis-redist-ospf {
        value 2;
        description "Redistributed protocol is OSPF";
      }
      enum isis-redist-bgp {
        value 3;
        description "Redistributed protocol is BGP";
      }
      enum isis-redist-isis {
        value 4;
        description "Redistributed protocol is IS-IS";
      }
      enum isis-redist-ospfv3 {
        value 5;
        description "Redistributed protocol is OSPFv3";
      }
      enum isis-redist-rip {
        value 6;
        description "Redistributed protocol is RIP";
      }
      enum isis-redist-eigrp {
        value 7;
        description "Redistributed protocol is EIGRP";
      }
      enum isis-redist-subscriber {
        value 8;
        description "Redistributed protocol is Subscriber";
      }
      enum isis-redist-application {
        value 9;
        description "Redistributed protocol is Application";
      }
      enum isis-redist-mobile {
        value 10;
        description "Redistributed protocol is Mobile";
      }
    }
    description "Isis redist proto";
  }
  typedef Isis-valid {
    type enumeration {
      enum isis-invalid {
        value 0;
        description "Invalid";
      }
      enum isis-valid {
        value 1;
        description "Valid";
      }
    }
    description "Isis valid";
  }
  typedef Isis-prefix-tag {
    type uint32;
    description "Isis prefix tag";
  }
  typedef Isis-sh-interface-name {
    type string;
    description "Isis sh interface name";
  }
  typedef Isis-metric {
    type uint32;
    description "Isis metric";
  }
  typedef Isis-reachable {
    type enumeration {
      enum isis-unreachable {
        value 0;
        description "Unreachable";
      }
      enum isis-reachable {
        value 1;
        description "Reachable";
      }
    }
    description "Isis reachable";
  }
  typedef Isis-metric-mode {
    type enumeration {
      enum isis-metric-mode-fixed {
        value 0;
        description "Fixed";
      }
      enum isis-metric-mode-relative {
        value 1;
        description "Relative";
      }
      enum isis-metric-mode-absolute {
        value 2;
        description "Absolute";
      }
    }
    description "Isis metric mode";
  }
  typedef Isis-ip-prefix-length {
    type uint8;
    description "Isis ip prefix length";
  }
  typedef Isis-spf-trigger {
    type enumeration {
      enum isis-spf-trig-config {
        description "Configuration change";
      }
      enum isis-spf-trig-nsr-fo {
        description "NSR FO is done";
      }
      enum isis-spf-trig-periodic {
        description "Periodic SPF";
      }
      enum isis-spf-trig-clear {
        description "Cleared route table";
      }
      enum isis-spf-trig-newadj {
        description "New adjacency";
      }
      enum isis-spf-trig-deladj {
        description "Deleted adjacency";
      }
      enum isis-spf-trig-next-hop {
        description "IP nexthop address change";
      }
      enum isis-spf-trig-metric {
        description "Changed interface metric";
      }
      enum isis-spf-trig-dis {
        description "Change to elected DIS";
      }
      enum isis-spf-trig-frr-per-link {
        description "Change to per-link FRR config";
      }
      enum isis-spf-trig-frr-per-prefix {
        description "Change to per-prefix FRR config";
      }
      enum isis-spf-trig-ucmp {
        description "Change to UCMP config/calculation";
      }
      enum isis-spf-trig-new-tunnel {
        description "New TE Autoroute Tunnel";
      }
      enum isis-spf-trig-del-tunnel {
        description "Deleted TE Autoroute Tunnel";
      }
      enum isis-spf-trig-chg-tunnel {
        description "Changed TE Autoroute Tunnel";
      }
      enum isis-spf-trig-new-node {
        description "New LSP zero which participates in topology";
      }
      enum isis-spf-trig-del-node {
        description
          "New LSP zero which no longer participates in
          topology";
      }
      enum isis-spf-trig-newlsp {
        description "Previously unseen LSP fragment";
      }
      enum isis-spf-trig-lsp-expiry {
        description "LSP expired";
      }
      enum isis-spf-trig-attach-set {
        description "Attached bit set";
      }
      enum isis-spf-trig-attach-clr {
        description "Attached bit cleared";
      }
      enum isis-spf-trig-overload-set {
        description "Overload bit set";
      }
      enum isis-spf-trig-overload-clr {
        description "Overload bit cleared";
      }
      enum isis-spf-trig-link-good {
        description "Good news link TLV content change";
      }
      enum isis-spf-trig-link-bad {
        description "Bad news link TLV content change";
      }
      enum isis-spf-trig-prefix-good {
        description "Good news prefix TLV content change";
      }
      enum isis-spf-trig-prefix-bad {
        description "Bad news prefix TLV content change";
      }
      enum isis-spf-trig-prefix {
        description
          "Neutral (neither good nor bad news) prefix TLV
          content change";
      }
      enum isis-spf-trig-area-addr {
        description "Area address TLV content change";
      }
      enum isis-spf-trig-ip-addr {
        description "IP address TLV content change";
      }
      enum isis-spf-trig-rtrid {
        description "Router id TLV content change";
      }
      enum isis-spf-trig-prefix-policy {
        description "Prefix policy change";
      }
    }
    description "Isis spf trigger";
  }
  typedef Isis-spf-class {
    type enumeration {
      enum isis-spf-frr-per-link {
        value 0;
        description "FRR per-link SPF";
      }
      enum isis-spf-partial {
        value 1;
        description "PRC";
      }
      enum isis-spf-frr-per-prefix {
        value 2;
        description "FRR per-prefix SPF";
      }
      enum isis-spf-ucmp-calc {
        value 3;
        description "UCMP SPF";
      }
      enum isis-spf-next-hop {
        value 4;
        description "Next Hop";
      }
      enum isis-spf-incremental {
        value 5;
        description "Incremental SPF";
      }
      enum isis-spf-full {
        value 6;
        description "Full SPF";
      }
    }
    description "Types of route calculation";
  }
  typedef Isis-sh-te-pce-flooding-scope {
    type enumeration {
      enum none {
        description "Flooding is disabled";
      }
      enum area {
        description "Area wide flooding";
      }
      enum domain {
        description "Domain wide flooding";
      }
    }
    description "Isis sh te pce flooding scope";
  }
  typedef Isis-sh-te-link {
    type enumeration {
      enum isis-sh-te-link-p2p {
        description "Tunnel is absolute";
      }
      enum isis-sh-te-link-broadcast {
        description "Broadcast link";
      }
    }
    description "Isis sh te link";
  }
  typedef Isis-lsp-db-op {
    type enumeration {
      enum isis-lsp-db-clear {
        description "Clear the LSP database";
      }
      enum isis-lsp-db-insert-new-lsp {
        description "Insertion of new LSP";
      }
      enum isis-lsp-db-replace-lsp-with-lsp {
        description "LSP replacing LSP";
      }
      enum isis-lsp-db-purge-lsp {
        description "LSP purged by the local system";
      }
      enum isis-lsp-db-delete-lsp {
        description "Removal of the LSP from the database";
      }
    }
    description "Isis lsp db op";
  }
  typedef Isis-pseudo-node-number {
    type uint8;
    description "Isis pseudo node number";
  }
  typedef Isis-lsp-trigger {
    type enumeration {
      enum isis-lsp-trig-config {
        description "Any configuration change";
      }
      enum isis-lsp-trig-newadj {
        description "New adjacency came up";
      }
      enum isis-lsp-trig-deladj {
        description "Adjacency went down";
      }
      enum isis-lsp-trig-dr-change {
        description "DIS changed, or pseudonode changed";
      }
      enum isis-lsp-trig-area-set {
        description "Active area set changed";
      }
      enum isis-lsp-trig-attach {
        description "Attached bit changed state";
      }
      enum isis-lsp-trig-hippity {
        description "LSPDB overload bit changed state";
      }
      enum isis-lsp-trig-regen {
        description "LSP regeneration";
      }
      enum isis-lsp-trig-ip-if-up {
        description "Directly connected IP prefix up";
      }
      enum isis-lsp-trig-ip-if-down {
        description "Directly connected IP prefix down";
      }
      enum isis-lsp-trig-ip-inter-area {
        description "Interarea IP route appeared or gone";
      }
      enum isis-lsp-trig-ip-external {
        description "Redistributed IP route appeared or gone";
      }
      enum isis-lsp-trig-ip-def-orig {
        description "Default information originate changed";
      }
      enum isis-lsp-trig-ip-addr-chg {
        description "IP interface address changed";
      }
      enum isis-lsp-trig-te-info {
        description "TE bandwidth resource information";
      }
      enum isis-lsp-trig-te-pce-info {
        description "TE PCE information";
      }
      enum isis-lsp-trig-te-fa-info {
        description "TE forwarding adjacency information";
      }
      enum isis-lsp-trig-nsr-fo {
        description "NSR FO is done";
      }
      enum isis-lsp-trig-pn-cancel {
        description "Pseudo-node generation canceled";
      }
      enum isis-lsp-trig-lkgp {
        description "Link-group offset metric change";
      }
      enum isis-lsp-trig-pp {
        description "Proactive Protection metric change";
      }
    }
    description "Isis lsp trigger";
  }
  typedef Isis-adj-topo-status {
    type enumeration {
      enum isis-adj-topo-status-ok {
        description "Topology is included in adjacency";
      }
      enum isis-adj-topo-status-intf-not-configured {
        description "Topology is not configured on the interface";
      }
      enum isis-adj-topo-status-intf-not-running {
        description "Topology is not running on the interface";
      }
      enum isis-adj-topo-status-init-state {
        description "Adjacency is in INIT state";
      }
      enum isis-adj-topo-status-neighbor-doesnt-participate {
        description "Neighbor doesn't participate in topology";
      }
      enum isis-adj-topo-status-ipv4-address-tlv-missing {
        description "Neighbor IIH doesn't contain IPv4 address TLV";
      }
      enum isis-adj-topo-status-ipv4-address-tlv-empty {
        description "Neighbor's IPv4 address TLV is empty";
      }
      enum isis-adj-topo-status-ipv6-address-tlv-missing {
        description "Neighbor IIH doesn't contain IPv6 address TLV";
      }
      enum isis-adj-topo-status-ipv6-address-tlv-empty {
        description "Neighbor's IPv6 address TLV is empty";
      }
      enum isis-adj-topo-status-ipv4-address-matches-ours {
        description "Neighbor's IPv4 address matches ours";
      }
      enum isis-adj-topo-status-ipv6-address-matches-ours {
        description "Neighbor's IPv6 address matches ours";
      }
      enum isis-adj-topo-status-ipv4-address-subnet-mismatch {
        description
          "Neighbor's IPv4 address is in a different
          subnet to ours";
      }
      enum isis-adj-topo-status-ipv6-address-not-link-local {
        description "Neighbor's IPv6 address is not link local";
      }
    }
    description "Status of a topology in an adjacency";
  }
  typedef Isis-dr-priority {
    type uint8;
    description "Isis dr priority";
  }
  typedef Isis-adj-bfd-state {
    type enumeration {
      enum isis-adj-bfd-no-state {
        value 0;
        description "No BFD session created";
      }
      enum isis-adj-bfd-down-state {
        value 1;
        description "BFD session is DOWN";
      }
      enum isis-adj-bfd-init-state {
        value 2;
        description "Waiting for BFD session to come UP";
      }
      enum isis-adj-bfd-up-state {
        value 3;
        description "BFD session is UP";
      }
    }
    description "Current BFD state of an adjacency";
  }
  typedef Isis-adj-topo-change {
    type enumeration {
      enum isis-adj-topo-up-change {
        value 0;
        description "Topology up";
      }
      enum isis-adj-topo-next-hop-change {
        value 1;
        description "Topology next-hop changed";
      }
      enum isis-adj-topo-down-change {
        value 2;
        description "Topology down";
      }
    }
    description "Per-topology change type for an adjacency";
  }
  typedef Isis-adj-state-reason {
    type enumeration {
      enum isis-adj-up-nsf-restart {
        value 0;
        description "NSF Restart";
      }
      enum isis-adj-up-new-adj {
        value 1;
        description "New adjacency";
      }
      enum isis-adj-up-restarted {
        value 2;
        description "Restarted";
      }
      enum isis-adj-up-nsf-restored {
        value 3;
        description "Restored during NSF";
      }
      enum isis-adj-up-chkpt-restored {
        value 4;
        description "Restored from checkpoint";
      }
      enum isis-adj-init-reason {
        value 5;
        description "Into INIT";
      }
      enum isis-adj-init-neighbor-forgot {
        value 6;
        description "Neighbor forgot us";
      }
      enum isis-adj-down-hold-time {
        value 7;
        description "Holdtime expired";
      }
      enum isis-adj-down-if-down {
        value 8;
        description "Interface state going down";
      }
      enum isis-adj-down-cfg-mismatch {
        value 9;
        description "Area address/level mismatch";
      }
      enum isis-adj-down-circ-id {
        value 10;
        description "Circuit ID changed";
      }
      enum isis-adj-down-nsf-ack-fail {
        value 11;
        description "NSF could not CSNP Ack P2P adjacency";
      }
      enum isis-adj-down-db-clear {
        value 12;
        description "Clear of the Adjacency DB";
      }
      enum isis-adj-down-no-common-topology {
        value 13;
        description "Neighbors have no common link topology";
      }
      enum isis-adj-down-restart-tlv-missing {
        value 14;
        description "Restart TLV missing during IETF NSF restart";
      }
      enum isis-adj-down-bfd-down {
        value 15;
        description "BFD session has gone DOWN";
      }
      enum isis-adj-down-3way-down {
        value 16;
        description "3-way state down";
      }
    }
    description "Isis adj state reason";
  }
  typedef Isis-level {
    type enumeration {
      enum isis-level0 {
        value 0;
        description "isis level0";
      }
      enum isis-level1 {
        value 1;
        description "isis level1";
      }
      enum isis-level2 {
        value 2;
        description "isis level2";
      }
    }
    description "Isis level";
  }
  typedef Isis-ipv6-address {
    type inet:ipv6-address;
    description "Isis ipv6 address";
  }
  typedef Isis-nodal-sid-value {
    type uint32;
    description "Isis nodal sid value";
  }
  typedef Isis-ipv4-address {
    type inet:ipv4-address;
    description "Isis ipv4 address";
  }
  typedef Isis-sub-af-id {
    type enumeration {
      enum unicast {
        value 0;
        description "Unicast";
      }
      enum multicast {
        value 1;
        description "Multicast";
      }
    }
    description "Isis sub af id";
  }
  typedef Isis-af-id {
    type enumeration {
      enum ipv4 {
        value 0;
        description "IPv4";
      }
      enum ipv6 {
        value 1;
        description "IPv6";
      }
    }
    description "Isis af id";
  }
  typedef Isis-media-class {
    type enumeration {
      enum isis-media-class-lan {
        value 0;
        description "LAN";
      }
      enum isis-media-class-p2p {
        value 1;
        description "P2P";
      }
      enum isis-media-class-loop-back {
        value 2;
        description "Loopback";
      }
    }
    description "Isis media class";
  }
  typedef Isis-levels {
    type enumeration {
      enum isis-levels-none {
        value 0;
        description "isis levels none";
      }
      enum isis-levels-1 {
        value 1;
        description "isis levels 1";
      }
      enum isis-levels-2 {
        value 2;
        description "isis levels 2";
      }
      enum isis-levels-12 {
        value 3;
        description "isis levels 12";
      }
      enum isis-levels-total {
        value 4;
        description "isis levels total";
      }
    }
    description "Isis levels";
  }
  typedef Isis-adj-state {
    type enumeration {
      enum isis-adj-up-state {
        value 0;
        description "Adjacency up";
      }
      enum isis-adj-init-state {
        value 1;
        description "Adjacency initializing";
      }
      enum isis-adj-failed-state {
        value 2;
        description "Adjacency down/failed";
      }
    }
    description "Isis adj state";
  }

  grouping ISIS-SH-CHKPT-TE-TUNNEL {
    description "Checkpointed TE tunnel";
    leaf checkpoint-te-level {
      xr:xr-xml-map "isis_oper_types:CheckpointTELevel";
      type Isis-level;
      description "TE database level";
    }
    leaf checkpoint-te-system-id {
      xr:xr-xml-map "isis_oper_types:CheckpointTESystemID";
      type xr:Osi-system-id;
      description "Destination system ID";
    }
    leaf checkpoint-te-interface {
      xr:xr-xml-map "isis_oper_types:CheckpointTEInterface";
      type xr:Interface-name;
      description "Tunnel interface";
    }
    leaf checkpoint-te-flags {
      xr:xr-xml-map "isis_oper_types:CheckpointTEFlags";
      type uint32;
      description "Tunnel flags";
    }
    leaf checkpoint-te-nexthop {
      xr:xr-xml-map "isis_oper_types:CheckpointTENexthop";
      type Isis-ipv4-address;
      description "Tunnel next-hop IP address";
    }
    leaf checkpoint-te-metric {
      xr:xr-xml-map "isis_oper_types:CheckpointTEMetric";
      type int32;
      description "Tunnel metric";
    }
    leaf checkpoint-te-metric-mode {
      xr:xr-xml-map "isis_oper_types:CheckpointTEMetricMode";
      type Isis-metric-mode;
      description "Tunnel metric mode";
    }
    leaf checkpoint-te-bandwidth {
      xr:xr-xml-map "isis_oper_types:CheckpointTEBandwidth";
      type uint32;
      description "Tunnel bandwidth";
    }
    leaf checkpoint-te-object-id {
      xr:xr-xml-map "isis_oper_types:CheckpointTEObjectID";
      type uint32;
      description "Tunnel checkpoint object ID";
    }
  }

  grouping NSR-STATS-GBL-TYPE {
    description "NSR STATS GBL TYPE";
    leaf no-of-l1-lsp {
      xr:xr-xml-map "isis_oper_types:no_of_l1_lsp";
      type uint32;
      description "no of l1 lsp";
    }
    leaf no-of-l2-lsp {
      xr:xr-xml-map "isis_oper_types:no_of_l2_lsp";
      type uint32;
      description "no of l2 lsp";
    }
    leaf no-of-l1-adj {
      xr:xr-xml-map "isis_oper_types:no_of_l1_adj";
      type uint16;
      description "no of l1 adj";
    }
    leaf no-of-l2-adj {
      xr:xr-xml-map "isis_oper_types:no_of_l2_adj";
      type uint16;
      description "no of l2 adj";
    }
    leaf no-of-live-interface {
      xr:xr-xml-map "isis_oper_types:no_of_live_interface";
      type uint16;
      description "no of live interface";
    }
    leaf no-of-ptp-interface {
      xr:xr-xml-map "isis_oper_types:no_of_ptp_interface";
      type uint16;
      description "no of ptp interface";
    }
    leaf no-of-lan-interface {
      xr:xr-xml-map "isis_oper_types:no_of_lan_interface";
      type uint16;
      description "no of lan interface";
    }
    leaf no-of-loopback-interface {
      xr:xr-xml-map "isis_oper_types:no_of_loopback_interface";
      type uint16;
      description "no of loopback interface";
    }
    leaf no-of-te-tunnels {
      xr:xr-xml-map "isis_oper_types:no_of_te_tunnels";
      type uint16;
      description "no of te tunnels";
    }
    leaf no-of-te-links {
      xr:xr-xml-map "isis_oper_types:no_of_te_links";
      type uint16;
      description "no of te links";
    }
    leaf no-of-ipv4-routes {
      xr:xr-xml-map "isis_oper_types:no_of_ipv4_routes";
      type uint32;
      description "no of ipv4 routes";
    }
    leaf no-of-ipv6-routes {
      xr:xr-xml-map "isis_oper_types:no_of_ipv6_routes";
      type uint32;
      description "no of ipv6 routes";
    }
    leaf seqnum {
      xr:xr-xml-map "isis_oper_types:seqnum";
      type uint32;
      description "seqnum";
    }
  }

  grouping NSR-STATS-GBL-ARR-TYPE {
    description "NSR STATS GBL ARR TYPE";

    container self {
      description "self";
      uses NSR-STATS-GBL-TYPE;
    }

    list peer {
      max-elements "3";
      description "peer";
      uses NSR-STATS-GBL-TYPE;
    }
  }

  grouping ISIS-SH-NSR-STATS-GLOBAL {
    description "IS-IS process NSR statistics";

    container isis-nsr-stats-data {
      description "ISIS NSR STATS Data";
      uses NSR-STATS-GBL-ARR-TYPE;
    }
    leaf isis-vm-state {
      xr:xr-xml-map "isis_oper_types:ISIS_VM_STATE";
      type uint16;
      description "ISIS VM STATE";
    }
  }

  grouping ISIS-SH-MESH-ENTRY {
    description "Mesh-group informaiton for one interface";

    list isis-sh-mesh-entry {
      description "isis sh mesh entry";
      leaf mesh-group-interface {
        type xr:Interface-name;
        description "This interface";
      }
      leaf mesh-group-number {
        type Isis-mesh-group-number;
        description "Mesh-group number";
      }
    }
  }

  grouping ISIS-SH-MESH-GROUPS {
    description "IS-IS mesh-group data";

    container mesh-group-configured-interface-list {
      description "List of mesh-group-configured interfaces";
      uses ISIS-SH-MESH-ENTRY;
    }
  }

  grouping ISIS-SH-CHKPT-LSP {
    description "Checkpointed LSP";
    leaf checkpoint-lsp-object-id {
      xr:xr-xml-map "isis_oper_types:CheckpointLSPObjectID";
      type uint32;
      description "LSP Checkpoint table object ID";
    }
    leaf checkpoint-lsp-level {
      xr:xr-xml-map "isis_oper_types:CheckpointLSPLevel";
      type uint8;
      description "LSP level";
    }
    leaf checkpoint-lsp-local-flag {
      xr:xr-xml-map "isis_oper_types:CheckpointLSPLocalFlag";
      type boolean;
      description "TRUE if this is a local LSP";
    }
    leaf checkpoint-lsp-id {
      xr:xr-xml-map "isis_oper_types:CheckpointLSP_ID";
      type xr:Isis-lsp-id;
      description "LSP ID";
    }
  }

  grouping ISIS-SH-NBR-SUMM-LEVEL {
    description "Neighbor states for one level";
    leaf neighbor-up-count {
      xr:xr-xml-map "isis_oper_types:NeighborUpCount";
      type uint32;
      description "Neighbors up";
    }
    leaf neighbor-init-count {
      xr:xr-xml-map "isis_oper_types:NeighborInitCount";
      type uint32;
      description "Neighbors being initialized";
    }
    leaf neighbor-down-count {
      xr:xr-xml-map "isis_oper_types:NeighborDownCount";
      type uint32;
      description "Neighbors down";
    }
  }

  grouping ISIS-SH-NBR-SUMM {
    description "Neighbor summary data";

    container level1-neighbors {
      description "L1-only neighbors";
      uses ISIS-SH-NBR-SUMM-LEVEL;
    }

    container level2-neighbors {
      description "L2-only neighbors";
      uses ISIS-SH-NBR-SUMM-LEVEL;
    }

    container level12-neigbors {
      description "L12 neighbors";
      uses ISIS-SH-NBR-SUMM-LEVEL;
    }
  }

  grouping ISIS-SH-TOPO-AREA {
    description "Per-topology, per-area IS-IS protocol data";
    leaf level {
      xr:xr-xml-map "isis_oper_types:Level";
      type Isis-level;
      description "The level this data refers to";
    }
    leaf uses-default-link-topo-flag {
      xr:xr-xml-map "isis_oper_types:UsesDefaultLinkTopoFlag";
      type boolean;
      description
        "Does this topology use the default link topology";
    }
    leaf generated-metric-style {
      xr:xr-xml-map "isis_oper_types:GeneratedMetricStyle";
      type Isis-metric-style;
      description "Generate metric style";
    }
    leaf accepted-metric-style {
      xr:xr-xml-map "isis_oper_types:AcceptedMetricStyle";
      type Isis-metric-style;
      description "Accept metric style";
    }
    leaf metric {
      xr:xr-xml-map "isis_oper_types:Metric";
      type Isis-metric;
      description "Metric";
    }
    leaf ispf-state {
      xr:xr-xml-map "isis_oper_types:ISPFState";
      type Isis-enabled;
      description "ISPF state";
    }
    leaf te-enabled {
      xr:xr-xml-map "isis_oper_types:TEEnabled";
      type boolean;
      description "Indicates whether MPLS TE is enabled";
    }
  }

  grouping ISIS-SH-REDIST-ENTRY {
    description "Redistributed protocol entry";

    list isis-sh-redist-entry {
      description "isis sh redist entry";

      container protocol-details {
        description
          "Relevant details of the redistributed protocol";
        uses ISIS-SH-REDIST-ENTRY-PROTO;
      }
    }
  }

  grouping ISIS-SH-TOPO {
    description "Per-topology IS-IS instance data";

    container id {
      description "Topology ID";
      uses ISIS-TOPO-ID-TYPE;
    }

    container redist-protocols-list {
      description "List of redistributed protocols";
      uses ISIS-SH-REDIST-ENTRY;
    }
    leaf default-admin-distance {
      xr:xr-xml-map "isis_oper_types:DefaultAdminDistance";
      type uint32;
      description "Default administrative distance";
    }
    leaf advertise-passive-only {
      xr:xr-xml-map "isis_oper_types:AdvertisePassiveOnly";
      type boolean;
      description "Advertise passive interface prefixes only";
    }

    list per-area-data {
      description "Per-area data";
      uses ISIS-SH-TOPO-AREA;
    }
  }

  grouping ISIS-SH-PROTO {
    description "Information about an IS-IS instance";
    leaf nsap-system-id {
      xr:xr-xml-map "isis_oper_types:NSAPSystemID";
      type xr:Osi-system-id;
      description "Local system ID";
    }
    leaf valid-nsap-system-id {
      xr:xr-xml-map "isis_oper_types:ValidNSAPSystemID";
      type boolean;
      description "Indicates if system ID valid";
    }
    leaf running-levels {
      xr:xr-xml-map "isis_oper_types:RunningLevels";
      type Isis-levels;
      description "Levels running";
    }
    leaf configured-nsf-flavor {
      xr:xr-xml-map "isis_oper_types:ConfiguredNSFFlavor";
      type Isis-nsf-flavor;
      description "Configured NSF type";
    }
    leaf last-restart-nsf-flavor {
      xr:xr-xml-map "isis_oper_types:LastRestartNSFFlavor";
      type Isis-nsf-flavor;
      description "NSF type of last restart";
    }
    leaf last-restart-status {
      xr:xr-xml-map "isis_oper_types:LastRestartStatus";
      type Isis-startup-status;
      description "Last restart status";
    }
    leaf remaining-time-for-next-nsf-restart {
      xr:xr-xml-map "isis_oper_types:RemainingTimeForNextNSFRestart";
      type uint32;
      description
        "Time remaining until the next NSF restart may be
        attempted";
    }
    leaf-list manual-area-address {
      xr:xr-xml-map "isis_oper_types:ManualAreaAddresses";
      type xr:Osi-area-address;
      description "Manual area addresses";
    }
    leaf-list active-area-address {
      xr:xr-xml-map "isis_oper_types:ActiveAreaAddresses";
      type xr:Osi-area-address;
      description "Active area addresses";
    }

    list per-topo-data {
      description "Per-topology data";
      uses ISIS-SH-TOPO;
    }
  }

  grouping ISIS-TRAFFIC-INTF-AREA-LAN-TYPE {
    description "Per-interface, per-area LAN-only statistics";

    container iih-count {
      description "IIH statistics";
      uses ISIS-TRAFFIC-PDU-COUNT-TYPE;
    }
    leaf memory-exhausted-iih-count {
      xr:xr-xml-map "isis_oper_types:MemoryExhaustedIIHCount";
      type uint32;
      description "IIHs not sent due to memory exhaustion";
    }
    leaf dis-election-count {
      xr:xr-xml-map "isis_oper_types:DISElectionCount";
      type uint32;
      description "DIS elections";
    }
  }

  grouping ISIS-TRAFFIC-INTF-AREA-TYPE {
    description "Per-interface, per-area statistics";

    container lsp-count {
      description "LSP statistics";
      uses ISIS-TRAFFIC-PDU-COUNT-TYPE;
    }

    container csnp-count {
      description "CSNP statistics";
      uses ISIS-TRAFFIC-PDU-COUNT-TYPE;
    }

    container psnp-count {
      description "PSNP statistics";
      uses ISIS-TRAFFIC-PDU-COUNT-TYPE;
    }
    leaf lsp-drop-count {
      xr:xr-xml-map "isis_oper_types:LSPDropCount";
      type uint32;
      description
        "Count of LSPs dropped due to minimum arrival
        time config";
    }
    leaf lsp-flooding-dup-count {
      xr:xr-xml-map "isis_oper_types:LSPFloodingDupCount";
      type uint32;
      description
        "Count of LSPs already received by neighbors and
        not flooded";
    }
  }

  grouping ISIS-SH-TRAFFIC-INTF-AREA {
    description "Per-interface, per-area data";

    container statistics {
      description "Statistics";
      uses ISIS-TRAFFIC-INTF-AREA-TYPE;
    }

    container lan-data {
      description
        "LAN interface statistics. NULL for non-LAN
        interfaces";
      uses ISIS-TRAFFIC-INTF-AREA-LAN-TYPE;
    }
    leaf level {
      xr:xr-xml-map "isis_oper_types:Level";
      type Isis-level;
      description "Level of the area this data relates to";
    }
  }

  grouping ISIS-TRAFFIC-PDU-COUNT-TYPE {
    description "Per-interface, per-PDU statistics";
    leaf pdu-receive-count {
      xr:xr-xml-map "isis_oper_types:PDUReceiveCount";
      type uint32;
      description "PDUs received";
    }
    leaf pdu-send-count {
      xr:xr-xml-map "isis_oper_types:PDUSendCount";
      type uint32;
      description "PDUs sent";
    }
  }

  grouping ISIS-TRAFFIC-INTF-P2P-TYPE {
    description "Per-interface point-to-point statistics";

    container iih-count {
      description "IIH statistics";
      uses ISIS-TRAFFIC-PDU-COUNT-TYPE;
    }
    leaf memory-exhausted-iih-count {
      xr:xr-xml-map "isis_oper_types:MemoryExhaustedIIHCount";
      type uint32;
      description "IIHs not sent due to memory exhaustion";
    }
    leaf lsp-retransmit-count {
      xr:xr-xml-map "isis_oper_types:LSPRetransmitCount";
      type uint32;
      description "LSP retransmissions";
    }
  }

  grouping ISIS-SH-TRAFFIC-INTF {
    description "IS-IS interface traffic data";

    container p2p-statistics {
      description
        "P2P interface statistics. NULL for non-P2P
        interfaces";
      uses ISIS-TRAFFIC-INTF-P2P-TYPE;
    }
    leaf traffic-interface {
      xr:xr-xml-map "isis_oper_types:TrafficInterface";
      type xr:Interface-name;
      description "Interface to which traffic statistics apply";
    }
    leaf interface-media-type {
      xr:xr-xml-map "isis_oper_types:InterfaceMediaType";
      type Isis-media-class;
      description "Interface media class";
    }

    list per-area-data {
      description "Per-area data";
      uses ISIS-SH-TRAFFIC-INTF-AREA;
    }
  }

  grouping ISIS-SH-CHKPT-IDB {
    description "Checkpointed interface";
    leaf checkpoint-object-id {
      xr:xr-xml-map "isis_oper_types:CheckpointObjectID";
      type uint32;
      description "Checkpoint object ID";
    }
    leaf interface-name-xr {
      xr:xr-xml-map "isis_oper_types:interface-name-xr";
      type string;
      description "Interface name";
    }
    leaf checkpoint-interface-handle {
      xr:xr-xml-map "isis_oper_types:CheckpointInterfaceHandle";
      type xr:Interface-name;
      description "Local interface handle";
    }
    leaf local-circuit-number {
      xr:xr-xml-map "isis_oper_types:LocalCircuitNumber";
      type Isis-circuit-number;
      description "Local circuit number";
    }
    leaf dis-areas {
      xr:xr-xml-map "isis_oper_types:DISAreas";
      type Isis-levels;
      description "Areas in which this system is DIS";
    }
    leaf has-adjacency {
      xr:xr-xml-map "isis_oper_types:HasAdjacency";
      type boolean;
      description "TRUE if there is an adjacency on this interface";
    }
    leaf local-snpa {
      xr:xr-xml-map "isis_oper_types:LocalSNPA";
      type xr:Isis-snpa;
      description "SNPA of this interface";
    }
    leaf has-joined-mcast-group {
      xr:xr-xml-map "isis_oper_types:HasJoinedMcastGroup";
      type boolean;
      description
        "TRUE if multicast group registration succeeded
        on this interface";
    }
    leaf has-achieved-ldp-sync {
      xr:xr-xml-map "isis_oper_types:HasAchievedLDPSync";
      type boolean;
      description "MPLS LDP sync status";
    }
    leaf has-achieved-ld-pv6-sync {
      xr:xr-xml-map "isis_oper_types:HasAchievedLDPv6Sync";
      type boolean;
      description "MPLS LDPv6 sync status";
    }
  }

  grouping ISIS-SH-ERR-LOG-ENT {
    description "An error log entry";

    container generic-data {
      description "Generic entry data";
      uses ISIS-SH-GENERIC-LOG-ENT;
    }
    leaf error-log-level {
      xr:xr-xml-map "isis_oper_types:ErrorLogLevel";
      type Isis-err-log-level;
      description "Logging level";
    }
    leaf error-code {
      xr:xr-xml-map "isis_oper_types:ErrorCode";
      type uint32;
      description "Error code";
    }
    leaf error-reason {
      xr:xr-xml-map "isis_oper_types:ErrorReason";
      type string;
      description "Error details";
    }
  }

  grouping ISIS-SH-ERR-LOG-STRUC {
    description "Error log structure";

    list log-entry {
      description "Error Log entries";
      uses ISIS-SH-ERR-LOG-ENT;
    }
  }

  grouping ISIS-SH-CHKPT-ADJ {
    description "Checkpointed adjacency";
    leaf checkpoint-adjacency-object-id {
      xr:xr-xml-map "isis_oper_types:CheckpointAdjacencyObjectID";
      type uint32;
      description "Checkpoint object ID";
    }
    leaf checkpoint-adjacency-system-id {
      xr:xr-xml-map "isis_oper_types:CheckpointAdjacencySystemID";
      type xr:Osi-system-id;
      description "Neighbor system ID";
    }
    leaf checkpoint-adjacency-snpa {
      xr:xr-xml-map "isis_oper_types:CheckpointAdjacencySNPA";
      type xr:Isis-snpa;
      description "Neighbor SNPA";
    }
    leaf checkpoint-adjacency-interface {
      xr:xr-xml-map "isis_oper_types:CheckpointAdjacencyInterface";
      type xr:Interface-name;
      description "Local interface";
    }
    leaf checkpoint-adjacency-level {
      xr:xr-xml-map "isis_oper_types:CheckpointAdjacencyLevel";
      type Isis-level;
      description "Adjacency level";
    }
    leaf checkpoint-adjacency-holdtime {
      xr:xr-xml-map "isis_oper_types:CheckpointAdjacencyHoldtime";
      type uint16;
      description "Adjacency holdtime (s)";
    }
    leaf checkpoint-adjacency-lan-priority {
      xr:xr-xml-map "isis_oper_types:CheckpointAdjacencyLANPriority";
      type Isis-dr-priority;
      description "Adjacency LAN priority";
    }
    leaf checkpoint-adjacency-circuit-number {
      xr:xr-xml-map "isis_oper_types:CheckpointAdjacencyCircuitNumb"+
        "er";
      type Isis-circuit-number;
      description "Neighbor circuit number";
    }

    list checkpoint-adjacency-per-address-family-next-hop {
      description "Per address family next hops";
      uses ISIS-IP-ADDR-TYPE;
    }
  }

  grouping ISIS-SH-IF-AF-PREFIX-DATA {
    description "Address prefix info";
    leaf is-unnumbered {
      xr:xr-xml-map "isis_oper_types:IsUnnumbered";
      type boolean;
      description "Is the interface unnumbered";
    }

    list prefix {
      description "Array of global prefixes";
      uses ISIS-IP-PREFIX-TYPE;
    }
  }

  grouping ISIS-SH-IF-AF-PREFIX-UNKNOWN {
    description "Address prefix unknown info";
    leaf reason-code {
      xr:xr-xml-map "isis_oper_types:ReasonCode";
      type Isis-if-af-prefix-unknown-reason;
      description
        "Reason why the global prefix(es) is(are) unknown";
    }
  }

  grouping ISIS-SH-IF-AF-PREFIX-STATUS {
    description "ISIS SH IF AF PREFIX STATUS";

    container unknown {
      when "../status = 'isis-unknown'" {
        description "../Status = 'ISIS_UNKNOWN'";
      }
      description "Unknown state for the global prefixes";
      uses ISIS-SH-IF-AF-PREFIX-UNKNOWN;
    }

    container prefix-data {
      when "../status = 'isis-known'" {
        description "../Status = 'ISIS_KNOWN'";
      }
      description "Global prefix data for the Address Family";
      uses ISIS-SH-IF-AF-PREFIX-DATA;
    }
    leaf status {
      xr:xr-xml-map "isis_oper_types:Status";
      type Isis-known;
      description "Status";
    }
  }

  grouping ISIS-IP-ADDR-TYPE {
    description "ISIS IP ADDR TYPE";
    leaf af-name {
      xr:xr-xml-map "isis_oper_types:AFName";
      type Isis-af-id;
      description "AFName";
    }
    leaf ipv4 {
      xr:xr-xml-map "isis_oper_types:IPV4";
      when "../af-name = 'ipv4'" {
        description "../AFName = 'IPv4'";
      }
      type Isis-ipv4-address;
      description "IPV4 address type";
    }
    leaf ipv6 {
      xr:xr-xml-map "isis_oper_types:IPV6";
      when "../af-name = 'ipv6'" {
        description "../AFName = 'IPv6'";
      }
      type Isis-ipv6-address;
      description "IPV6 address type";
    }
  }

  grouping ISIS-SH-IF-AF-FWD-ADDR-DATA {
    description "Address-family forwarding address data";
    leaf unnumbered-interface-name {
      xr:xr-xml-map "isis_oper_types:UnnumberedInterfaceName";
      type string;
      description
        "If the interface is unnumbered, then its name,
        else NULL";
    }

    list forwarding-address {
      description "Array of forwarding addresses";
      uses ISIS-IP-ADDR-TYPE;
    }
  }

  grouping ISIS-SH-IF-AF-FWD-ADDR-UNKNOWN {
    description "Forwarding address unknown data";
    leaf reason-code {
      xr:xr-xml-map "isis_oper_types:ReasonCode";
      type Isis-if-af-fwd-addr-unknown-reason;
      description
        "Reason why the forwarding address(es) of an AF
        is(are) unknown";
    }
  }

  grouping ISIS-SH-IF-AF-FWD-ADDR-STATUS {
    description "ISIS SH IF AF FWD ADDR STATUS";

    container unknown {
      when "../status = 'isis-unknown'" {
        description "../Status = 'ISIS_UNKNOWN'";
      }
      description "Unknown forwarding address data";
      uses ISIS-SH-IF-AF-FWD-ADDR-UNKNOWN;
    }

    container forwarding-address-data {
      when "../status = 'isis-known'" {
        description "../Status = 'ISIS_KNOWN'";
      }
      description "Known Forwarding address data";
      uses ISIS-SH-IF-AF-FWD-ADDR-DATA;
    }
    leaf status {
      xr:xr-xml-map "isis_oper_types:Status";
      type Isis-known;
      description "Status";
    }
  }

  grouping ISIS-SH-IF-AF-PROTO-DOWN {
    description "Address family protocol down info";
    leaf reason-code {
      xr:xr-xml-map "isis_oper_types:ReasonCode";
      type Isis-if-af-proto-down-reason;
      description
        "Reason why the Address Family protocol status is
        down";
    }
  }

  grouping ISIS-SH-IF-AF-PROTO-STATUS {
    description "ISIS SH IF AF PROTO STATUS";

    container disabled {
      when "../status = 'isis-down'" {
        description "../Status = 'ISIS_DOWN'";
      }
      description "Disabled state of the Address Family protocol";
      uses ISIS-SH-IF-AF-PROTO-DOWN;
    }
    leaf status {
      xr:xr-xml-map "isis_oper_types:Status";
      type Isis-up;
      description "Status";
    }
  }

  grouping ISIS-SH-IF-AF-ENABLED {
    description "Enabled address-family info of an interface";

    container protocol-status {
      description "Protocol status of the AF";
      uses ISIS-SH-IF-AF-PROTO-STATUS;
    }

    container forwarding-address-status {
      description "Forwarding status of the AF";
      uses ISIS-SH-IF-AF-FWD-ADDR-STATUS;
    }

    container prefix-status {
      description "Prefix status of the AF";
      uses ISIS-SH-IF-AF-PREFIX-STATUS;
    }
  }

  grouping ISIS-SH-IF-AF-DISABLED {
    description "Address family disabled info";
    leaf reason-code {
      xr:xr-xml-map "isis_oper_types:ReasonCode";
      type Isis-if-af-disabled-reason;
      description "Reason why the Address Family is disabled";
    }
  }

  grouping ISIS-SH-IF-AF-STATUS {
    description "ISIS SH IF AF STATUS";

    container disabled {
      when "../status = 'isis-disabled'" {
        description "../Status = 'ISIS_DISABLED'";
      }
      description "Disabled info for the AF of an interface";
      uses ISIS-SH-IF-AF-DISABLED;
    }

    container af-data {
      when "../status = 'isis-enabled'" {
        description "../Status = 'ISIS_ENABLED'";
      }
      description "Enabled data for the AF of an interface";
      uses ISIS-SH-IF-AF-ENABLED;
    }
    leaf status {
      xr:xr-xml-map "isis_oper_types:Status";
      type Isis-enabled;
      description "Status";
    }
  }

  grouping ISIS-SH-IF-AF {
    description "Per Address family info";

    container af-status {
      description "Address Family status of the interface";
      uses ISIS-SH-IF-AF-STATUS;
    }
    leaf af-name {
      xr:xr-xml-map "isis_oper_types:AFName";
      type Isis-af-id;
      description "Address Family Identifier of the interface";
    }
  }

  grouping ISIS-SH-IF-TOPO-ADV-PREFIX-DISABLED {
    description
      "Topology info when prefix advertisement is
      disabled";
    leaf reason-code {
      xr:xr-xml-map "isis_oper_types:ReasonCode";
      type Isis-if-topo-adv-prefix-disabled-reason;
      description
        "Reason why the prefix advertisement status of a
        topology is disabled";
    }
  }

  grouping ISIS-SH-IF-TOPO-ADV-PREFIX-STATUS {
    description "ISIS SH IF TOPO ADV PREFIX STATUS";

    container disabled {
      when "../status = 'isis-disabled'" {
        description "../Status = 'ISIS_DISABLED'";
      }
      description
        "Disabled state for the prefix advertisement
        status of a topology";
      uses ISIS-SH-IF-TOPO-ADV-PREFIX-DISABLED;
    }
    leaf status {
      xr:xr-xml-map "isis_oper_types:Status";
      type Isis-enabled;
      description "Status";
    }
  }

  grouping ISIS-SH-IF-TOPO-ADJ-FORM-DISABLED {
    description
      "Topology info when adjacency formation is
      disabled";
    leaf reason-code {
      xr:xr-xml-map "isis_oper_types:ReasonCode";
      type Isis-if-topo-adj-form-disabled-reason;
      description
        "Reason why the adjacency formation status of a
        topology is disabled";
    }
  }

  grouping ISIS-SH-IF-TOPO-ADJ-FORM-STATUS {
    description "ISIS SH IF TOPO ADJ FORM STATUS";

    container disabled {
      when "../status = 'isis-disabled'" {
        description "../Status = 'ISIS_DISABLED'";
      }
      description
        "Disabled state for the adjacency formation
        status of a topology";
      uses ISIS-SH-IF-TOPO-ADJ-FORM-DISABLED;
    }
    leaf status {
      xr:xr-xml-map "isis_oper_types:Status";
      type Isis-enabled;
      description "Status";
    }
  }

  grouping ISIS-SH-IF-TOPO-ENABLED {
    description "Enabled topology info of an interface";

    container adjacency-form-status {
      description "Adjacency formation status of a topology";
      uses ISIS-SH-IF-TOPO-ADJ-FORM-STATUS;
    }

    container adv-prefix-status {
      description "Prefix advertisement status of a topology";
      uses ISIS-SH-IF-TOPO-ADV-PREFIX-STATUS;
    }
    leaf level1-metric {
      xr:xr-xml-map "isis_oper_types:Level1Metric";
      type Isis-metric;
      description "L1 metric for this topology";
    }
    leaf level2-metric {
      xr:xr-xml-map "isis_oper_types:Level2Metric";
      type Isis-metric;
      description "L2 metric for this topology";
    }
    leaf level1-weight {
      xr:xr-xml-map "isis_oper_types:Level1Weight";
      type Isis-metric;
      description "L1 metric for this topology";
    }
    leaf level2-weight {
      xr:xr-xml-map "isis_oper_types:Level2Weight";
      type Isis-metric;
      description "L2 metric for this topology";
    }
    leaf max-label-supported {
      xr:xr-xml-map "isis_oper_types:MaxLabelSupported";
      type uint16;
      description "MPLS maximum number of labels supported";
    }
    leaf level1ldp-sync-enabled {
      xr:xr-xml-map "isis_oper_types:Level1LDPSyncEnabled";
      type boolean;
      description "MPLS LDP sync enabled status for L1";
    }
    leaf level2ldp-sync-enabled {
      xr:xr-xml-map "isis_oper_types:Level2LDPSyncEnabled";
      type boolean;
      description "MPLS LDP sync enabled status for L2";
    }
    leaf ldp-sync-status {
      xr:xr-xml-map "isis_oper_types:LDPSyncStatus";
      type boolean;
      description "Status of MPLS LDP synchronization";
    }
    leaf ld-pv6-sync-status {
      xr:xr-xml-map "isis_oper_types:LDPv6SyncStatus";
      type boolean;
      description "Status of MPLS LDPv6 synchronization";
    }
    leaf level1-offset-metric {
      xr:xr-xml-map "isis_oper_types:Level1OffsetMetric";
      type Isis-metric;
      description "L1 metric-offset for this topology";
    }
    leaf level2-offset-metric {
      xr:xr-xml-map "isis_oper_types:Level2OffsetMetric";
      type Isis-metric;
      description "L2 metric-offset for this topology";
    }
    leaf level1-lkgp-configured {
      xr:xr-xml-map "isis_oper_types:Level1LkgpConfigured";
      type boolean;
      description "Link-Group configure status for L1";
    }
    leaf level2-lkgp-configured {
      xr:xr-xml-map "isis_oper_types:Level2LkgpConfigured";
      type boolean;
      description "Link-Group configure status for L2";
    }
    leaf level1pp-metric {
      xr:xr-xml-map "isis_oper_types:Level1PPMetric";
      type Isis-metric;
      description "L1 PP-metric for this topology";
    }
    leaf level2pp-metric {
      xr:xr-xml-map "isis_oper_types:Level2PPMetric";
      type Isis-metric;
      description "L2 PP-metric for this topology";
    }
    leaf level1pp-configured {
      xr:xr-xml-map "isis_oper_types:Level1PPConfigured";
      type boolean;
      description "PP configure status for L1";
    }
    leaf level2pp-configured {
      xr:xr-xml-map "isis_oper_types:Level2PPConfigured";
      type boolean;
      description "PP configure status for L2";
    }
  }

  grouping ISIS-SH-IF-TOPO-DISABLED {
    description "Disabled topology info of an interface";
    leaf reason-code {
      xr:xr-xml-map "isis_oper_types:ReasonCode";
      type Isis-if-topo-disabled-reason;
      description "Reason why the topology is disabled";
    }
  }

  grouping ISIS-SH-IF-TOPO-STATUS {
    description "ISIS SH IF TOPO STATUS";

    container disabled {
      when "../status = 'isis-disabled'" {
        description "../Status = 'ISIS_DISABLED'";
      }
      description "Disabled information of a topology";
      uses ISIS-SH-IF-TOPO-DISABLED;
    }

    container enabled {
      when "../status = 'isis-enabled'" {
        description "../Status = 'ISIS_ENABLED'";
      }
      description "Enabled information of a topology";
      uses ISIS-SH-IF-TOPO-ENABLED;
    }
    leaf status {
      xr:xr-xml-map "isis_oper_types:Status";
      type Isis-enabled;
      description "Status";
    }
  }

  grouping ISIS-SH-IF-TOPO {
    description "Per topology info of an interface";

    container topology-id {
      description "Topology identifier";
      uses ISIS-TOPO-ID-TYPE;
    }

    container status {
      description "Status of the topology";
      uses ISIS-SH-IF-TOPO-STATUS;
    }
  }

  grouping ISIS-SH-IF-AREA-ACTIVE-LAN {
    description
      "Per-interface, per-area data for active LAN
      interface";
    leaf circuit-lan-id {
      xr:xr-xml-map "isis_oper_types:CircuitLAN_ID";
      type Isis-circuit-id;
      description "Circuit LAN ID";
    }
    leaf time-until-next-iih {
      xr:xr-xml-map "isis_oper_types:TimeUntilNextIIH";
      type uint32;
      description "Time (ms) until next IIH";
    }
    leaf interface-priority {
      xr:xr-xml-map "isis_oper_types:InterfacePriority";
      type Isis-dr-priority;
      description "Interface's DIS-election priority";
    }
    leaf dispriority {
      xr:xr-xml-map "isis_oper_types:DISPriority";
      type Isis-dr-priority;
      description "Priority of current DIS on this LAN";
    }
    leaf are-we-dis {
      xr:xr-xml-map "isis_oper_types:AreWeDIS";
      type boolean;
      description "Flag indicating if this LAN circuit is the DIS";
    }
  }

  grouping ISIS-SH-IF-AREA-ACTIVE {
    description "Per-area data for an interface";

    container lan-data {
      description
        "LAN data, NULL iff interface has non-LAN media
        type";
      uses ISIS-SH-IF-AREA-ACTIVE-LAN;
    }
    leaf level {
      xr:xr-xml-map "isis_oper_types:Level";
      type Isis-level;
      description "Level of the area";
    }
    leaf adjacency-count {
      xr:xr-xml-map "isis_oper_types:AdjacencyCount";
      type uint32;
      description "Number of adjacencies";
    }
    leaf lsp-pacing-interval {
      xr:xr-xml-map "isis_oper_types:LSPPacingInterval";
      type uint32;
      description "LSP pacing time period (ms)";
    }
    leaf psnp-transmit-queue-size {
      xr:xr-xml-map "isis_oper_types:PSNPTransmitQueueSize";
      type uint32;
      description "No. of SNP entries queued to be transmitted";
    }
  }

  grouping ISIS-SH-IF-CLNS-P2P-OVER-LAN {
    description "Point-to-point over LAN specific CLNS state";

    container multicast-status {
      description "Multicast group membership status";
      uses ISIS-SH-IF-MCAST-STATUS;
    }
  }

  grouping ISIS-SH-IF-CLNS-P2P {
    description "Point-to-point CLNS state";

    container p2p-over-lan-data {
      description "Point-to-point over LAN data";
      uses ISIS-SH-IF-CLNS-P2P-OVER-LAN;
    }
  }

  grouping ISIS-SH-IF-MCAST-INVALID {
    description "Invalid multicast info";
    leaf reason-code {
      xr:xr-xml-map "isis_oper_types:ReasonCode";
      type Isis-if-mcast-invalid-reason;
      description "Reason why the multicast status is invalid";
    }
  }

  grouping ISIS-SH-IF-MCAST-STATUS {
    description "ISIS SH IF MCAST STATUS";

    container invalid {
      when "../status = 'isis-invalid'" {
        description "../Status = 'ISIS_INVALID'";
      }
      description
        "Information pertaining to the invalid multicast
        status";
      uses ISIS-SH-IF-MCAST-INVALID;
    }
    leaf status {
      xr:xr-xml-map "isis_oper_types:Status";
      type Isis-valid;
      description "Status";
    }
  }

  grouping ISIS-SH-IF-AREA-CLNS {
    description "Per interface per area CLNS state";

    container multicast-status {
      description "Multicast group membership status";
      uses ISIS-SH-IF-MCAST-STATUS;
    }
    leaf level {
      xr:xr-xml-map "isis_oper_types:Level";
      type Isis-level;
      description "Level of the area";
    }
  }

  grouping ISIS-SH-IF-CLNS-LAN {
    description "LAN specific CLNS state";

    list per-area-data {
      description "Array of per area CLNS data";
      uses ISIS-SH-IF-AREA-CLNS;
    }
  }

  grouping ISIS-SH-IF-CLNS-MEDIA-SPECIFIC-STATUS {
    description "Media Specific CLNS state";

    container clns-lan-data {
      when "../clns-media-type = 'isis-media-class-lan'" {
        description "../CLNSMediaType = 'ISIS_MEDIA_CLASS_LAN'";
      }
      description "LAN state";
      uses ISIS-SH-IF-CLNS-LAN;
    }

    container clns-p2p-data {
      when "../clns-media-type = 'isis-media-class-p2p'" {
        description "../CLNSMediaType = 'ISIS_MEDIA_CLASS_P2P'";
      }
      description "Point-to-point state";
      uses ISIS-SH-IF-CLNS-P2P;
    }
    leaf clns-media-type {
      xr:xr-xml-map "isis_oper_types:CLNSMediaType";
      type Isis-media-class;
      description "CLNSMediaType";
    }
  }

  grouping ISIS-SH-IF-CLNS-SNPA-KNOWN {
    description "CLNS SNPA info";
    leaf snpa {
      xr:xr-xml-map "isis_oper_types:SNPA";
      type xr:Isis-snpa;
      description "Valid SNPA";
    }
  }

  grouping ISIS-SH-IF-CLNS-SNPA-UNKNOWN {
    description "Interface info with CLNS SNPA unknown";
    leaf reason-code {
      xr:xr-xml-map "isis_oper_types:ReasonCode";
      type Isis-if-clns-snpa-unknown-reason;
      description "Reason why the SNPA is unknown";
    }
  }

  grouping ISIS-SH-IF-CLNS-SNPA-STATUS {
    description "ISIS SH IF CLNS SNPA STATUS";

    container unknown {
      when "../status = 'isis-unknown'" {
        description "../Status = 'ISIS_UNKNOWN'";
      }
      description
        "Information pertaining to the unknown SNPA state";
      uses ISIS-SH-IF-CLNS-SNPA-UNKNOWN;
    }

    container known {
      when "../status = 'isis-known'" {
        description "../Status = 'ISIS_KNOWN'";
      }
      description "Information pertaining to the known SNPA state";
      uses ISIS-SH-IF-CLNS-SNPA-KNOWN;
    }
    leaf status {
      xr:xr-xml-map "isis_oper_types:Status";
      type Isis-known;
      description "Status";
    }
  }

  grouping ISIS-SH-IF-CLNS-MTU-INVALID {
    description "Interface info with invalid MTU";
    leaf reason-code {
      xr:xr-xml-map "isis_oper_types:ReasonCode";
      type Isis-if-clns-mtu-invalid-reason;
      description "Reason why the MTU is invalid";
    }
  }

  grouping ISIS-SH-IF-CLNS-MTU-STATUS {
    description "ISIS SH IF CLNS MTU STATUS";

    container invalid {
      when "../status = 'isis-invalid'" {
        description "../Status = 'ISIS_INVALID'";
      }
      description "Information pertaining to the invalid CLNS MTU";
      uses ISIS-SH-IF-CLNS-MTU-INVALID;
    }
    leaf status {
      xr:xr-xml-map "isis_oper_types:Status";
      type Isis-valid;
      description "Status";
    }
    leaf mtu {
      xr:xr-xml-map "isis_oper_types:MTU";
      when "../status = 'isis-valid'" {
        description "../Status = 'ISIS_VALID'";
      }
      type uint32;
      description "Valid MTU";
    }
  }

  grouping ISIS-SH-IF-CLNS-PROTO-DOWN {
    description "Interface info when CLNS is down";
    leaf reason-code {
      xr:xr-xml-map "isis_oper_types:ReasonCode";
      type Isis-if-clns-proto-down-reason;
      description "Reason why CLNS is down";
    }
  }

  grouping ISIS-SH-IF-CLNS-STATUS {
    description "ISIS SH IF CLNS STATUS";

    container clns-down-info {
      when "../status = 'isis-down'" {
        description "../Status = 'ISIS_DOWN'";
      }
      description "State describing why CLNS is down";
      uses ISIS-SH-IF-CLNS-PROTO-DOWN;
    }
    leaf status {
      xr:xr-xml-map "isis_oper_types:Status";
      type Isis-up;
      description "Status";
    }
  }

  grouping ISIS-SH-IF-CLNS {
    description "CLNS I/O data for an interface";

    container clns-status {
      description
        "Is CLNS protcol up or if not, the reason why it
        is not up";
      uses ISIS-SH-IF-CLNS-STATUS;
    }

    container mtu-info {
      description
        "A valid MTU or the reason for the MTU being
        invalid";
      uses ISIS-SH-IF-CLNS-MTU-STATUS;
    }

    container snpa-state {
      description "SNPA state";
      uses ISIS-SH-IF-CLNS-SNPA-STATUS;
    }

    container media-specific-state {
      description "Media Specific CLNS state";
      uses ISIS-SH-IF-CLNS-MEDIA-SPECIFIC-STATUS;
    }
    leaf time-until-next-lsp {
      xr:xr-xml-map "isis_oper_types:TimeUntilNextLSP";
      type uint32;
      description "Time until next LSP may be sent (ms)";
    }
    leaf lsp-transmit-requested-flag {
      xr:xr-xml-map "isis_oper_types:LSPTransmitRequestedFlag";
      type boolean;
      description "TRUE if an LSP transmission has been requested";
    }
    leaf lsp-transmitted-flag {
      xr:xr-xml-map "isis_oper_types:LSPTransmittedFlag";
      type boolean;
      description
        "TRUE if an LSP transmission has been sent,
        indicates LastLSPLevelTransmitted and
        LastLSP_IDTransmitted valid";
    }
    leaf lsp-txmitd-b2b-limit {
      xr:xr-xml-map "isis_oper_types:LSPTxmitdB2BLimit";
      type uint32;
      description
        "Number of LSPs that can be sent back to back in
        the current window without exceeding the pacing
        limit";
    }
    leaf lsp-txmt-b2b-msecs {
      xr:xr-xml-map "isis_oper_types:LSPTxmtB2BMsecs";
      type uint32;
      units "millisecond";
      description
        "Time im msecs indicating the end of the window
        in which the 'back to back lsps to be sent'
        counter applies";
    }
    leaf last-lsp-level-transmitted {
      xr:xr-xml-map "isis_oper_types:LastLSPLevelTransmitted";
      type Isis-level;
      description "Level of the Last LSP Transmitted";
    }
    leaf last-lsp-id-transmitted {
      xr:xr-xml-map "isis_oper_types:LastLSP_IDTransmitted";
      type xr:Isis-lsp-id;
      description "Last LSP ID Transmitted";
    }
  }

  grouping ISIS-SH-IF-BFD-TYPE {
    description "Per-interface BFD data";
    leaf enabled {
      xr:xr-xml-map "isis_oper_types:Enabled";
      type boolean;
      description "IPv4 BFD enabled status";
    }
    leaf ipv6-enabled {
      xr:xr-xml-map "isis_oper_types:IPv6Enabled";
      type boolean;
      description "IPv6 BFD enabled status";
    }
    leaf interval {
      xr:xr-xml-map "isis_oper_types:Interval";
      type uint32;
      units "millisecond";
      description "BFD hello minimum interval in milliseconds";
    }
    leaf multiplier {
      xr:xr-xml-map "isis_oper_types:Multiplier";
      type uint32;
      description "BFD hello multiplier";
    }
  }

  grouping ISIS-SH-IF-ACTIVE-P2P {
    description "Per-interface data";
    leaf time-until-next-iih {
      xr:xr-xml-map "isis_oper_types:TimeUntilNextIIH";
      type uint32;
      description "Time in ms before the next IIH can be sent";
    }
    leaf retransmit-lsp-queue-size {
      xr:xr-xml-map "isis_oper_types:RetransmitLSPQueueSize";
      type uint32;
      description "No. of LSPs queued to be retransmitted";
    }
    leaf retransmit-lsp-interval {
      xr:xr-xml-map "isis_oper_types:RetransmitLSPInterval";
      type uint32;
      description
        "Time in ms until the next scheduled LSP is
        retransmitted";
    }
    leaf extended-circuit-number {
      xr:xr-xml-map "isis_oper_types:ExtendedCircuitNumber";
      type Isis-extended-circuit-number;
      description
        "Extended Circuit Number valid for a P2P
        interface";
    }
  }

  grouping ISIS-SH-IF-ADV-PREFIX-DISABLED {
    description
      "Interface info when prefix advertisement is
      disabled";
    leaf reason-code {
      xr:xr-xml-map "isis_oper_types:ReasonCode";
      type Isis-if-adv-prefix-disabled-reason;
      description
        "Reason why the interface is not able to
        advertise prefixes";
    }
  }

  grouping ISIS-SH-IF-ADV-PREFIX-STATUS {
    description "ISIS SH IF ADV PREFIX STATUS";

    container disabled {
      when "../status = 'isis-disabled'" {
        description "../Status = 'ISIS_DISABLED'";
      }
      description
        "Disabled info for the prefix advertisement
        status";
      uses ISIS-SH-IF-ADV-PREFIX-DISABLED;
    }
    leaf status {
      xr:xr-xml-map "isis_oper_types:Status";
      type Isis-enabled;
      description "Status";
    }
  }

  grouping ISIS-SH-IF-ADJ-FORM-DISABLED {
    description
      "Interface info when adjacency formation is
      disabled";
    leaf reason-code {
      xr:xr-xml-map "isis_oper_types:ReasonCode";
      type Isis-if-adj-form-disabled-reason;
      description
        "Reason why the interface is not able to form
        adjacencies";
    }
  }

  grouping ISIS-SH-IF-ADJ-FORM-STATUS {
    description "ISIS SH IF ADJ FORM STATUS";

    container disabled {
      when "../status = 'isis-disabled'" {
        description "../Status = 'ISIS_DISABLED'";
      }
      description
        "Disabled info for the adjacency formation status";
      uses ISIS-SH-IF-ADJ-FORM-DISABLED;
    }
    leaf status {
      xr:xr-xml-map "isis_oper_types:Status";
      type Isis-enabled;
      description "Status";
    }
  }

  grouping ISIS-SH-IF-ENABLED {
    description "State of an enabled interface";

    container adjacency-form-status {
      description "Interface's Adjacency Formation status";
      uses ISIS-SH-IF-ADJ-FORM-STATUS;
    }

    container adv-prefix-status {
      description "Interface's Prefix Advertisement status";
      uses ISIS-SH-IF-ADV-PREFIX-STATUS;
    }

    container p2p-data {
      description
        "Data for an active P2P interface, NULL if not
        active or P2P";
      uses ISIS-SH-IF-ACTIVE-P2P;
    }

    container bfd-data {
      description "The BFD data for the given interface";
      uses ISIS-SH-IF-BFD-TYPE;
    }

    container clns-data {
      description "Interface data specific to CLNS I/O services";
      uses ISIS-SH-IF-CLNS;
    }
    leaf interface-media-type {
      xr:xr-xml-map "isis_oper_types:InterfaceMediaType";
      type Isis-media-class;
      description "Media type of the interface";
    }
    leaf enabled-circuit-type {
      xr:xr-xml-map "isis_oper_types:EnabledCircuitType";
      type Isis-levels;
      description "Enabled Circuit type of the interface";
    }
    leaf local-circuit-number {
      xr:xr-xml-map "isis_oper_types:LocalCircuitNumber";
      type Isis-circuit-number;
      description "Local Circuit Number of the interface";
    }

    list per-area-data {
      description
        "Array of area information for an active
        interface";
      uses ISIS-SH-IF-AREA-ACTIVE;
    }

    list per-topology-data {
      description "Array of topology information";
      uses ISIS-SH-IF-TOPO;
    }

    list per-address-family-data {
      description "Array of address family information";
      uses ISIS-SH-IF-AF;
    }
  }

  grouping ISIS-SH-IF-DISABLED {
    description "Disabled interface info";
    leaf reason-code {
      xr:xr-xml-map "isis_oper_types:ReasonCode";
      type Isis-if-disabled-reason;
      description "Reason why the interface is disabled";
    }
  }

  grouping ISIS-SH-IF-STATUS {
    description "ISIS SH IF STATUS";

    container disabled {
      when "../status = 'isis-disabled'" {
        description "../Status = 'ISIS_DISABLED'";
      }
      description "The interface state if disabled";
      uses ISIS-SH-IF-DISABLED;
    }

    container enabled {
      when "../status = 'isis-enabled'" {
        description "../Status = 'ISIS_ENABLED'";
      }
      description "The interface state if enabled";
      uses ISIS-SH-IF-ENABLED;
    }
    leaf status {
      xr:xr-xml-map "isis_oper_types:Status";
      type Isis-enabled;
      description "Status";
    }
  }

  grouping ISIS-SH-IF-CFG-STATUS {
    description "Configured state of an interface";
    leaf adjacency-form-status {
      xr:xr-xml-map "isis_oper_types:AdjacencyFormStatus";
      type boolean;
      description "Configured adjacency formation status";
    }
    leaf adv-prefix-status {
      xr:xr-xml-map "isis_oper_types:AdvPrefixStatus";
      type boolean;
      description "Configured prefix advertisement status";
    }
  }

  grouping ISIS-SH-IF {
    description "All the Information of an IS-IS interface";

    container configured-status {
      description "Configured interface status";
      uses ISIS-SH-IF-CFG-STATUS;
    }

    container interface-status-and-data {
      description
        "Information about the interface status and its
        data";
      uses ISIS-SH-IF-STATUS;
    }
    leaf configured-circuit-type {
      xr:xr-xml-map "isis_oper_types:ConfiguredCircuitType";
      type Isis-levels;
      description "Configured circuit type for the interface";
    }
    leaf mesh-group {
      xr:xr-xml-map "isis_oper_types:MeshGroup";
      type Isis-mesh-group-number;
      description "Interface mesh group";
    }
    leaf is-type {
      xr:xr-xml-map "isis_oper_types:ISType";
      type Isis-levels;
      description "IS-type of the router";
    }
    leaf nsr-intf {
      xr:xr-xml-map "isis_oper_types:NSR_INTF";
      type boolean;
      description "ISIS NSR Interface";
    }
  }

  grouping NSR-STATUS-NII-INTF {
    description "NSR STATUS NII INTF";
    leaf exist {
      xr:xr-xml-map "isis_oper_types:exist";
      type boolean;
      description "exist";
    }
    leaf brought-up {
      xr:xr-xml-map "isis_oper_types:brought_up";
      type boolean;
      description "brought up";
    }
    leaf retry-timer {
      xr:xr-xml-map "isis_oper_types:retry_timer";
      type boolean;
      description "retry timer";
    }
    leaf running {
      xr:xr-xml-map "isis_oper_types:running";
      type boolean;
      description "running";
    }
    leaf has-adj {
      xr:xr-xml-map "isis_oper_types:has_adj";
      type boolean;
      description "has adj";
    }
  }

  grouping NSR-STATUS-TE {
    description "NSR STATUS TE";
    leaf enabled {
      xr:xr-xml-map "isis_oper_types:enabled";
      type uint8;
      description "enabled";
    }
    leaf conn-up {
      xr:xr-xml-map "isis_oper_types:conn_up";
      type uint8;
      description "conn up";
    }
    leaf te-link-cb {
      xr:xr-xml-map "isis_oper_types:te_link_cb";
      type uint8;
      description "te link cb";
    }
    leaf te-tunnel-cb {
      xr:xr-xml-map "isis_oper_types:te_tunnel_cb";
      type uint8;
      description "te tunnel cb";
    }
    leaf adv-sync-data {
      xr:xr-xml-map "isis_oper_types:adv_sync_data";
      type uint8;
      description "adv sync data";
    }
    leaf link-purge-time-on {
      xr:xr-xml-map "isis_oper_types:link_purge_time_on";
      type uint8;
      description "link purge time on";
    }
    leaf tunnel-purge-time-on {
      xr:xr-xml-map "isis_oper_types:tunnel_purge_time_on";
      type uint8;
      description "tunnel purge time on";
    }
    leaf has-info-from-te {
      xr:xr-xml-map "isis_oper_types:has_info_from_te";
      type uint8;
      description "has info from te";
    }
  }

  grouping NSR-STATUS-DS {
    description "NSR STATUS DS";

    container conn-ts {
      description "conn ts";
      uses ISIS-SH-TIMESTAMP-TYPE;
    }

    container conn-cb-ts {
      description "conn cb ts";
      uses ISIS-SH-TIMESTAMP-TYPE;
    }

    container pub-ts {
      description "pub ts";
      uses ISIS-SH-TIMESTAMP-TYPE;
    }

    container pub-cb-ts {
      description "pub cb ts";
      uses ISIS-SH-TIMESTAMP-TYPE;
    }

    container reg-ts {
      description "reg ts";
      uses ISIS-SH-TIMESTAMP-TYPE;
    }

    container reg-cb-ts {
      description "reg cb ts";
      uses ISIS-SH-TIMESTAMP-TYPE;
    }

    container unreg-ts {
      description "unreg ts";
      uses ISIS-SH-TIMESTAMP-TYPE;
    }

    container unreg-cb-ts {
      description "unreg cb ts";
      uses ISIS-SH-TIMESTAMP-TYPE;
    }

    container disconn-cb-ts {
      description "disconn cb ts";
      uses ISIS-SH-TIMESTAMP-TYPE;
    }

    container notify-cb-ts {
      description "notify cb ts";
      uses ISIS-SH-TIMESTAMP-TYPE;
    }

    container del-cb-ts {
      description "del cb ts";
      uses ISIS-SH-TIMESTAMP-TYPE;
    }

    container remove-srv-ts {
      description "remove srv ts";
      uses ISIS-SH-TIMESTAMP-TYPE;
    }

    container conn-status-ts {
      description "conn status ts";
      uses ISIS-SH-TIMESTAMP-TYPE;
    }
    leaf conn {
      xr:xr-xml-map "isis_oper_types:conn";
      type uint8;
      description "conn";
    }
    leaf conn-cb {
      xr:xr-xml-map "isis_oper_types:conn_cb";
      type uint8;
      description "conn cb";
    }
    leaf pub {
      xr:xr-xml-map "isis_oper_types:pub";
      type uint8;
      description "pub";
    }
    leaf pub-cb {
      xr:xr-xml-map "isis_oper_types:pub_cb";
      type uint8;
      description "pub cb";
    }
    leaf reg {
      xr:xr-xml-map "isis_oper_types:reg";
      type uint8;
      description "reg";
    }
    leaf reg-cb {
      xr:xr-xml-map "isis_oper_types:reg_cb";
      type uint8;
      description "reg cb";
    }
    leaf unreg {
      xr:xr-xml-map "isis_oper_types:unreg";
      type uint8;
      description "unreg";
    }
    leaf unreg-cb {
      xr:xr-xml-map "isis_oper_types:unreg_cb";
      type uint8;
      description "unreg cb";
    }
    leaf disconn-cb {
      xr:xr-xml-map "isis_oper_types:disconn_cb";
      type uint8;
      description "disconn cb";
    }
    leaf notify-cb {
      xr:xr-xml-map "isis_oper_types:notify_cb";
      type uint8;
      description "notify cb";
    }
    leaf notify-peer-xr {
      xr:xr-xml-map "isis_oper_types:notify_peer";
      type yang:hex-string;
      description "notify peer xr";
    }
    leaf del-cb {
      xr:xr-xml-map "isis_oper_types:del_cb";
      type uint8;
      description "del cb";
    }
    leaf remove-srv {
      xr:xr-xml-map "isis_oper_types:remove_srv";
      type uint8;
      description "remove srv";
    }
    leaf conn-status {
      xr:xr-xml-map "isis_oper_types:conn_status";
      type boolean;
      description "conn status";
    }

    list notify-peer {
      max-elements "4";
      description "notify peer";
      uses ISIS-SH-TIMESTAMP-TYPE;
    }
  }

  grouping NSR-STATUS-ISM {
    description "NSR STATUS ISM";
    leaf conn {
      xr:xr-xml-map "isis_oper_types:conn";
      type uint8;
      description "conn";
    }
    leaf conn-cb {
      xr:xr-xml-map "isis_oper_types:conn_cb";
      type uint8;
      description "conn cb";
    }
    leaf disconn {
      xr:xr-xml-map "isis_oper_types:disconn";
      type uint8;
      description "disconn";
    }
    leaf disconn-cb {
      xr:xr-xml-map "isis_oper_types:disconn_cb";
      type uint8;
      description "disconn cb";
    }
    leaf ha-opt {
      xr:xr-xml-map "isis_oper_types:ha_opt";
      type uint8;
      description "ha opt";
    }
    leaf ha-opt-cb {
      xr:xr-xml-map "isis_oper_types:ha_opt_cb";
      type uint8;
      description "ha opt cb";
    }
    leaf wait-ready {
      xr:xr-xml-map "isis_oper_types:wait_ready";
      type uint8;
      description "wait ready";
    }
    leaf send-ready {
      xr:xr-xml-map "isis_oper_types:send_ready";
      type uint8;
      description "send ready";
    }
    leaf evt-rsp-cb {
      xr:xr-xml-map "isis_oper_types:evt_rsp_cb";
      type uint8;
      description "evt rsp cb";
    }
    leaf reg-rsp-cb {
      xr:xr-xml-map "isis_oper_types:reg_rsp_cb";
      type uint8;
      description "reg rsp cb";
    }
    leaf conn-status {
      xr:xr-xml-map "isis_oper_types:conn_status";
      type boolean;
      description "conn status";
    }
  }

  grouping NSR-STATUS-PM {
    description "NSR STATUS PM";
    leaf reg {
      xr:xr-xml-map "isis_oper_types:reg";
      type uint8;
      description "reg";
    }
    leaf conn-cb {
      xr:xr-xml-map "isis_oper_types:conn_cb";
      type uint8;
      description "conn cb";
    }
    leaf disconn-cb {
      xr:xr-xml-map "isis_oper_types:disconn_cb";
      type uint8;
      description "disconn cb";
    }
    leaf conn-status {
      xr:xr-xml-map "isis_oper_types:conn_status";
      type boolean;
      description "conn status";
    }
  }

  grouping NSR-STATUS-NCD {
    description "NSR STATUS NCD";
    leaf vm-idx {
      xr:xr-xml-map "isis_oper_types:vm_idx";
      type uint8;
      description "vm idx";
    }
    leaf conn-up {
      xr:xr-xml-map "isis_oper_types:conn_up";
      type boolean;
      description "conn up";
    }
    leaf endp-hdl {
      xr:xr-xml-map "isis_oper_types:endp_hdl";
      type uint8;
      description "endp hdl";
    }
    leaf chksum {
      xr:xr-xml-map "isis_oper_types:chksum";
      type uint16;
      description "chksum";
    }
    leaf send-seqnum {
      xr:xr-xml-map "isis_oper_types:send_seqnum";
      type uint32;
      description "send seqnum";
    }
    leaf recv-cnt {
      xr:xr-xml-map "isis_oper_types:recv_cnt";
      type uint32;
      description "recv cnt";
    }
  }

  grouping NSR-STATUS-GEN {
    description "NSR STATUS GEN";
    leaf my-nodeid {
      xr:xr-xml-map "isis_oper_types:my_nodeid";
      type uint32;
      description "my nodeid";
    }
    leaf my-process-id {
      xr:xr-xml-map "isis_oper_types:my_process_id";
      type uint32;
      description "my process id";
    }
    leaf pm-issu-role {
      xr:xr-xml-map "isis_oper_types:pm_issu_role";
      type uint8;
      description "pm issu role";
    }
    leaf pm-ha-role {
      xr:xr-xml-map "isis_oper_types:pm_ha_role";
      type uint8;
      description "pm ha role";
    }
    leaf sysmgr-ha-role {
      xr:xr-xml-map "isis_oper_types:sysmgr_ha_role";
      type uint8;
      description "sysmgr ha role";
    }
    leaf nsr-send-ready {
      xr:xr-xml-map "isis_oper_types:nsr_send_ready";
      type uint8;
      description "nsr send ready";
    }
    leaf nsr-send-unready {
      xr:xr-xml-map "isis_oper_types:nsr_send_unready";
      type uint8;
      description "nsr send unready";
    }
    leaf nsr-send-err {
      xr:xr-xml-map "isis_oper_types:nsr_send_err";
      type uint32;
      description "nsr send err";
    }
    leaf nsr-recv-err {
      xr:xr-xml-map "isis_oper_types:nsr_recv_err";
      type uint32;
      description "nsr recv err";
    }
    leaf retry-flag {
      xr:xr-xml-map "isis_oper_types:retry_flag";
      type uint32;
      description "retry flag";
    }
    leaf nsr-enabled {
      xr:xr-xml-map "isis_oper_types:nsr_enabled";
      type boolean;
      description "nsr enabled";
    }
    leaf nsr-configured {
      xr:xr-xml-map "isis_oper_types:nsr_configured";
      type boolean;
      description "nsr configured";
    }
    leaf nsf-configured {
      xr:xr-xml-map "isis_oper_types:nsf_configured";
      type boolean;
      description "nsf configured";
    }
    leaf failover {
      xr:xr-xml-map "isis_oper_types:failover";
      type boolean;
      description "failover";
    }
    leaf lanid-req-needed {
      xr:xr-xml-map "isis_oper_types:lanid_req_needed";
      type boolean;
      description "lanid req needed";
    }
  }

  grouping NSR-STATUS-INFRA-TYPE {
    description "NSR STATUS INFRA TYPE";

    container gen {
      description "gen";
      uses NSR-STATUS-GEN;
    }

    container pm {
      description "pm";
      uses NSR-STATUS-PM;
    }

    container ism {
      description "ism";
      uses NSR-STATUS-ISM;
    }

    container ds {
      description "ds";
      uses NSR-STATUS-DS;
    }

    container te {
      description "te";
      uses NSR-STATUS-TE;
    }

    list ncd {
      max-elements "5";
      description "ncd";
      uses NSR-STATUS-NCD;
    }

    list nii-idb {
      max-elements "3";
      description "nii idb";
      uses NSR-STATUS-NII-INTF;
    }
  }

  grouping NSR-STATUS-GBL-TYPE {
    description "NSR STATUS GBL TYPE";
    leaf-list full-sync-achieved {
      xr:xr-xml-map "isis_oper_types:full_sync_achieved";
      type uint32;
      max-elements "3";
      description "full sync achieved";
    }
    leaf-list man-sync-count {
      xr:xr-xml-map "isis_oper_types:man_sync_count";
      type uint32;
      max-elements "3";
      description "man sync count";
    }
    leaf-list nsr-chg-count {
      xr:xr-xml-map "isis_oper_types:nsr_chg_count";
      type uint32;
      max-elements "3";
      description "nsr chg count";
    }
    leaf-list uptime {
      xr:xr-xml-map "isis_oper_types:uptime";
      type uint32;
      max-elements "3";
      description "uptime";
    }

    list uptime-valid {
      min-elements "3";
      max-elements "3";
      description "uptime valid";
      leaf entry {
        type boolean;
        description "Array entry.";
      }
    }
  }

  grouping ISIS-SH-NSR-STATUS-GLOBAL {
    description "IS-IS process NSR status";

    container isis-nsr-peer {
      description "ISIS NSR PEER STATUS";
      uses NSR-STATUS-GBL-TYPE;
    }

    container isis-nsr-infra {
      description "ISIS NSR Infra";
      uses NSR-STATUS-INFRA-TYPE;
    }
    leaf isis-vm-state {
      xr:xr-xml-map "isis_oper_types:ISIS_VM_STATE";
      type uint16;
      description "ISIS VM STATE";
    }
  }

  grouping ISIS-SH-IPV4-ROUTE-SUMMARIZATION-STATUS {
    description "Summarization status";

    container summary-prefix {
      when "../is-valid = 'isis-valid'" {
        description "../IsValid = 'ISIS_VALID'";
      }
      description "Summarizing Prefix";
      uses ISIS-IPV4-PREFIX-TYPE;
    }
    leaf is-valid {
      xr:xr-xml-map "isis_oper_types:IsValid";
      type Isis-valid;
      description "IsValid";
    }
  }

  grouping ISIS-SH-IPV4-ROUTE-ADV {
    description "How a prefix is advertised in a particular level";

    container summarization-status {
      description "Status of summarization for the prefix";
      uses ISIS-SH-IPV4-ROUTE-SUMMARIZATION-STATUS;
    }
    leaf level {
      xr:xr-xml-map "isis_oper_types:Level";
      type Isis-level;
      description "Level in which the prefix is advertised";
    }
    leaf advertising-origin {
      xr:xr-xml-map "isis_oper_types:AdvertisingOrigin";
      type Isis-sh-route-adv-origin;
      description "The origin of the advertisement";
    }
    leaf metric {
      xr:xr-xml-map "isis_oper_types:Metric";
      type Isis-metric;
      description "Metric with which the prefix is advertised";
    }
    leaf is-propagated {
      xr:xr-xml-map "isis_oper_types:IsPropagated";
      type boolean;
      description
        "Has the prefix been propagated from another
        level?";
    }
    leaf is-external-metric {
      xr:xr-xml-map "isis_oper_types:IsExternalMetric";
      type boolean;
      description "Is the metric an external metric?";
    }
    leaf is-external-reachability {
      xr:xr-xml-map "isis_oper_types:IsExternalReachability";
      type boolean;
      description "Is the prefix external to the IS-IS domain?";
    }
    leaf is-interarea {
      xr:xr-xml-map "isis_oper_types:IsInterarea";
      type boolean;
      description "Is the up/down bit set?";
    }
    leaf-list tags {
      xr:xr-xml-map "isis_oper_types:Tags";
      type Isis-prefix-tag;
      description "Tags associated with the prefix";
    }

    list nodal-sid {
      description "Nodal SIDs with the prefix item";
      uses ISIS-NODAL-SID-TYPE;
    }
  }

  grouping ISIS-SH-IPV4-ROUTE-NATIVE-SOURCE {
    description "Source of a native route";
    leaf source-lsp-id {
      xr:xr-xml-map "isis_oper_types:SourceLSP_ID";
      type xr:Isis-lsp-id;
      description "ID of the LSP advertising the prefix";
    }
    leaf source-address {
      xr:xr-xml-map "isis_oper_types:SourceAddress";
      type Isis-ipv4-address;
      description "Source address of the IS advertising the prefix";
    }
    leaf-list tags {
      xr:xr-xml-map "isis_oper_types:Tags";
      type Isis-prefix-tag;
      description "Tags associated with the prefix item";
    }

    list nodal-sid {
      description "Nodal SIDs with the prefix item";
      uses ISIS-NODAL-SID-TYPE;
    }
  }

  grouping ISIS-SH-IPV4-UCMP-PATH {
    description "IPv4 path to a destination";

    container frr-backup {
      description "FRR backup for this path";
      uses ISIS-SH-IPV4-FRR-BACKUP;
    }
    leaf neighbor-id {
      xr:xr-xml-map "isis_oper_types:NeighborID";
      type xr:Osi-system-id;
      description "Next hop neighbor ID";
    }
    leaf egress-interface {
      xr:xr-xml-map "isis_oper_types:EgressInterface";
      type Isis-sh-interface-name;
      description "Interface to send the packet out of";
    }
    leaf neighbor-address {
      xr:xr-xml-map "isis_oper_types:NeighborAddress";
      type Isis-ipv4-address;
      description "Next hop neighbor's forwarding address";
    }
    leaf neighbor-snpa {
      xr:xr-xml-map "isis_oper_types:NeighborSNPA";
      type xr:Isis-snpa;
      description "Next hop neighbor's SNPA";
    }
    leaf tag {
      xr:xr-xml-map "isis_oper_types:Tag";
      type Isis-prefix-tag;
      description "Tag associated with the path";
    }
    leaf total-ucmp-distance {
      xr:xr-xml-map "isis_oper_types:TotalUCMPDistance";
      type Isis-metric;
      description "Distance to the network via this UCMP next hop";
    }
    leaf segment-routing-sid-value {
      xr:xr-xml-map "isis_oper_types:SegmentRoutingSidValue";
      type Isis-nodal-sid-value;
      description
        "Segment routing sid value received from first
        hop";
    }
    leaf weight {
      xr:xr-xml-map "isis_oper_types:Weight";
      type Isis-metric;
      description "Weight configured on the interface";
    }
  }

  grouping ISIS-SH-IPV4-ROUTE-NATIVE-PREFERENCE {
    description
      "Paths and sources for a native route at a
      particular preference";
    leaf origin {
      xr:xr-xml-map "isis_oper_types:Origin";
      type Isis-prefix-origin;
      description "Origin of route";
    }
    leaf metric {
      xr:xr-xml-map "isis_oper_types:Metric";
      type Isis-metric;
      description "Distance to network";
    }
    leaf multicast-metric {
      xr:xr-xml-map "isis_oper_types:MulticastMetric";
      type Isis-metric;
      description "Multicast-intact distance to network";
    }
    leaf is-external-metric {
      xr:xr-xml-map "isis_oper_types:IsExternalMetric";
      type boolean;
      description "Is the metric an external metric?";
    }
    leaf administrative-distance {
      xr:xr-xml-map "isis_oper_types:AdministrativeDistance";
      type uint16;
      description "Administrative Distance";
    }

    list paths {
      description "First hops toward the prefix";
      uses ISIS-SH-IPV4-PATH;
    }

    list ucmp-next-hop {
      description "UCMP first hops toward the prefix";
      uses ISIS-SH-IPV4-UCMP-PATH;
    }

    list multicast-path {
      description "Multicast intact first hops toward the prefix";
      uses ISIS-SH-IPV4-PATH;
    }

    list srte-path {
      description "SR-TE native first hops toward the prefix";
      uses ISIS-SH-IPV4-PATH;
    }

    list source {
      description "Sources advertising the prefix";
      uses ISIS-SH-IPV4-ROUTE-NATIVE-SOURCE;
    }

    list multicast-source {
      description "Multicast-intact sources advertising the prefix";
      uses ISIS-SH-IPV4-ROUTE-NATIVE-SOURCE;
    }
  }

  grouping ISIS-SH-IPV4-ROUTE-NATIVE-DETAILS {
    description "Details of a native IS-IS route to a prefix";

    container primary {
      description "Primary paths to prefix";
      uses ISIS-SH-IPV4-ROUTE-NATIVE-PREFERENCE;
    }
    leaf priority {
      xr:xr-xml-map "isis_oper_types:Priority";
      type Isis-prefix-priority;
      description "Relative importance of the prefix";
    }

    list backup {
      description "Backup paths to prefix";
      uses ISIS-SH-IPV4-ROUTE-NATIVE-PREFERENCE;
    }
  }

  grouping ISIS-SH-IPV4-ROUTE-NATIVE-STATUS {
    description "Status of a native IS-IS route to a prefix";

    container native-details {
      when "../is-valid = 'isis-valid'" {
        description "../IsValid = 'ISIS_VALID'";
      }
      description "Details of the native route";
      uses ISIS-SH-IPV4-ROUTE-NATIVE-DETAILS;
    }
    leaf is-valid {
      xr:xr-xml-map "isis_oper_types:IsValid";
      type Isis-valid;
      description "IsValid";
    }
  }

  grouping ISIS-SH-IPV4-ROUTE {
    description "IS-IS IPv4 route";

    container connected-status {
      description
        "Status of IS-IS directly connected routes to the
        prefix";
      uses ISIS-SH-ROUTE-CONN-STATUS;
    }

    container redistributed-status {
      description
        "Status of other protocols' routes redistributed
        into IS-IS";
      uses ISIS-SH-ROUTE-REDIST-STATUS;
    }

    container native-status {
      description "Status of native IS-IS routes to the prefix";
      uses ISIS-SH-IPV4-ROUTE-NATIVE-STATUS;
    }

    list per-level-advertising-detail {
      description
        "Per level details of how the local system
        advertises the prefix";
      uses ISIS-SH-IPV4-ROUTE-ADV;
    }
  }

  grouping ISIS-SH-IPV6-ROUTE-SUMMARIZATION-STATUS {
    description "Summarization status";

    container summary-prefix {
      when "../is-valid = 'isis-valid'" {
        description "../IsValid = 'ISIS_VALID'";
      }
      description "Summarizing Prefix";
      uses ISIS-IPV6-PREFIX-TYPE;
    }
    leaf is-valid {
      xr:xr-xml-map "isis_oper_types:IsValid";
      type Isis-valid;
      description "IsValid";
    }
  }

  grouping ISIS-SH-IPV6-ROUTE-ADV {
    description "How a prefix is advertised in a particular level";

    container summarization-status {
      description "Status of summarization for the prefix";
      uses ISIS-SH-IPV6-ROUTE-SUMMARIZATION-STATUS;
    }
    leaf level {
      xr:xr-xml-map "isis_oper_types:Level";
      type Isis-level;
      description "Level in which the prefix is advertised";
    }
    leaf advertising-origin {
      xr:xr-xml-map "isis_oper_types:AdvertisingOrigin";
      type Isis-sh-route-adv-origin;
      description "The origin of the advertisement";
    }
    leaf metric {
      xr:xr-xml-map "isis_oper_types:Metric";
      type Isis-metric;
      description "Metric with which the prefix is advertised";
    }
    leaf is-propagated {
      xr:xr-xml-map "isis_oper_types:IsPropagated";
      type boolean;
      description
        "Has the prefix been propagated from another
        level?";
    }
    leaf is-external-metric {
      xr:xr-xml-map "isis_oper_types:IsExternalMetric";
      type boolean;
      description "Is the metric an external metric?";
    }
    leaf is-external-reachability {
      xr:xr-xml-map "isis_oper_types:IsExternalReachability";
      type boolean;
      description "Is the prefix external to the IS-IS domain?";
    }
    leaf is-interarea {
      xr:xr-xml-map "isis_oper_types:IsInterarea";
      type boolean;
      description "Is the up/down bit set?";
    }
    leaf-list tags {
      xr:xr-xml-map "isis_oper_types:Tags";
      type Isis-prefix-tag;
      description "Tags associated with the prefix";
    }

    list nodal-sid {
      description "Nodal SIDs with the prefix item";
      uses ISIS-NODAL-SID-TYPE;
    }
  }

  grouping ISIS-NODAL-SID-TYPE {
    description "ISIS NODAL SID TYPE";
    leaf sid-value {
      xr:xr-xml-map "isis_oper_types:sid_value";
      type Isis-nodal-sid-value;
      description "sid value";
    }
    leaf rflag {
      xr:xr-xml-map "isis_oper_types:rflag";
      type uint8;
      description "rflag";
    }
    leaf nflag {
      xr:xr-xml-map "isis_oper_types:nflag";
      type uint8;
      description "nflag";
    }
    leaf pflag {
      xr:xr-xml-map "isis_oper_types:pflag";
      type uint8;
      description "pflag";
    }
    leaf eflag {
      xr:xr-xml-map "isis_oper_types:eflag";
      type uint8;
      description "eflag";
    }
    leaf vflag {
      xr:xr-xml-map "isis_oper_types:vflag";
      type uint8;
      description "vflag";
    }
    leaf lflag {
      xr:xr-xml-map "isis_oper_types:lflag";
      type uint8;
      description "lflag";
    }
  }

  grouping ISIS-SH-IPV6-ROUTE-NATIVE-SOURCE {
    description "Source of a native route";
    leaf source-lsp-id {
      xr:xr-xml-map "isis_oper_types:SourceLSP_ID";
      type xr:Isis-lsp-id;
      description "ID of the LSP advertising the prefix";
    }
    leaf source-address {
      xr:xr-xml-map "isis_oper_types:SourceAddress";
      type Isis-ipv6-address;
      description "Source address of the IS advertising the prefix";
    }
    leaf-list tags {
      xr:xr-xml-map "isis_oper_types:Tags";
      type Isis-prefix-tag;
      description "Tags associated with the prefix item";
    }

    list nodal-sid {
      description "Nodal SIDs with the prefix item";
      uses ISIS-NODAL-SID-TYPE;
    }
  }

  grouping ISIS-SH-IPV6-UCMP-PATH {
    description "IPv6 path to a destination";

    container frr-backup {
      description "FRR backup for this path";
      uses ISIS-SH-IPV6-FRR-BACKUP;
    }
    leaf neighbor-id {
      xr:xr-xml-map "isis_oper_types:NeighborID";
      type xr:Osi-system-id;
      description "Next hop neighbor ID";
    }
    leaf egress-interface {
      xr:xr-xml-map "isis_oper_types:EgressInterface";
      type Isis-sh-interface-name;
      description "Interface to send the packet out of";
    }
    leaf neighbor-address {
      xr:xr-xml-map "isis_oper_types:NeighborAddress";
      type Isis-ipv6-address;
      description "Next hop neighbor's forwarding address";
    }
    leaf neighbor-snpa {
      xr:xr-xml-map "isis_oper_types:NeighborSNPA";
      type xr:Isis-snpa;
      description "Next hop neighbor's SNPA";
    }
    leaf tag {
      xr:xr-xml-map "isis_oper_types:Tag";
      type Isis-prefix-tag;
      description "Tag associated with the path";
    }
    leaf total-ucmp-distance {
      xr:xr-xml-map "isis_oper_types:TotalUCMPDistance";
      type Isis-metric;
      description "Distance to the network via this UCMP next hop";
    }
    leaf segment-routing-sid-value {
      xr:xr-xml-map "isis_oper_types:SegmentRoutingSidValue";
      type Isis-nodal-sid-value;
      description
        "Segment routing sid value received from first
        hop";
    }
    leaf weight {
      xr:xr-xml-map "isis_oper_types:Weight";
      type Isis-metric;
      description "Weight configured on the interface";
    }
  }

  grouping ISIS-SH-IPV6-ROUTE-NATIVE-PREFERENCE {
    description
      "Paths and sources for a native route at a
      particular preference";
    leaf origin {
      xr:xr-xml-map "isis_oper_types:Origin";
      type Isis-prefix-origin;
      description "Origin of route";
    }
    leaf metric {
      xr:xr-xml-map "isis_oper_types:Metric";
      type Isis-metric;
      description "Distance to network";
    }
    leaf multicast-metric {
      xr:xr-xml-map "isis_oper_types:MulticastMetric";
      type Isis-metric;
      description "Multicast-intact distance to network";
    }
    leaf is-external-metric {
      xr:xr-xml-map "isis_oper_types:IsExternalMetric";
      type boolean;
      description "Is the metric an external metric?";
    }
    leaf administrative-distance {
      xr:xr-xml-map "isis_oper_types:AdministrativeDistance";
      type uint16;
      description "Administrative Distance";
    }

    list paths {
      description "First hops toward the prefix";
      uses ISIS-SH-IPV6-PATH;
    }

    list ucmp-next-hop {
      description "UCMP first hops toward the prefix";
      uses ISIS-SH-IPV6-UCMP-PATH;
    }

    list multicast-path {
      description "Multicast intact first hops toward the prefix";
      uses ISIS-SH-IPV6-PATH;
    }

    list srte-path {
      description "SR-TE native first hops toward the prefix";
      uses ISIS-SH-IPV6-PATH;
    }

    list source {
      description "Sources advertising the prefix";
      uses ISIS-SH-IPV6-ROUTE-NATIVE-SOURCE;
    }

    list multicast-source {
      description "Multicast-intact sources advertising the prefix";
      uses ISIS-SH-IPV6-ROUTE-NATIVE-SOURCE;
    }
  }

  grouping ISIS-SH-IPV6-ROUTE-NATIVE-DETAILS {
    description "Details of a native IS-IS route to a prefix";

    container primary {
      description "Primary paths to prefix";
      uses ISIS-SH-IPV6-ROUTE-NATIVE-PREFERENCE;
    }
    leaf priority {
      xr:xr-xml-map "isis_oper_types:Priority";
      type Isis-prefix-priority;
      description "Relative importance of the prefix";
    }

    list backup {
      description "Backup paths to prefix";
      uses ISIS-SH-IPV6-ROUTE-NATIVE-PREFERENCE;
    }
  }

  grouping ISIS-SH-IPV6-ROUTE-NATIVE-STATUS {
    description "Status of a native IS-IS route to a prefix";

    container native-details {
      when "../is-valid = 'isis-valid'" {
        description "../IsValid = 'ISIS_VALID'";
      }
      description "Details of the native route";
      uses ISIS-SH-IPV6-ROUTE-NATIVE-DETAILS;
    }
    leaf is-valid {
      xr:xr-xml-map "isis_oper_types:IsValid";
      type Isis-valid;
      description "IsValid";
    }
  }

  grouping ISIS-SH-REDIST-ENTRY-PROTO {
    description "Redistributed protocol information";
    leaf protocol {
      xr:xr-xml-map "isis_oper_types:Protocol";
      type Isis-redist-proto;
      description "Protocol";
    }
    leaf isis-instance-id {
      xr:xr-xml-map "isis_oper_types:ISISInstanceID";
      when "../protocol = 'isis-redist-isis'" {
        description "../Protocol = 'ISIS_REDIST_ISIS'";
      }
      type Isis-string;
      description "IS-IS instance identifier";
    }
    leaf ospf-process-id {
      xr:xr-xml-map "isis_oper_types:OSPFProcessID";
      when "../protocol = 'isis-redist-ospf'" {
        description "../Protocol = 'ISIS_REDIST_OSPF'";
      }
      type Isis-string;
      description "OSPF process identifier";
    }
    leaf ospfv3-process-id {
      xr:xr-xml-map "isis_oper_types:OSPFv3ProcessID";
      when "../protocol = 'isis-redist-ospfv3'" {
        description "../Protocol = 'ISIS_REDIST_OSPFV3'";
      }
      type Isis-string;
      description "OSPFv3 process identifier";
    }
    leaf bgp-as-number {
      xr:xr-xml-map "isis_oper_types:BGP_ASNumber";
      when "../protocol = 'isis-redist-bgp'" {
        description "../Protocol = 'ISIS_REDIST_BGP'";
      }
      type Isis-string;
      description "BGP Autonomous System number";
    }
    leaf eigrp-as-number {
      xr:xr-xml-map "isis_oper_types:EIGRP_ASNumber";
      when "../protocol = 'isis-redist-eigrp'" {
        description "../Protocol = 'ISIS_REDIST_EIGRP'";
      }
      type Isis-string;
      description "EIGRP Autonomous System number";
    }
    leaf application-name {
      xr:xr-xml-map "isis_oper_types:Application_Name";
      when "../protocol = 'isis-redist-application'" {
        description "../Protocol = 'ISIS_REDIST_APPLICATION'";
      }
      type Isis-string;
      description "Application Name";
    }
  }

  grouping ISIS-SH-ROUTE-REDIST-LEVEL-DETAILS {
    description
      "Details of a route redistributed into a
      particular level";

    container owner {
      description "Protocol redistributing the route";
      uses ISIS-SH-REDIST-ENTRY-PROTO;
    }
    leaf level {
      xr:xr-xml-map "isis_oper_types:Level";
      type Isis-level;
      description "Level into which the route is redistributed";
    }
  }

  grouping ISIS-SH-ROUTE-REDIST-DETAILS {
    description "ISIS SH ROUTE REDIST DETAILS";

    list isis-sh-route-redist-detail {
      description "isis sh route redist detail";
      uses ISIS-SH-ROUTE-REDIST-LEVEL-DETAILS;
    }
  }

  grouping ISIS-SH-ROUTE-REDIST-STATUS {
    description "Status of redistributed routes to a prefix";

    container redistribution-details {
      when "../is-valid = 'isis-valid'" {
        description "../IsValid = 'ISIS_VALID'";
      }
      description "Per level details of the redistributed route";
      uses ISIS-SH-ROUTE-REDIST-DETAILS;
    }
    leaf is-valid {
      xr:xr-xml-map "isis_oper_types:IsValid";
      type Isis-valid;
      description "IsValid";
    }
  }

  grouping ISIS-SH-ROUTE-CONN-DETAILS {
    description "Details of an IS-IS directly connected prefix";
    leaf-list interface {
      xr:xr-xml-map "isis_oper_types:Interfaces";
      type Isis-sh-interface-name;
      description "Interfaces";
    }
  }

  grouping ISIS-SH-ROUTE-CONN-STATUS {
    description "Status of an IS-IS directly connected prefix";

    container connected-details {
      when "../is-valid = 'isis-valid'" {
        description "../IsValid = 'ISIS_VALID'";
      }
      description "Details of the directly connected prefix";
      uses ISIS-SH-ROUTE-CONN-DETAILS;
    }
    leaf is-valid {
      xr:xr-xml-map "isis_oper_types:IsValid";
      type Isis-valid;
      description "IsValid";
    }
  }

  grouping ISIS-SH-IPV6-ROUTE {
    description "IS-IS IPv6 route";

    container connected-status {
      description
        "Status of IS-IS directly connected routes to the
        prefix";
      uses ISIS-SH-ROUTE-CONN-STATUS;
    }

    container redistributed-status {
      description
        "Status of other protocols' routes redistributed
        into IS-IS";
      uses ISIS-SH-ROUTE-REDIST-STATUS;
    }

    container native-status {
      description "Status of native IS-IS routes to the prefix";
      uses ISIS-SH-IPV6-ROUTE-NATIVE-STATUS;
    }

    list per-level-advertising-detail {
      description
        "Per level details of how the local system
        advertises the prefix";
      uses ISIS-SH-IPV6-ROUTE-ADV;
    }
  }

  grouping ISIS-SH-IPV6-FRR-BACKUP {
    description "FRR backup path";
    leaf neighbor-id {
      xr:xr-xml-map "isis_oper_types:NeighborID";
      type xr:Osi-system-id;
      description "Next hop neighbor ID";
    }
    leaf egress-interface {
      xr:xr-xml-map "isis_oper_types:EgressInterface";
      type Isis-sh-interface-name;
      description "Interface to send the packet out of";
    }
    leaf neighbor-address {
      xr:xr-xml-map "isis_oper_types:NeighborAddress";
      type Isis-ipv6-address;
      description "Next hop neighbor's forwarding address";
    }
    leaf neighbor-snpa {
      xr:xr-xml-map "isis_oper_types:NeighborSNPA";
      type xr:Isis-snpa;
      description "Next hop neighbor's SNPA";
    }
    leaf remote-lfa-system-id {
      xr:xr-xml-map "isis_oper_types:RemoteLFASystemID";
      type xr:Osi-system-id;
      description "Remote LFA PQ Node's ID";
    }
    leaf remote-lfa-router-id {
      xr:xr-xml-map "isis_oper_types:RemoteLFARouterID";
      type Isis-ipv6-address;
      description "Remote LFA Router ID";
    }
    leaf remote-lfa-system-pid {
      xr:xr-xml-map "isis_oper_types:RemoteLFASystemPID";
      type xr:Osi-system-id;
      description "Remote LFA PQ Node's ID";
    }
    leaf remote-lfa-router-pid {
      xr:xr-xml-map "isis_oper_types:RemoteLFARouterPID";
      type Isis-ipv6-address;
      description "Remote LFA Router ID";
    }
    leaf total-backup-distance {
      xr:xr-xml-map "isis_oper_types:TotalBackupDistance";
      type Isis-metric;
      description "Distance to the network via this backup path";
    }
    leaf segment-routing-sid-value {
      xr:xr-xml-map "isis_oper_types:SegmentRoutingSidValue";
      type Isis-nodal-sid-value;
      description
        "Segment routing sid value received from first
        hop";
    }
    leaf num-sid {
      xr:xr-xml-map "isis_oper_types:NumSid";
      type uint32;
      description "Number of SIDs in TI-LFA/rLFA";
    }
    leaf is-downstream {
      xr:xr-xml-map "isis_oper_types:IsDownstream";
      type boolean;
      description "Is the backup path via downstream node?";
    }
    leaf is-lc-disjoint {
      xr:xr-xml-map "isis_oper_types:IsLCDisjoint";
      type boolean;
      description
        "Is the backup path line card disjoint with
        primary?";
    }
    leaf is-node-protecting {
      xr:xr-xml-map "isis_oper_types:IsNodeProtecting";
      type boolean;
      description "Is the backup path node protecting?";
    }
    leaf is-primary-path {
      xr:xr-xml-map "isis_oper_types:IsPrimaryPath";
      type boolean;
      description "Is the backup path an ECMP to the network?";
    }
    leaf is-srlg-disjoint {
      xr:xr-xml-map "isis_oper_types:IsSRLGDisjoint";
      type boolean;
      description "Is the backup path SRLG disjoint with primary?";
    }
    leaf is-remote-lfa {
      xr:xr-xml-map "isis_oper_types:IsRemoteLFA";
      type boolean;
      description "Is the backup path via a Remote LFA?";
    }
    leaf is-epcfrr-lfa {
      xr:xr-xml-map "isis_oper_types:IsEpcfrrLFA";
      type boolean;
      description "Is the backup path via a TI-LFA?";
    }
    leaf weight {
      xr:xr-xml-map "isis_oper_types:Weight";
      type Isis-metric;
      description "Weight configured on the interface";
    }
    leaf-list segment-routing-sid-value-entry {
      xr:xr-xml-map "isis_oper_types:SegmentRoutingSidValues";
      type Isis-nodal-sid-value;
      max-elements "3";
      description "Segment routing sid values for TI-LFA/rLFA";
    }
  }

  grouping ISIS-SH-IPV6-PATH {
    description "IPv6 path to a destination";

    container frr-backup {
      description "FRR backup for this path";
      uses ISIS-SH-IPV6-FRR-BACKUP;
    }
    leaf neighbor-id {
      xr:xr-xml-map "isis_oper_types:NeighborID";
      type xr:Osi-system-id;
      description "Next hop neighbor ID";
    }
    leaf egress-interface {
      xr:xr-xml-map "isis_oper_types:EgressInterface";
      type Isis-sh-interface-name;
      description "Interface to send the packet out of";
    }
    leaf neighbor-address {
      xr:xr-xml-map "isis_oper_types:NeighborAddress";
      type Isis-ipv6-address;
      description "Next hop neighbor's forwarding address";
    }
    leaf neighbor-snpa {
      xr:xr-xml-map "isis_oper_types:NeighborSNPA";
      type xr:Isis-snpa;
      description "Next hop neighbor's SNPA";
    }
    leaf tag {
      xr:xr-xml-map "isis_oper_types:Tag";
      type Isis-prefix-tag;
      description "Tag associated with the path";
    }
    leaf segment-routing-sid-value {
      xr:xr-xml-map "isis_oper_types:SegmentRoutingSidValue";
      type Isis-nodal-sid-value;
      description
        "Segment routing sid value received from first
        hop";
    }
    leaf weight {
      xr:xr-xml-map "isis_oper_types:Weight";
      type Isis-metric;
      description "Weight configured on the interface";
    }
  }

  grouping ISIS-SH-IPV6-TOPO-REACHABLE-DETAILS {
    description "Status of a reachable IPv6 IS";
    leaf root-distance {
      xr:xr-xml-map "isis_oper_types:RootDistance";
      type Isis-metric;
      description "Distance to the IS";
    }
    leaf multicast-root-distance {
      xr:xr-xml-map "isis_oper_types:MulticastRootDistance";
      type Isis-metric;
      description "Distance to the IS";
    }

    list paths {
      description "First hops towards the IS";
      uses ISIS-SH-IPV6-PATH;
    }

    list multicast-path {
      description "Multicast intact first hops towards the IS";
      uses ISIS-SH-IPV6-PATH;
    }

    list parent {
      description "Parents of the IS within the SPT";
      uses ISIS-SH-TOPO-NEIGHBOR;
    }

    list children {
      description "Children of the IS within the SPT";
      uses ISIS-SH-TOPO-NEIGHBOR;
    }
  }

  grouping ISIS-SH-IPV6-TOPO-REACHABLE-STATUS {
    description "Reachability status of an IPv6 IS";

    container reachable-details {
      when "../reachable-status = 'isis-reachable'" {
        description "../ReachableStatus = 'ISIS_REACHABLE'";
      }
      description "Status of the IS within the SPT";
      uses ISIS-SH-IPV6-TOPO-REACHABLE-DETAILS;
    }
    leaf reachable-status {
      xr:xr-xml-map "isis_oper_types:ReachableStatus";
      type Isis-reachable;
      description "ReachableStatus";
    }
  }

  grouping ISIS-SH-IPV6-TOPO-ENTRY {
    description "IPv6 IS Link Topology Entry";

    container reachability-status {
      description
        "Is the IS reachable, and, if so, its status
        within the SPT";
      uses ISIS-SH-IPV6-TOPO-REACHABLE-STATUS;
    }

    container advertised-prefix-item-counts {
      description
        "Per-priority counts of prefix items advertised
        by the IS";
      uses ISIS-PER-PRIORITY-COUNTS;
    }
    leaf source-address {
      xr:xr-xml-map "isis_oper_types:SourceAddress";
      type Isis-ipv6-address;
      description "Source Address";
    }
    leaf is-participant {
      xr:xr-xml-map "isis_oper_types:IsParticipant";
      type boolean;
      description "Does the IS participate in the topology?";
    }
    leaf is-overloaded {
      xr:xr-xml-map "isis_oper_types:IsOverloaded";
      type boolean;
      description "Is the IS overloaded?";
    }
    leaf is-attached {
      xr:xr-xml-map "isis_oper_types:IsAttached";
      type boolean;
      description "Is the IS attached?";
    }
  }

  grouping ISIS-SH-TOPO-SUMMARY-NODE-STATS {
    description "Reachability counters";
    leaf reachable-node-count {
      xr:xr-xml-map "isis_oper_types:ReachableNodeCount";
      type uint32;
      description "Number of nodes reachable in SPT";
    }
    leaf unreachable-node-count {
      xr:xr-xml-map "isis_oper_types:UnreachableNodeCount";
      type uint32;
      description "Number of nodes unreachable in SPT";
    }
    leaf unreachable-participant-node-count {
      xr:xr-xml-map "isis_oper_types:UnreachableParticipantNodeCoun"+
        "t";
      type uint32;
      description
        "Number of participating nodes unreachable in SPT";
    }
  }

  grouping ISIS-SH-TOPO-SUMMARY {
    description "Summary Statistics for an IS Topology";

    container router-node-count {
      description "Node Counts for System nodes";
      uses ISIS-SH-TOPO-SUMMARY-NODE-STATS;
    }

    container pseudonode-node-count {
      description "Node Counts for Pseudonode nodes";
      uses ISIS-SH-TOPO-SUMMARY-NODE-STATS;
    }
  }

  grouping ISIS-SH-TOPO-NEIGHBOR {
    description "SPT Neighbor";
    leaf neighbor-id {
      xr:xr-xml-map "isis_oper_types:NeighborID";
      type xr:Osi-system-id;
      description "Neighbor ID";
    }
    leaf intermediate-pseudonode {
      xr:xr-xml-map "isis_oper_types:IntermediatePseudonode";
      type xr:Isis-node-id;
      description "Pseudonode between system and its neighbor";
    }
  }

  grouping ISIS-SH-IPV4-FRR-BACKUP {
    description "FRR backup path";
    leaf neighbor-id {
      xr:xr-xml-map "isis_oper_types:NeighborID";
      type xr:Osi-system-id;
      description "Next hop neighbor ID";
    }
    leaf egress-interface {
      xr:xr-xml-map "isis_oper_types:EgressInterface";
      type Isis-sh-interface-name;
      description "Interface to send the packet out of";
    }
    leaf neighbor-address {
      xr:xr-xml-map "isis_oper_types:NeighborAddress";
      type Isis-ipv4-address;
      description "Next hop neighbor's forwarding address";
    }
    leaf neighbor-snpa {
      xr:xr-xml-map "isis_oper_types:NeighborSNPA";
      type xr:Isis-snpa;
      description "Next hop neighbor's SNPA";
    }
    leaf remote-lfa-system-id {
      xr:xr-xml-map "isis_oper_types:RemoteLFASystemID";
      type xr:Osi-system-id;
      description "Remote LFA PQ Node's ID";
    }
    leaf remote-lfa-router-id {
      xr:xr-xml-map "isis_oper_types:RemoteLFARouterID";
      type Isis-ipv4-address;
      description "Remote LFA Router ID";
    }
    leaf remote-lfa-system-pid {
      xr:xr-xml-map "isis_oper_types:RemoteLFASystemPID";
      type xr:Osi-system-id;
      description "Remote LFA PQ Node's ID";
    }
    leaf remote-lfa-router-pid {
      xr:xr-xml-map "isis_oper_types:RemoteLFARouterPID";
      type Isis-ipv4-address;
      description "Remote LFA Router ID";
    }
    leaf total-backup-distance {
      xr:xr-xml-map "isis_oper_types:TotalBackupDistance";
      type Isis-metric;
      description "Distance to the network via this backup path";
    }
    leaf segment-routing-sid-value {
      xr:xr-xml-map "isis_oper_types:SegmentRoutingSidValue";
      type Isis-nodal-sid-value;
      description
        "Segment routing sid value received from first
        hop";
    }
    leaf num-sid {
      xr:xr-xml-map "isis_oper_types:NumSid";
      type uint32;
      description "Number of SIDs in TI-LFA/rLFA";
    }
    leaf is-downstream {
      xr:xr-xml-map "isis_oper_types:IsDownstream";
      type boolean;
      description "Is the backup path via downstream node?";
    }
    leaf is-lc-disjoint {
      xr:xr-xml-map "isis_oper_types:IsLCDisjoint";
      type boolean;
      description
        "Is the backup path line card disjoint with
        primary?";
    }
    leaf is-node-protecting {
      xr:xr-xml-map "isis_oper_types:IsNodeProtecting";
      type boolean;
      description "Is the backup path node protecting?";
    }
    leaf is-primary-path {
      xr:xr-xml-map "isis_oper_types:IsPrimaryPath";
      type boolean;
      description "Is the backup path an ECMP to the network?";
    }
    leaf is-srlg-disjoint {
      xr:xr-xml-map "isis_oper_types:IsSRLGDisjoint";
      type boolean;
      description "Is the backup path SRLG disjoint with primary?";
    }
    leaf is-remote-lfa {
      xr:xr-xml-map "isis_oper_types:IsRemoteLFA";
      type boolean;
      description "Is the backup path via a Remote LFA?";
    }
    leaf is-epcfrr-lfa {
      xr:xr-xml-map "isis_oper_types:IsEpcfrrLFA";
      type boolean;
      description "Is the backup path via a TI-LFA?";
    }
    leaf weight {
      xr:xr-xml-map "isis_oper_types:Weight";
      type Isis-metric;
      description "Weight configured on the interface";
    }
    leaf-list segment-routing-sid-value-entry {
      xr:xr-xml-map "isis_oper_types:SegmentRoutingSidValues";
      type Isis-nodal-sid-value;
      max-elements "3";
      description "Segment routing sid values for TI-LFA/rLFA";
    }
  }

  grouping ISIS-SH-IPV4-PATH {
    description "IPv4 path to a destination";

    container frr-backup {
      description "FRR backup for this path";
      uses ISIS-SH-IPV4-FRR-BACKUP;
    }
    leaf neighbor-id {
      xr:xr-xml-map "isis_oper_types:NeighborID";
      type xr:Osi-system-id;
      description "Next hop neighbor ID";
    }
    leaf egress-interface {
      xr:xr-xml-map "isis_oper_types:EgressInterface";
      type Isis-sh-interface-name;
      description "Interface to send the packet out of";
    }
    leaf neighbor-address {
      xr:xr-xml-map "isis_oper_types:NeighborAddress";
      type Isis-ipv4-address;
      description "Next hop neighbor's forwarding address";
    }
    leaf neighbor-snpa {
      xr:xr-xml-map "isis_oper_types:NeighborSNPA";
      type xr:Isis-snpa;
      description "Next hop neighbor's SNPA";
    }
    leaf tag {
      xr:xr-xml-map "isis_oper_types:Tag";
      type Isis-prefix-tag;
      description "Tag associated with the path";
    }
    leaf segment-routing-sid-value {
      xr:xr-xml-map "isis_oper_types:SegmentRoutingSidValue";
      type Isis-nodal-sid-value;
      description
        "Segment routing sid value received from first
        hop";
    }
    leaf weight {
      xr:xr-xml-map "isis_oper_types:Weight";
      type Isis-metric;
      description "Weight configured on the interface";
    }
  }

  grouping ISIS-SH-IPV4-TOPO-REACHABLE-DETAILS {
    description "Status of a reachable IPv4 IS";
    leaf root-distance {
      xr:xr-xml-map "isis_oper_types:RootDistance";
      type Isis-metric;
      description "Distance to the IS";
    }
    leaf multicast-root-distance {
      xr:xr-xml-map "isis_oper_types:MulticastRootDistance";
      type Isis-metric;
      description "Distance to the IS";
    }

    list paths {
      description "First hops towards the IS";
      uses ISIS-SH-IPV4-PATH;
    }

    list multicast-path {
      description "Multicast intact first hops towards the IS";
      uses ISIS-SH-IPV4-PATH;
    }

    list parent {
      description "Parents of the IS within the SPT";
      uses ISIS-SH-TOPO-NEIGHBOR;
    }

    list children {
      description "Children of the IS within the SPT";
      uses ISIS-SH-TOPO-NEIGHBOR;
    }
  }

  grouping ISIS-SH-IPV4-TOPO-REACHABLE-STATUS {
    description "Reachability status of an IPv4 IS";

    container reachable-details {
      when "../reachable-status = 'isis-reachable'" {
        description "../ReachableStatus = 'ISIS_REACHABLE'";
      }
      description "Status of the IS within the SPT";
      uses ISIS-SH-IPV4-TOPO-REACHABLE-DETAILS;
    }
    leaf reachable-status {
      xr:xr-xml-map "isis_oper_types:ReachableStatus";
      type Isis-reachable;
      description "ReachableStatus";
    }
  }

  grouping ISIS-SH-IPV4-TOPO-ENTRY {
    description "IPv4 IS Link Topology Entry";

    container reachability-status {
      description
        "Is the IS reachable, and, if so, its status
        within the SPT";
      uses ISIS-SH-IPV4-TOPO-REACHABLE-STATUS;
    }

    container advertised-prefix-item-counts {
      description
        "Per-priority counts of prefix items advertised
        by the IS";
      uses ISIS-PER-PRIORITY-COUNTS;
    }
    leaf source-address {
      xr:xr-xml-map "isis_oper_types:SourceAddress";
      type Isis-ipv4-address;
      description "Source Address";
    }
    leaf is-participant {
      xr:xr-xml-map "isis_oper_types:IsParticipant";
      type boolean;
      description "Does the IS participate in the topology?";
    }
    leaf is-overloaded {
      xr:xr-xml-map "isis_oper_types:IsOverloaded";
      type boolean;
      description "Is the IS overloaded?";
    }
    leaf is-attached {
      xr:xr-xml-map "isis_oper_types:IsAttached";
      type boolean;
      description "Is the IS attached?";
    }
  }

  grouping ISIS-SH-TE-TUNNEL {
    description "MPLS TE tunnel";
    leaf te-system-id {
      xr:xr-xml-map "isis_oper_types:TESystemID";
      type xr:Osi-system-id;
      description "Destination system ID";
    }
    leaf te-interface {
      xr:xr-xml-map "isis_oper_types:TEInterface";
      type xr:Interface-name;
      description "Tunnel interface";
    }
    leaf te-bandwidth {
      xr:xr-xml-map "isis_oper_types:TEBandwidth";
      type uint32;
      description "Tunnel bandwidth";
    }
    leaf teigp-metric {
      xr:xr-xml-map "isis_oper_types:TEIGPMetric";
      type int32;
      description "Tunnel metric";
    }
    leaf te-next-hop-ip-address {
      xr:xr-xml-map "isis_oper_types:TENextHopIPAddress";
      type inet:ipv4-address;
      description "Tunnel next-hop IP address";
    }
    leaf te-mode-type {
      xr:xr-xml-map "isis_oper_types:TEModeType";
      type Isis-metric-mode;
      description "Tunnel metric mode";
    }
    leaf teipv4fa-enabled {
      xr:xr-xml-map "isis_oper_types:TEIPv4FAEnabled";
      type boolean;
      description
        "Indicates whether MPLS TE IPv4 forwarding
        adjacency is enabled";
    }
    leaf teipv6fa-enabled {
      xr:xr-xml-map "isis_oper_types:TEIPv6FAEnabled";
      type boolean;
      description
        "Indicates whether MPLS TE IPv6 forwarding
        adjacency is enabled";
    }
    leaf teipv4aa-enabled {
      xr:xr-xml-map "isis_oper_types:TEIPv4AAEnabled";
      type boolean;
      description
        "Indicates whether MPLS TE IPv4 autoroute
        announce is enabled";
    }
    leaf teipv6aa-enabled {
      xr:xr-xml-map "isis_oper_types:TEIPv6AAEnabled";
      type boolean;
      description
        "Indicates whether MPLS TE IPv6 autoroute
        announce is enabled";
    }
    leaf te-checkpoint-object-id {
      xr:xr-xml-map "isis_oper_types:TECheckpointObjectID";
      type uint32;
      description "Tunnel checkpoint object ID";
    }
  }

  grouping ISIS-SH-SPF-LOG-ROUTE-UPDATE-PREFIX-COUNTS {
    description "Prefix item counts for the route update phase";

    container unreachable {
      description "Number of unreachable prefixes in the database";
      uses ISIS-PER-PRIORITY-COUNTS;
    }

    container reachable {
      description "Number of reachable prefixes in the database";
      uses ISIS-PER-PRIORITY-COUNTS;
    }

    container added {
      description "Number of prefixes added during calculation";
      uses ISIS-PER-PRIORITY-COUNTS;
    }

    container deleted {
      description "Number of prefixes deleted during calculation";
      uses ISIS-PER-PRIORITY-COUNTS;
    }

    container modified {
      description
        "Number of prefixes modified, i.e. a first hop
        and/or metric change";
      uses ISIS-PER-PRIORITY-COUNTS;
    }

    container touched {
      description
        "Number of prefixes considered whilst updating
        the routing table";
      uses ISIS-PER-PRIORITY-COUNTS;
    }
  }

  grouping ISIS-SH-SPF-LOG-ROUTE-UPDATE-NODE-COUNTS {
    description "Node counts for the route update phase";

    container per-priority-touched {
      description
        "Per-priority count of nodes considered during
        route update";
      uses ISIS-PER-PRIORITY-COUNTS;
    }
    leaf total-touched {
      xr:xr-xml-map "isis_oper_types:TotalTouched";
      type uint32;
      description
        "Total number of nodes considered during route
        update";
    }
  }

  grouping ISIS-PER-PRIORITY-TIMINGS {
    description "Per-priority timings";

    container critical {
      description "Critical priority";
      uses ISIS-TIMINGS-TYPE;
    }

    container high {
      description "High priority";
      uses ISIS-TIMINGS-TYPE;
    }

    container medium {
      description "Medium priority";
      uses ISIS-TIMINGS-TYPE;
    }

    container low {
      description "Low priority";
      uses ISIS-TIMINGS-TYPE;
    }
  }

  grouping ISIS-SH-SPF-LOG-ROUTE-UPDATE-TIMINGS-BREAKDOWN {
    description
      "Breakdown of the time taken to perform the route
      update";

    container local-rib-update {
      description "Time to update IS-IS's local RIB";
      uses ISIS-PER-PRIORITY-TIMINGS;
    }

    container global-rib-build {
      description
        "Time to build the update to send to the global
        RIB";
      uses ISIS-PER-PRIORITY-TIMINGS;
    }

    container global-rib-send {
      description "Time to send the update to the global RIB";
      uses ISIS-PER-PRIORITY-TIMINGS;
    }
  }

  grouping ISIS-SH-SPF-LOG-ROUTE-UPDATE {
    description
      "Statistics for the route update phase of the
      calculation";

    container duration {
      description "Duration of the routing table update";
      uses ISIS-TIMINGS-TYPE;
    }

    container duration-breakdown {
      description
        "Breakdown of the time taken by the routing table
        update";
      uses ISIS-SH-SPF-LOG-ROUTE-UPDATE-TIMINGS-BREAKDOWN;
    }

    container node-counts {
      description "Node counts";
      uses ISIS-SH-SPF-LOG-ROUTE-UPDATE-NODE-COUNTS;
    }

    container item-counts {
      description "Prefix item counts";
      uses ISIS-SH-SPF-LOG-ROUTE-UPDATE-PREFIX-COUNTS;
    }

    container route-counts {
      description "Distinct prefix counts";
      uses ISIS-SH-SPF-LOG-ROUTE-UPDATE-PREFIX-COUNTS;
    }

    container rib-batch-counts {
      description "Number of RIB batches sent";
      uses ISIS-PER-PRIORITY-COUNTS;
    }
  }

  grouping ISIS-SH-SPF-LOG-SPT-CALC-NODE-COUNTS {
    description "Node counts for the SPT calculation phase";
    leaf unreachable {
      xr:xr-xml-map "isis_oper_types:Unreachable";
      type uint32;
      description "Number of unreachable nodes in the database";
    }
    leaf reachable {
      xr:xr-xml-map "isis_oper_types:Reachable";
      type uint32;
      description "Number of reachable nodes in the database";
    }
    leaf added {
      xr:xr-xml-map "isis_oper_types:Added";
      type uint32;
      description "Number of nodes added to the SPT";
    }
    leaf deleted {
      xr:xr-xml-map "isis_oper_types:Deleted";
      type uint32;
      description "Number of nodes deleted from the SPT";
    }
    leaf modified {
      xr:xr-xml-map "isis_oper_types:Modified";
      type uint32;
      description
        "Number of modified nodes (first hop and/or
        metric change)";
    }
    leaf touched {
      xr:xr-xml-map "isis_oper_types:Touched";
      type uint32;
      description
        "Number of nodes touched whilst calculating the
        SPT";
    }
  }

  grouping ISIS-TIMINGS-TYPE {
    description "Duration of an event in real and CPU time";
    leaf real-duration {
      xr:xr-xml-map "isis_oper_types:RealDuration";
      type uint32;
      units "millisecond";
      description "Real time duration in milliseconds";
    }
    leaf cpu-duration {
      xr:xr-xml-map "isis_oper_types:CPUDuration";
      type uint32;
      units "millisecond";
      description "CPU time duration in milliseconds";
    }
  }

  grouping ISIS-SH-SPF-LOG-SPT-CALC {
    description "Statistics for the SPT calculation phase";

    container duration {
      description "Duration of the SPT calculation";
      uses ISIS-TIMINGS-TYPE;
    }

    container node-counts {
      description "Node counts";
      uses ISIS-SH-SPF-LOG-SPT-CALC-NODE-COUNTS;
    }
  }

  grouping ISIS-IPV6-PREFIX-TYPE {
    description "IPv4 address and prefix length";
    leaf prefix {
      xr:xr-xml-map "isis_oper_types:Prefix";
      type Isis-ipv6-address;
      description "prefix";
    }
    leaf prefix-length {
      xr:xr-xml-map "isis_oper_types:PrefixLength";
      type Isis-ip-prefix-length;
      description "prefix length";
    }
  }

  grouping ISIS-IPV4-PREFIX-TYPE {
    description "IPv4 address and prefix length";
    leaf prefix {
      xr:xr-xml-map "isis_oper_types:Prefix";
      type Isis-ipv4-address;
      description "prefix";
    }
    leaf prefix-length {
      xr:xr-xml-map "isis_oper_types:PrefixLength";
      type Isis-ip-prefix-length;
      description "prefix length";
    }
  }

  grouping ISIS-IP-PREFIX-TYPE {
    description "ISIS IP PREFIX TYPE";

    container ipv4 {
      when "../af-name = 'ipv4'" {
        description "../AFName = 'IPv4'";
      }
      description "ipv4";
      uses ISIS-IPV4-PREFIX-TYPE;
    }

    container ipv6 {
      when "../af-name = 'ipv6'" {
        description "../AFName = 'IPv6'";
      }
      description "ipv6";
      uses ISIS-IPV6-PREFIX-TYPE;
    }
    leaf af-name {
      xr:xr-xml-map "isis_oper_types:AFName";
      type Isis-af-id;
      description "AFName";
    }
  }

  grouping ISIS-SH-SPF-LOG-TRIGGERS {
    description "The reasons for running a calculation";

    container trigger-prefix {
      description
        "ID of a changed prefix in the first trigger LSP,
        if any";
      uses ISIS-IP-PREFIX-TYPE;
    }
    leaf unique-trigger-count {
      xr:xr-xml-map "isis_oper_types:UniqueTriggerCount";
      type uint32;
      description "Number of unique triggers on this run";
    }
    leaf first-trigger-lsp-id {
      xr:xr-xml-map "isis_oper_types:FirstTriggerLSP_ID";
      type xr:Isis-lsp-id;
      description
        "ID of the first LSP to trigger the calculation,
        if any";
    }
    leaf trigger-link {
      xr:xr-xml-map "isis_oper_types:TriggerLink";
      type xr:Isis-node-id;
      description
        "ID of a changed link in the first trigger LSP,
        if any";
    }
    leaf trigger-next-hop-id {
      xr:xr-xml-map "isis_oper_types:TriggerNextHopID";
      type xr:Osi-system-id;
      description "ID of a changed next hop, if any";
    }
    leaf-list trigger {
      xr:xr-xml-map "isis_oper_types:Triggers";
      type Isis-spf-trigger;
      description "Triggers applying to this log entry";
    }
  }

  grouping ISIS-SH-SPF-LOG-ENT {
    description "IS-IS route calculation log entry";

    container generic-data {
      description "Generic entry data.";
      uses ISIS-SH-GENERIC-LOG-ENT;
    }

    container triggers {
      description "Trigger information";
      uses ISIS-SH-SPF-LOG-TRIGGERS;
    }

    container spt-calculation-statistics {
      description "Statistics for the SPT calculation phase";
      uses ISIS-SH-SPF-LOG-SPT-CALC;
    }

    container route-update-statistics {
      description "Statistics for the route update phase";
      uses ISIS-SH-SPF-LOG-ROUTE-UPDATE;
    }
    leaf class {
      xr:xr-xml-map "isis_oper_types:Class";
      type Isis-spf-class;
      description "Type of calculation.";
    }
    leaf wait-enforced {
      xr:xr-xml-map "isis_oper_types:WaitEnforced";
      type uint32;
      units "millisecond";
      description
        "Time between the first trigger and the start of
        the route calculation, in milliseconds.";
    }
    leaf next-wait-interval {
      xr:xr-xml-map "isis_oper_types:NextWaitInterval";
      type uint32;
      units "millisecond";
      description
        "Minimum time from end of this route calculation
        until the start of the next, in milliseconds";
    }
    leaf updated-lsp-count {
      xr:xr-xml-map "isis_oper_types:UpdatedLSPCount";
      type uint32;
      description
        "Number of LSPs which arrived during the route
        calculation";
    }
  }

  grouping ISIS-SH-SPF-LOG-STRUC {
    description "Log of IS-IS route calculations";

    list log-entry {
      description "SPF Log entries";
      uses ISIS-SH-SPF-LOG-ENT;
    }
  }

  grouping ISIS-SH-TE-LOG-ENT {
    description "MPLS TE log entry";

    container generic-data {
      description "Generic entry data";
      uses ISIS-SH-GENERIC-LOG-ENT;
    }
    leaf neighbor-ip-address {
      xr:xr-xml-map "isis_oper_types:NeighborIPAddress";
      type inet:ipv4-address;
      description "Neighbor ip address";
    }
    leaf status {
      xr:xr-xml-map "isis_oper_types:Status";
      type boolean;
      description "Up (TRUE) or down";
    }
    leaf log-interface {
      xr:xr-xml-map "isis_oper_types:LogInterface";
      type xr:Interface-name;
      description "Interface";
    }
    leaf te-log-neighbor-system-id {
      xr:xr-xml-map "isis_oper_types:TELogNeighborSystemID";
      type xr:Osi-system-id;
      description "Neighbor system ID";
    }
  }

  grouping ISIS-SH-TE-LOG-STRUC {
    description "MPLS TE log";

    list log-entry {
      description "Log entries";
      uses ISIS-SH-TE-LOG-ENT;
    }
  }

  grouping ISIS-SH-TE-PCE-ADV {
    description "TE PCE advertisements for an IS-IS level";
    leaf pce-adv-data-present {
      xr:xr-xml-map "isis_oper_types:PCEAdvDataPresent";
      type boolean;
      description
        "Indicates whether any PCE advertisements are
        present";
    }
    leaf pce-flooding-scope {
      xr:xr-xml-map "isis_oper_types:PCEFloodingScope";
      type Isis-sh-te-pce-flooding-scope;
      description "Flooding scope for PCE advertisement";
    }
    leaf pce-address-ipv4 {
      xr:xr-xml-map "isis_oper_types:PCEAddressIPv4";
      type inet:ipv4-address;
      description "IPv4 PCE address";
    }
    leaf pce-path-scope-bits {
      xr:xr-xml-map "isis_oper_types:PCEPathScopeBits";
      type uint8;
      description "PCE path scope bits";
    }
    leaf pce-path-scope-prefs {
      xr:xr-xml-map "isis_oper_types:PCEPathScopePrefs";
      type uint16;
      description "PCE path scope preferences";
    }
  }

  grouping ISIS-SH-TE-ADV-SUB-TLV {
    description "MPLS TE advertisement sub TLV";
    leaf te-sub-tlv-type {
      xr:xr-xml-map "isis_oper_types:TESubTlvType";
      type uint16;
      description "Type of sub TLV";
    }
    leaf te-sub-tlv-length {
      xr:xr-xml-map "isis_oper_types:TESubTlvLength";
      type uint16;
      description "Length of sub TLV";
    }
    leaf te-sub-tlv-value {
      xr:xr-xml-map "isis_oper_types:TESubTlvValue";
      type yang:hex-string;
      description "Value of sub TLV";
    }
  }

  grouping ISIS-SH-TE-ADV-ENTRY {
    description "MPLS TE advertisement";
    leaf te-neighbor-system-id {
      xr:xr-xml-map "isis_oper_types:TENeighborSystemID";
      type xr:Osi-system-id;
      description "Neighbor system ID";
    }
    leaf link-type {
      xr:xr-xml-map "isis_oper_types:LinkType";
      type Isis-sh-te-link;
      description "Link type";
    }
    leaf local-ip-address {
      xr:xr-xml-map "isis_oper_types:LocalIPAddress";
      type inet:ipv4-address;
      description "Local IP address";
    }
    leaf te-neighbor-ip-address {
      xr:xr-xml-map "isis_oper_types:TENeighborIPAddress";
      type inet:ipv4-address;
      description "Neighbor IP address";
    }
    leaf te-metric {
      xr:xr-xml-map "isis_oper_types:TEMetric";
      type uint32;
      description "TE metric";
    }
    leaf te-physical-link-bandwidth {
      xr:xr-xml-map "isis_oper_types:TEPhysicalLinkBandwidth";
      type uint32;
      description "Physical link bandwidth";
    }
    leaf te-reserved-link-bandwidth {
      xr:xr-xml-map "isis_oper_types:TEReservedLinkBandwidth";
      type uint32;
      description "Reservable link bandwidth in global pool";
    }
    leaf te-subpool-reserved-link-bandwidth {
      xr:xr-xml-map "isis_oper_types:TESubpoolReservedLinkBandwidth";
      type uint32;
      description "Reservable link bandwidth in subpool";
    }
    leaf te-affinity {
      xr:xr-xml-map "isis_oper_types:TEAffinity";
      type uint32;
      description "Affinity bits";
    }
    leaf te-ext-admin-num {
      xr:xr-xml-map "isis_oper_types:TEExtAdminNum";
      type uint32;
      description "TE Ext Admin Number";
    }
    leaf te-sub-tlv-data-present {
      xr:xr-xml-map "isis_oper_types:TESubTlvDataPresent";
      type boolean;
      description "Indicates whether any TE sub TLVs are present";
    }
    leaf-list te-transmitted-bandwidth {
      xr:xr-xml-map "isis_oper_types:TETransmittedBandwidth";
      type uint32;
      max-elements "8";
      description "Bandwidth in use in global pool";
    }
    leaf-list te-subpool-transmitted-bandwidth {
      xr:xr-xml-map "isis_oper_types:TESubpoolTransmittedBandwidth";
      type uint32;
      max-elements "8";
      description "Bandwidth in use in subpool";
    }
    leaf-list te-ext-admin-sub {
      xr:xr-xml-map "isis_oper_types:TEExtAdminSub";
      type uint32;
      max-elements "8";
      description "TE Extended Admin Group";
    }

    list te-sub-tlv {
      description "List of TE sub TLVs";
      uses ISIS-SH-TE-ADV-SUB-TLV;
    }
  }

  grouping ISIS-SH-TE-ADV {
    description "TE advertisements for an IS-IS level";

    container tepceadv {
      description "TE PCE advertisements";
      uses ISIS-SH-TE-PCE-ADV;
    }
    leaf te-adv-data-present {
      xr:xr-xml-map "isis_oper_types:TEAdvDataPresent";
      type boolean;
      description
        "Indicates whether any TE advertisements are
        present";
    }
    leaf te-system-id {
      xr:xr-xml-map "isis_oper_types:TESystemID";
      type xr:Osi-system-id;
      description "Local system ID";
    }
    leaf te-local-router-id {
      xr:xr-xml-map "isis_oper_types:TELocalRouterID";
      type inet:ipv4-address;
      description "Local TE router ID";
    }

    list te-adv {
      description "List of TE advertisement entries";
      uses ISIS-SH-TE-ADV-ENTRY;
    }
  }

  grouping ISIS-PER-PRIORITY-COUNTS {
    description "Per-priority counts";
    leaf critical {
      xr:xr-xml-map "isis_oper_types:Critical";
      type uint32;
      description "Critical priority";
    }
    leaf high {
      xr:xr-xml-map "isis_oper_types:High";
      type uint32;
      description "High priority";
    }
    leaf medium {
      xr:xr-xml-map "isis_oper_types:Medium";
      type uint32;
      description "Medium priority";
    }
    leaf low {
      xr:xr-xml-map "isis_oper_types:Low";
      type uint32;
      description "Low priority";
    }
  }

  grouping ISIS-SH-FRR-LEVEL-SUMMARY {
    description "FRR backup statistics for one level";

    container all-paths-protected {
      description
        "Number of prefixes with all paths having FRR
        backup";
      uses ISIS-PER-PRIORITY-COUNTS;
    }

    container some-paths-protected {
      description
        "Number of prefixes with some paths having FRR
        backup";
      uses ISIS-PER-PRIORITY-COUNTS;
    }

    container unprotected {
      description "Number of reachable prefixes without FRR backup";
      uses ISIS-PER-PRIORITY-COUNTS;
    }
  }

  grouping ISIS-SH-FRR-SUMMARY {
    description "FRR summary for an ISIS topology";

    container level1-prefixes {
      description "FRR summary for prefixes reachable in L1";
      uses ISIS-SH-FRR-LEVEL-SUMMARY;
    }

    container level2-prefixes {
      description "FRR summary for prefixes reachable in L2";
      uses ISIS-SH-FRR-LEVEL-SUMMARY;
    }

    container unreachable-prefixes {
      description "Unreachable prefixes";
      uses ISIS-PER-PRIORITY-COUNTS;
    }
  }

  grouping ISIS-SH-LSP-DB-LOG-ENT {
    description "LSP Database Log Entry";

    container generic-data {
      description "Generic entry data";
      uses ISIS-SH-GENERIC-LOG-ENT;
    }

    container new-lsp-entry {
      description
        "Entry being inserted or the updated version of
        an old entry.";
      uses ISIS-SH-LSP-HEADER;
    }

    container old-lsp-entry {
      description "Entry being replaced.";
      uses ISIS-SH-LSP-HEADER;
    }
    leaf lspdb-operation {
      xr:xr-xml-map "isis_oper_types:LSPDBOperation";
      type Isis-lsp-db-op;
      description "Operation applying to this entry.";
    }
  }

  grouping ISIS-SH-LSP-DB-LOG-STRUC {
    description "LSP Database Log";

    list log-entry {
      description "Entries";
      uses ISIS-SH-LSP-DB-LOG-ENT;
    }
  }

  grouping ISIS-SH-LSP-LOG-ENT {
    description "LSP-log entry";

    container generic-data {
      description "Generic entry data";
      uses ISIS-SH-GENERIC-LOG-ENT;
    }
    leaf trigger-count {
      xr:xr-xml-map "isis_oper_types:TriggerCount";
      type uint32;
      description
        "Number of triggers on this run. May not be equal
        to the number of trigger event types if one or
        more trigger events has occurred more than once.";
    }
    leaf delayed-trigger-count {
      xr:xr-xml-map "isis_oper_types:DelayedTriggerCount";
      type uint32;
      description "Number of delayed triggers";
    }
    leaf log-interface {
      xr:xr-xml-map "isis_oper_types:LogInterface";
      type xr:Interface-name;
      description "Appropriate interface, if any";
    }
    leaf pseudo-node-number {
      xr:xr-xml-map "isis_oper_types:PseudoNodeNumber";
      type Isis-pseudo-node-number;
      description "Pseudo-node number";
    }
    leaf-list trigger {
      xr:xr-xml-map "isis_oper_types:Triggers";
      type Isis-lsp-trigger;
      description "Triggers applying to this log entry.";
    }
  }

  grouping ISIS-SH-LSP-LOG-STRUC {
    description "LSP log";

    list log-entry {
      description "Log entries";
      uses ISIS-SH-LSP-LOG-ENT;
    }
  }

  grouping ISIS-SH-LSP-HEADER {
    description "Contents of an IS-IS LSP header";
    leaf lsp-id {
      xr:xr-xml-map "isis_oper_types:LSP_ID";
      type xr:Isis-lsp-id;
      description "The LSP ID";
    }
    leaf local-lsp-flag {
      xr:xr-xml-map "isis_oper_types:LocalLSPFlag";
      type boolean;
      description "TRUE if this is a locally generated LSP";
    }
    leaf lsp-active-flag {
      xr:xr-xml-map "isis_oper_types:LSPActiveFlag";
      type boolean;
      description "TRUE if this LSP has not expired";
    }
    leaf lsp-holdtime {
      xr:xr-xml-map "isis_oper_types:LSPHoldtime";
      type uint16;
      units "second";
      description
        "Time, in seconds, until LSP expiry (if active)
        or deletion (if expired) ";
    }
    leaf lsp-sequence-number {
      xr:xr-xml-map "isis_oper_types:LSPSequenceNumber";
      type uint32;
      description "The LSP sequence number";
    }
    leaf lsp-checksum {
      xr:xr-xml-map "isis_oper_types:LSPChecksum";
      type uint16;
      description "The LSP checksum";
    }
    leaf lsp-parition-repair-supported-flag {
      xr:xr-xml-map "isis_oper_types:LSPParitionRepairSupportedFlag";
      type boolean;
      description "TRUE if partition repair is supported";
    }
    leaf lsp-attached-flag {
      xr:xr-xml-map "isis_oper_types:LSPAttachedFlag";
      type boolean;
      description "TRUE if attached bit is set";
    }
    leaf lsp-overloaded-flag {
      xr:xr-xml-map "isis_oper_types:LSPOverloadedFlag";
      type boolean;
      description "TRUE if the overload bit is set";
    }
    leaf lsp-nonv1a-flag {
      xr:xr-xml-map "isis_oper_types:LSPNonV1AFlag";
      type uint16;
      description "TRUE if the LSP is non-v1a, XXX for testing";
    }
    leaf lsp-level {
      xr:xr-xml-map "isis_oper_types:LSPLevel";
      type Isis-levels;
      description "The type of the IS sourcing the LSP";
    }
    leaf lsp-length {
      xr:xr-xml-map "isis_oper_types:LSPLength";
      type uint16;
      description "The total length of the LSP";
    }
  }

  grouping ISIS-SH-LSP {
    description "An IS-IS LSP";

    container lsp-header-data {
      description "Information from the LSP header";
      uses ISIS-SH-LSP-HEADER;
    }
    leaf lsp-body {
      xr:xr-xml-map "isis_oper_types:LSPBody";
      type yang:hex-string;
      description
        "LSP as received/sent over the wire, starting
        from the LSP ID field";
    }
  }

  grouping ISIS-SH-ADJ-TOPO {
    description "Per-topology per-adjacency data";

    container id {
      description "Topology ID";
      uses ISIS-TOPO-ID-TYPE;
    }
    leaf topology-status {
      xr:xr-xml-map "isis_oper_types:TopologyStatus";
      type Isis-adj-topo-status;
      description "Status of topology in adjacency";
    }
    leaf parallel-p2p-link-suppressed-flag {
      xr:xr-xml-map "isis_oper_types:ParallelP2PLinkSuppressedFlag";
      type boolean;
      description "TRUE if suppressed parallel point-to-point link";
    }
  }

  grouping ISIS-SH-ADJ {
    description "An IS-IS adjacency";
    leaf adjacency-system-id {
      xr:xr-xml-map "isis_oper_types:AdjacencySystemID";
      type xr:Osi-system-id;
      description "Neighbor system ID";
    }
    leaf adjacency-snpa {
      xr:xr-xml-map "isis_oper_types:AdjacencySNPA";
      type xr:Isis-snpa;
      description "Neighbor SNPA";
    }
    leaf adjacency-interface {
      xr:xr-xml-map "isis_oper_types:AdjacencyInterface";
      type xr:Interface-name;
      description "Local interface";
    }
    leaf adjacency-media-type {
      xr:xr-xml-map "isis_oper_types:AdjacencyMediaType";
      type Isis-media-class;
      description "Link media type";
    }
    leaf adjacency-state {
      xr:xr-xml-map "isis_oper_types:AdjacencyState";
      type Isis-adj-state;
      description "Adjacency state";
    }
    leaf adjacency-bfd-state {
      xr:xr-xml-map "isis_oper_types:AdjacencyBFDState";
      type Isis-adj-bfd-state;
      description "Adjacency IPv4 BFD state";
    }
    leaf adjacency-ipv6bfd-state {
      xr:xr-xml-map "isis_oper_types:AdjacencyIPv6BFDState";
      type Isis-adj-bfd-state;
      description "Adjacency IPv6 BFD state";
    }
    leaf adjacency-uptime-valid-flag {
      xr:xr-xml-map "isis_oper_types:AdjacencyUptimeValidFlag";
      type boolean;
      description "TRUE if AdjacencyUptime is set";
    }
    leaf adjacency-uptime {
      xr:xr-xml-map "isis_oper_types:AdjacencyUptime";
      type uint32;
      description "How long the adjacency has been up (s)";
    }
    leaf adjacency-holdtime {
      xr:xr-xml-map "isis_oper_types:AdjacencyHoldtime";
      type uint32;
      description
        "Time (s) until adjacency declared down if no IIH
        received";
    }
    leaf adjacency-checkpoint-object-id {
      xr:xr-xml-map "isis_oper_types:AdjacencyCheckpointObjectID";
      type uint32;
      description "Adjacency checkpoint object ID";
    }
    leaf adjacency-ietf-nsf-capable-flag {
      xr:xr-xml-map "isis_oper_types:AdjacencyIETF_NSFCapableFlag";
      type boolean;
      description "TRUE if neighbor is IETF-NSF capable";
    }
    leaf adjacency-dispriority {
      xr:xr-xml-map "isis_oper_types:AdjacencyDISPriority";
      type Isis-dr-priority;
      description
        "Priority of DIS on this LAN. Valid only if
        aj_media_class is ISIS_MEDIA_CLASS_LAN";
    }
    leaf adjacency-neighbor-priority {
      xr:xr-xml-map "isis_oper_types:AdjacencyNeighborPriority";
      type Isis-dr-priority;
      description
        "Neighbor IS priority. Valid only if
        aj_media_class is ISIS_MEDIA_CLASS_LAN";
    }
    leaf adjacency-local-priority {
      xr:xr-xml-map "isis_oper_types:AdjacencyLocalPriority";
      type Isis-dr-priority;
      description
        "Local IS priority. Valid only if aj_media_class
        is ISIS_MEDIA_CLASS_LAN";
    }
    leaf local-dis-flag {
      xr:xr-xml-map "isis_oper_types:LocalDISFlag";
      type boolean;
      description
        "TRUE if local system is DIS. Valid only if
        AdjacencyMediaType is ISIS_MEDIA_CLASS_LAN";
    }
    leaf neighbor-dis-flag {
      xr:xr-xml-map "isis_oper_types:NeighborDISFlag";
      type boolean;
      description
        "TRUE if neighbor is DIS. Valid only if
        AdjacencyMediaType is ISIS_MEDIA_CLASS_LAN";
    }
    leaf nsr-standby {
      xr:xr-xml-map "isis_oper_types:NSR_STANDBY";
      type uint8;
      description "ISIS NSR STANDBY";
    }
    leaf-list adjacency-area-address {
      xr:xr-xml-map "isis_oper_types:AdjacencyAreaAddresses";
      type xr:Osi-area-address;
      description "Area addresses active over this adjacency";
    }

    list adjacency-topology {
      description "Per-topology data";
      uses ISIS-SH-ADJ-TOPO;
    }

    list adjacency-per-address-family-data {
      description "Per-address-family data";
      uses ISIS-SH-ADJ-AF;
    }
  }

  grouping ISIS-SH-LSP-DB-SUMMARY-ALL-FRAGMENTS-STATS {
    description "All fragment counters";

    container node-counters {
      description "Summary by class of node";
      uses ISIS-SH-LSP-DB-SUMMARY-NODE-CLASS-COUNTERS;
    }
  }

  grouping ISIS-SH-LSP-DB-SUMMARY-TOPO-CLASS-COUNTERS {
    description "Per-topology related info";

    container id {
      description "Topology ID";
      uses ISIS-TOPO-ID-TYPE;
    }

    container overloaded-lsp-count {
      description
        "Number of LSPs with their per-topology overload
        bit set";
      uses ISIS-SH-LSP-DB-SUMMARY-STATUS-CLASS-COUNTERS;
    }

    container attached-lsp-count {
      description
        "Number of LSPs with their per-topology attached
        bit set";
      uses ISIS-SH-LSP-DB-SUMMARY-STATUS-CLASS-COUNTERS;
    }
  }

  grouping ISIS-SH-LSP-DB-SUMMARY-STATUS-CLASS-COUNTERS {
    description "LSP status counters";
    leaf active-lsp-count {
      xr:xr-xml-map "isis_oper_types:ActiveLSPCount";
      type uint32;
      description "Number of active LSPs";
    }
    leaf purged-lsp-count {
      xr:xr-xml-map "isis_oper_types:PurgedLSPCount";
      type uint32;
      description "Number of purged LSPs";
    }
  }

  grouping ISIS-SH-LSP-DB-SUMMARY-NODE-CLASS-COUNTERS {
    description "LSP node type counters";

    container route-lsp-count {
      description "Router LSPs";
      uses ISIS-SH-LSP-DB-SUMMARY-STATUS-CLASS-COUNTERS;
    }

    container pseudo-node-lsp-count {
      description "Pseudonode LSPs";
      uses ISIS-SH-LSP-DB-SUMMARY-STATUS-CLASS-COUNTERS;
    }
  }

  grouping ISIS-SH-LSP-DB-SUMMARY-FRAGMENT-0-STATS {
    description "Fragment-0 counters";

    container node-counters {
      description "Summary by class of node";
      uses ISIS-SH-LSP-DB-SUMMARY-NODE-CLASS-COUNTERS;
    }

    list per-topology-counter {
      description "Per topology counters";
      uses ISIS-SH-LSP-DB-SUMMARY-TOPO-CLASS-COUNTERS;
    }
  }

  grouping ISIS-SH-LSP-DB-SUMMARY {
    description "Summary Statistics for an IS-IS LSP Database";

    container fragment0lsp-stats {
      description "Statistics for fragment 0 LSPs";
      uses ISIS-SH-LSP-DB-SUMMARY-FRAGMENT-0-STATS;
    }

    container all-fragment-lsp-stats {
      description "Statistics for all LSP fragments";
      uses ISIS-SH-LSP-DB-SUMMARY-ALL-FRAGMENTS-STATS;
    }
  }

  grouping ISIS-ADJ-LOG-TOPO-TYPE {
    description "Per-topology per-adjacency log data";

    container id {
      description "Topology ID";
      uses ISIS-TOPO-ID-TYPE;
    }
    leaf change {
      xr:xr-xml-map "isis_oper_types:Change";
      type Isis-adj-topo-change;
      description "Change";
    }
  }

  grouping ISIS-SH-GENERIC-LOG-ENT {
    description "Generic portion of a log entry";

    container timestamp {
      description "Time in UTC relative to Jan 1st, 1970";
      uses ISIS-SH-TIMESTAMP-TYPE;
    }
  }

  grouping ISIS-SH-ADJ-LOG-ENT {
    description "An adjacency log entry";

    container generic-data {
      description "Generic entry data";
      uses ISIS-SH-GENERIC-LOG-ENT;
    }
    leaf adj-log-neighbor-system-id {
      xr:xr-xml-map "isis_oper_types:AdjLogNeighborSystemID";
      type xr:Osi-system-id;
      description "Neighbor system ID";
    }
    leaf interface-name {
      xr:xr-xml-map "isis_oper_types:InterfaceName";
      type string;
      description "Interface name";
    }
    leaf prev-adj-state {
      xr:xr-xml-map "isis_oper_types:PrevAdjState";
      type Isis-adj-state;
      description "Previous adjacency state";
    }
    leaf cur-adj-state {
      xr:xr-xml-map "isis_oper_types:CurAdjState";
      type Isis-adj-state;
      description "Current adjacency state";
    }
    leaf state-reason {
      xr:xr-xml-map "isis_oper_types:StateReason";
      type Isis-adj-state-reason;
      description "Reason adjacency changed state";
    }

    list adjacency-per-topology-change {
      description "Per-topology changes";
      uses ISIS-ADJ-LOG-TOPO-TYPE;
    }
  }

  grouping ISIS-SH-ADJ-LOG-STRUC {
    description "Adjacency log structure";

    list log-entry {
      description "Adjacency Log entries";
      uses ISIS-SH-ADJ-LOG-ENT;
    }
  }

  grouping ISIS-AREA-TOPO-STATS-TYPE {
    description "Per-area, per-topology traffic statistics";
    leaf spf-run-count {
      xr:xr-xml-map "isis_oper_types:SPFRunCount";
      type uint32;
      description "Number of full SPF calculations run";
    }
    leaf ispf-run-count {
      xr:xr-xml-map "isis_oper_types:ISPFRunCount";
      type uint32;
      description "Number of ISPF calculations run";
    }
    leaf nhc-run-count {
      xr:xr-xml-map "isis_oper_types:NHCRunCount";
      type uint32;
      description "Number of Next Hop Calculations run";
    }
    leaf prc-run-count {
      xr:xr-xml-map "isis_oper_types:PRCRunCount";
      type uint32;
      description "Number of PRCs run";
    }
    leaf periodic-run-count {
      xr:xr-xml-map "isis_oper_types:PeriodicRunCount";
      type uint32;
      description "Number of periodic SPF calculations run";
    }
  }

  grouping ISIS-SH-TRAFFIC-AREA-TOPO {
    description "Per-area, per-topology traffic data";

    container id {
      description "Topology ID";
      uses ISIS-TOPO-ID-TYPE;
    }

    container statistics {
      description "Statistics";
      uses ISIS-AREA-TOPO-STATS-TYPE;
    }
  }

  grouping ISIS-AREA-STATS-TYPE {
    description "Per-area traffic statistics";
    leaf system-lsp-build-count {
      xr:xr-xml-map "isis_oper_types:SystemLSPBuildCount";
      type uint32;
      description "Number of times system LSP rebuilt";
    }
    leaf system-lsp-refresh-count {
      xr:xr-xml-map "isis_oper_types:SystemLSPRefreshCount";
      type uint32;
      description "Number of times system LSP refreshed";
    }
  }

  grouping ISIS-SH-TRAFFIC-AREA {
    description "Per-area traffic data";

    container statistics {
      description "Statistics";
      uses ISIS-AREA-STATS-TYPE;
    }
    leaf level {
      xr:xr-xml-map "isis_oper_types:Level";
      type Isis-level;
      description "Level this data applies to";
    }

    list per-topology-data {
      description "Per-topoogy statistics";
      uses ISIS-SH-TRAFFIC-AREA-TOPO;
    }
  }

  grouping ISIS-SH-TIMESTAMP-TYPE {
    description "Timestamp for an event";
    leaf seconds {
      xr:xr-xml-map "isis_oper_types:Seconds";
      type uint32;
      units "second";
      description "Timestamp value (seconds)";
    }
    leaf nano-seconds {
      xr:xr-xml-map "isis_oper_types:NanoSeconds";
      type uint32;
      units "nanosecond";
      description "Timestamp value (nanoseconds)";
    }
  }

  grouping ISIS-TRAFFIC-GLOBAL-TYPE {
    description "IS-IS process traffic statistics";

    container avg-hello-process-time {
      description "Average hello process time";
      uses ISIS-SH-TIMESTAMP-TYPE;
    }

    container avg-csnp-process-time {
      description "Average CSNP process time";
      uses ISIS-SH-TIMESTAMP-TYPE;
    }

    container avg-psnp-process-time {
      description "Average PSNP process time";
      uses ISIS-SH-TIMESTAMP-TYPE;
    }

    container avg-lsp-process-time {
      description "Average LSP process time";
      uses ISIS-SH-TIMESTAMP-TYPE;
    }

    container avg-hello-transmit-time {
      description "Average hello transmit time";
      uses ISIS-SH-TIMESTAMP-TYPE;
    }

    container avg-csnp-transmit-time {
      description "Average CSNP transmit time";
      uses ISIS-SH-TIMESTAMP-TYPE;
    }

    container avg-psnp-transmit-time {
      description "Average PSNP transmit time";
      uses ISIS-SH-TIMESTAMP-TYPE;
    }

    container avg-lsp-transmit-time {
      description "Average LSP transmit time";
      uses ISIS-SH-TIMESTAMP-TYPE;
    }
    leaf fast-psnp-lookup-count {
      xr:xr-xml-map "isis_oper_types:FastPSNPLookupCount";
      type uint32;
      description "Fast-PSNP cache lookups";
    }
    leaf fast-psnp-lookup-hit-count {
      xr:xr-xml-map "isis_oper_types:FastPSNPLookupHitCount";
      type uint32;
      description "Fast-PSNP cache hits";
    }
    leaf fast-csnp-lookup-count {
      xr:xr-xml-map "isis_oper_types:FastCSNPLookupCount";
      type uint32;
      description "Fast-CSNP cache lookups";
    }
    leaf fast-csnp-lookup-hit-count {
      xr:xr-xml-map "isis_oper_types:FastCSNPLookupHitCount";
      type uint32;
      description "Fast-CSNP cache hits";
    }
    leaf fast-csnp-cache-update-count {
      xr:xr-xml-map "isis_oper_types:FastCSNPCacheUpdateCount";
      type uint32;
      description "Fast-CSNP cache updates";
    }
    leaf zero-holdtime-lsp-count {
      xr:xr-xml-map "isis_oper_types:ZeroHoldtimeLSPCount";
      type uint32;
      description "LSPs received with holdtime 0";
    }
    leaf invalid-checksum-lsp-count {
      xr:xr-xml-map "isis_oper_types:InvalidChecksumLSPCount";
      type uint32;
      description "LSPs received with invalid checksum";
    }
    leaf iih-dropped-count {
      xr:xr-xml-map "isis_oper_types:IIHDroppedCount";
      type uint32;
      description "IIHs dropped - Not Used";
    }
    leaf lsp-dropped-count {
      xr:xr-xml-map "isis_oper_types:LSPDroppedCount";
      type uint32;
      description "LSPs dropped";
    }
    leaf snp-dropped-count {
      xr:xr-xml-map "isis_oper_types:SNPDroppedCount";
      type uint32;
      description "SNPs dropped";
    }
    leaf maximum-iih-queue-length {
      xr:xr-xml-map "isis_oper_types:MaximumIIHQueueLength";
      type uint32;
      description "Maximum IIH queue length - Not Used";
    }
    leaf maximum-pdu-queue-length {
      xr:xr-xml-map "isis_oper_types:MaximumPDUQueueLength";
      type uint32;
      description "Maximum update PDU queue length";
    }
    leaf avg-hello-recv-rate {
      xr:xr-xml-map "isis_oper_types:AvgHelloRecvRate";
      type uint32;
      units "packet/s";
      description
        "Average hello receive rate in packets per second";
    }
    leaf avg-csnp-recv-rate {
      xr:xr-xml-map "isis_oper_types:AvgCSNPRecvRate";
      type uint32;
      units "packet/s";
      description "Average csnp receive rate in packets per second";
    }
    leaf avg-psnp-recv-rate {
      xr:xr-xml-map "isis_oper_types:AvgPSNPRecvRate";
      type uint32;
      units "packet/s";
      description "Average psnp receive rate in packets per second";
    }
    leaf avg-lsp-recv-rate {
      xr:xr-xml-map "isis_oper_types:AvgLSPRecvRate";
      type uint32;
      units "packet/s";
      description "Average LSP receive rate in packets per second";
    }
    leaf avg-hello-send-rate {
      xr:xr-xml-map "isis_oper_types:AvgHelloSendRate";
      type uint32;
      units "packet/s";
      description "Average hello send rate in packets per second";
    }
    leaf avg-csnp-send-rate {
      xr:xr-xml-map "isis_oper_types:AvgCSNPSendRate";
      type uint32;
      units "packet/s";
      description "Average csnp send rate in packets per second";
    }
    leaf avg-psnp-send-rate {
      xr:xr-xml-map "isis_oper_types:AvgPSNPSendRate";
      type uint32;
      units "packet/s";
      description "Average psnp send rate in packets per second";
    }
    leaf avg-lsp-send-rate {
      xr:xr-xml-map "isis_oper_types:AvgLSPSendRate";
      type uint32;
      units "packet/s";
      description "Average LSP send rate in packets per second";
    }
  }

  grouping ISIS-SH-TRAFFIC-GLOBAL {
    description "IS-IS process traffic data";

    container statistics {
      description "Statistics";
      uses ISIS-TRAFFIC-GLOBAL-TYPE;
    }

    list per-area-data {
      description "Per-area data";
      uses ISIS-SH-TRAFFIC-AREA;
    }
  }

  grouping ISIS-SH-HOST {
    description "Bag representing a host (IS)";
    leaf local-is-flag {
      xr:xr-xml-map "isis_oper_types:LocalISFlag";
      type boolean;
      description "TRUE if this is the local IS";
    }
    leaf host-levels {
      xr:xr-xml-map "isis_oper_types:HostLevels";
      type Isis-levels;
      description "Host levels";
    }
    leaf host-name {
      xr:xr-xml-map "isis_oper_types:HostName";
      type string;
      description "Host name";
    }
  }

  grouping ISIS-IPV6-ADJ-SID-BACKUP-INFO {
    description "IPv4 Adjacency SID backup information";
    leaf backup-label-stack-size {
      xr:xr-xml-map "isis_oper_types:BackupLabelStackSize";
      type uint8;
      description "Number of labels in the backup path label stack";
    }
    leaf backup-node-address {
      xr:xr-xml-map "isis_oper_types:BackupNodeAddress";
      type Isis-ipv6-address;
      description
        "Neighbor address used as adjacency backup target";
    }
    leaf backup-nexthop {
      xr:xr-xml-map "isis_oper_types:BackupNexthop";
      type Isis-ipv6-address;
      description "Backup path nexthop address";
    }
    leaf backup-interface {
      xr:xr-xml-map "isis_oper_types:BackupInterface";
      type xr:Interface-name;
      description "Backup path interface";
    }
    leaf-list backup-label-stack {
      xr:xr-xml-map "isis_oper_types:BackupLabelStack";
      type uint32;
      description "Backup path label stack";
    }
  }

  grouping ISIS-IPV6-ADJ-SID {
    description "IPv6 Adjacency SID";

    container adjacency-sid-backup {
      description "Adjacency SID Backup Info";
      uses ISIS-IPV6-ADJ-SID-BACKUP-INFO;
    }
    leaf adjacency-sid-value {
      xr:xr-xml-map "isis_oper_types:AdjacencySIDValue";
      type Isis-nodal-sid-value;
      description "Adjacency SID value";
    }
  }

  grouping ISIS-SH-ADJ-IPV6 {
    description "IPv6 Specific Per-Adjacency Data";

    container adjacency-sid {
      description "Adjacency SID";
      uses ISIS-IPV6-ADJ-SID;
    }

    container non-frr-adjacency-sid {
      description "Adjacency SID not eligible for FRR protection";
      uses ISIS-IPV6-ADJ-SID;
    }
    leaf next-hop {
      xr:xr-xml-map "isis_oper_types:NextHop";
      type Isis-ipv6-address;
      description "Adjacency next hop";
    }
    leaf-list interface-address {
      xr:xr-xml-map "isis_oper_types:InterfaceAddresses";
      type Isis-ipv6-address;
      description "Adjacency interface addresses";
    }
  }

  grouping ISIS-IPV4-ADJ-SID-BACKUP-INFO {
    description "IPv4 Adjacency SID backup information";
    leaf backup-label-stack-size {
      xr:xr-xml-map "isis_oper_types:BackupLabelStackSize";
      type uint8;
      description "Number of labels in the backup path label stack";
    }
    leaf backup-node-address {
      xr:xr-xml-map "isis_oper_types:BackupNodeAddress";
      type Isis-ipv4-address;
      description
        "Neighbor address used as adjacency backup target";
    }
    leaf backup-nexthop {
      xr:xr-xml-map "isis_oper_types:BackupNexthop";
      type Isis-ipv4-address;
      description "Backup path nexthop address";
    }
    leaf backup-interface {
      xr:xr-xml-map "isis_oper_types:BackupInterface";
      type xr:Interface-name;
      description "Backup path interface";
    }
    leaf-list backup-label-stack {
      xr:xr-xml-map "isis_oper_types:BackupLabelStack";
      type uint32;
      description "Backup path label stack";
    }
  }

  grouping ISIS-IPV4-ADJ-SID {
    description "IPv4 Adjacency SID";

    container adjacency-sid-backup {
      description "Adjacency SID Backup Info";
      uses ISIS-IPV4-ADJ-SID-BACKUP-INFO;
    }
    leaf adjacency-sid-value {
      xr:xr-xml-map "isis_oper_types:AdjacencySIDValue";
      type Isis-nodal-sid-value;
      description "Adjacency SID value";
    }
  }

  grouping ISIS-SH-ADJ-IPV4 {
    description "IPv4 Specific Per-Adjacency Data";

    container adjacency-sid {
      description "Adjacency SID";
      uses ISIS-IPV4-ADJ-SID;
    }

    container non-frr-adjacency-sid {
      description "Adjacency SID not eligible for FRR protection";
      uses ISIS-IPV4-ADJ-SID;
    }
    leaf next-hop {
      xr:xr-xml-map "isis_oper_types:NextHop";
      type Isis-ipv4-address;
      description "Adjacency next hop";
    }
    leaf-list interface-address {
      xr:xr-xml-map "isis_oper_types:InterfaceAddresses";
      type Isis-ipv4-address;
      description "Adjacency interface addresses";
    }
  }

  grouping ISIS-SH-ADJ-AF {
    description "ISIS SH ADJ AF";

    container ipv4 {
      when "../af-name = 'ipv4'" {
        description "../AFName = 'IPv4'";
      }
      description "IPV4 neighbor info";
      uses ISIS-SH-ADJ-IPV4;
    }

    container ipv6 {
      when "../af-name = 'ipv6'" {
        description "../AFName = 'IPv6'";
      }
      description "IPV6 neighbor info";
      uses ISIS-SH-ADJ-IPV6;
    }
    leaf af-name {
      xr:xr-xml-map "isis_oper_types:AFName";
      type Isis-af-id;
      description "AFName";
    }
  }

  grouping ISIS-TOPO-ID-TYPE {
    description "Identification of an IS-IS topology";
    leaf af-name {
      xr:xr-xml-map "isis_oper_types:AFName";
      type Isis-af-id;
      description "AF name";
    }
    leaf saf-name {
      xr:xr-xml-map "isis_oper_types:SAFName";
      type Isis-sub-af-id;
      description "Sub-AF name";
    }
    leaf vrf-name {
      xr:xr-xml-map "isis_oper_types:VRFName";
      type string;
      description "VRF Name";
    }
    leaf topology-name {
      xr:xr-xml-map "isis_oper_types:TopologyName";
      type string;
      description "Topology Name";
    }
  }

  grouping ISIS-SH-NBR {
    description "A neighbor IS";
    leaf neighbor-system-id {
      xr:xr-xml-map "isis_oper_types:NeighborSystemID";
      type xr:Osi-system-id;
      description "Neighbor system ID";
    }
    leaf neighbor-snpa {
      xr:xr-xml-map "isis_oper_types:NeighborSNPA";
      type xr:Isis-snpa;
      description "Neighbor SNPA";
    }
    leaf local-interface {
      xr:xr-xml-map "isis_oper_types:LocalInterface";
      type xr:Interface-name;
      description "Local interface";
    }
    leaf neighbor-state {
      xr:xr-xml-map "isis_oper_types:NeighborState";
      type Isis-adj-state;
      description "Neighbor (adjacency) state";
    }
    leaf neighbor-circuit-type {
      xr:xr-xml-map "isis_oper_types:NeighborCircuitType";
      type Isis-levels;
      description "Circuit type";
    }
    leaf neighbor-ietf-nsf-capable-flag {
      xr:xr-xml-map "isis_oper_types:NeighborIETF_NSFCapableFlag";
      type uint32;
      description "TRUE if neighbor is IETF-NSF capable";
    }
    leaf neighbor-media-type {
      xr:xr-xml-map "isis_oper_types:NeighborMediaType";
      type Isis-media-class;
      description "Link media type";
    }
    leaf neighbor-holdtime {
      xr:xr-xml-map "isis_oper_types:NeighborHoldtime";
      type uint32;
      description
        "Time (s) until neighbor declared down if no IIH
        received";
    }
    leaf neighbor-uptime-valid-flag {
      xr:xr-xml-map "isis_oper_types:NeighborUptimeValidFlag";
      type boolean;
      description "TRUE if NeighborUptime is set";
    }
    leaf neighbor-uptime {
      xr:xr-xml-map "isis_oper_types:NeighborUptime";
      type uint32;
      description "How long the neighbor has been up (s)";
    }
    leaf nsr-standby {
      xr:xr-xml-map "isis_oper_types:NSR_STANDBY";
      type boolean;
      description "ISIS NSR STANDBY";
    }
    leaf-list neighbor-active-area-address {
      xr:xr-xml-map "isis_oper_types:NeighborActiveAreaAddresses";
      type xr:Osi-area-address;
      description "Active area addresses";
    }

    list topologies-supported {
      description
        "Topologies supported by both neighbor and local
        system";
      uses ISIS-TOPO-ID-TYPE;
    }

    list neighbor-per-address-family-data {
      description "Per address-family data";
      uses ISIS-SH-ADJ-AF;
    }
  }
}
