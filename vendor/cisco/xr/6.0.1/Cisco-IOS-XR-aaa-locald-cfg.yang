module Cisco-IOS-XR-aaa-locald-cfg {

  /*** NAMESPACE / PREFIX DEFINITION ***/

  namespace "http://cisco.com/ns/yang/Cisco-IOS-XR-aaa-locald-cfg";


  prefix "aaa-locald-cfg";

  /*** LINKAGE (IMPORTS / INCLUDES) ***/

  import Cisco-IOS-XR-types { prefix "xr"; }

  import Cisco-IOS-XR-aaa-lib-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR aaa-locald package configuration.

     This YANG module augments the
       Cisco-IOS-XR-aaa-lib-cfg
     module with configuration data.

     Copyright (c) 2013-2015 by Cisco Systems, Inc.
     All rights reserved.";

  revision "2015-11-09" {
    description
      "IOS XR 6.0 revision.";
  }

  typedef Aaa-locald-task-id {
    type string;
    description "Aaa locald task id";
  }
  typedef Aaa-locald-task-class {
    type enumeration {
      enum read {
        value 0;
        description "Permits read operation for a Task ID";
      }
      enum write {
        value 1;
        description "Permits write operation for a Task ID";
      }
      enum execute {
        value 2;
        description "Permits execute operation for a Task ID";
      }
      enum debug {
        value 3;
        description "Permits debug operation for a Task ID";
      }
    }
    description "Aaa locald task class";
  }

  augment "/a1:aaa" {

    container server-groups {
      xr:xr-xml-map "aaa_locald_cfg:ServerGroups";
      description "AAA group definitions";
    }
    description
      "This augment extends the configuration data of
      'Cisco-IOS-XR-aaa-lib-cfg'";
  }

  augment "/a1:aaa" {
    leaf default-taskgroup {
      xr:xr-xml-map "aaa_locald_cfg:DefaultTaskgroup";
      type string;
      description
        "This class is used for setting the default
        taskgroup to be used for remote server
        authentication";
    }
    description
      "This augment extends the configuration data of
      'Cisco-IOS-XR-aaa-lib-cfg'";
  }

  augment "/a1:aaa" {

    container usernames {
      xr:xr-xml-map "aaa_locald_cfg:UsernameTable";
      description "Configure local usernames";

      list username {
        xr:xr-xml-map "aaa_locald_cfg:Username";
        key "ordering-index name";
        description "Local username";

        container usergroup-under-usernames {
          xr:xr-xml-map "aaa_locald_cfg:UsergroupsUnderUsername";
          description
            "Specify the usergroup to which this user
            belongs";

          list usergroup-under-username {
            xr:xr-xml-map "aaa_locald_cfg:UsergroupUnderUsername";
            key "name";
            description "Name of the usergroup";
            leaf name {
              xr:xr-xml-map "aaa_locald_cfg:Name";
              type xr:Cisco-ios-xr-string;
              description "Name of the usergroup";
            }
          }
        }
        leaf secret {
          xr:xr-xml-map "aaa_locald_cfg:Secret";
          type xr:Md5-password;
          description "Specify the secret for the user";
        }
        leaf password {
          xr:xr-xml-map "aaa_locald_cfg:Password";
          type xr:Proprietary-password;
          description "Specify the password for the user";
        }
        leaf ordering-index {
          xr:xr-xml-map "aaa_locald_cfg:OrderingIndex";
          type int32;
          description
            "This is used to sort the users in the order of
            precedence";
        }
        leaf name {
          xr:xr-xml-map "aaa_locald_cfg:Name";
          type string;
          description "Username";
        }
      }
    }
    description
      "This augment extends the configuration data of
      'Cisco-IOS-XR-aaa-lib-cfg'";
  }

  augment "/a1:aaa" {

    container taskgroups {
      xr:xr-xml-map "aaa_locald_cfg:TaskgroupTable";
      description "Specify a taskgroup to inherit from";

      list taskgroup {
        xr:xr-xml-map "aaa_locald_cfg:Taskgroup";
        key "name";
        description "Taskgroup name";

        container taskgroup-under-taskgroups {
          xr:xr-xml-map "aaa_locald_cfg:TaskgroupsUnderTaskgroup";
          description "Specify a taskgroup to inherit from";

          list taskgroup-under-taskgroup {
            xr:xr-xml-map "aaa_locald_cfg:TaskgroupUnderTaskgroup";
            key "name";
            description "Name of the task group to include";
            leaf name {
              xr:xr-xml-map "aaa_locald_cfg:Name";
              type xr:Cisco-ios-xr-string;
              description "Name of the task group to include";
            }
          }
        }

        container tasks {
          xr:xr-xml-map "aaa_locald_cfg:TaskTable";
          description "Specify task IDs to be part of this group";

          list task {
            xr:xr-xml-map "aaa_locald_cfg:Task";
            key "type task-id";
            description "Task ID to be included";
            leaf type {
              xr:xr-xml-map "aaa_locald_cfg:Type";
              type Aaa-locald-task-class;
              description
                "This specifies the operation permitted for
                this task eg: read/write/execute/debug";
            }
            leaf task-id {
              xr:xr-xml-map "aaa_locald_cfg:TaskID";
              type Aaa-locald-task-id;
              description
                "Task ID to which permission is to be granted
                (please use class AllTasks to get a list of
                valid task IDs)";
            }
          }
        }
        leaf description {
          xr:xr-xml-map "aaa_locald_cfg:Description";
          type string;
          description "Description for the task group";
        }
        leaf name {
          xr:xr-xml-map "aaa_locald_cfg:Name";
          type string;
          description "Taskgroup name";
        }
      }
    }
    description
      "This augment extends the configuration data of
      'Cisco-IOS-XR-aaa-lib-cfg'";
  }

  augment "/a1:aaa" {

    container usergroups {
      xr:xr-xml-map "aaa_locald_cfg:UsergroupTable";
      description "Specify a Usergroup to inherit from";

      list usergroup {
        xr:xr-xml-map "aaa_locald_cfg:Usergroup";
        key "name";
        description "Usergroup name";

        container taskgroup-under-usergroups {
          xr:xr-xml-map "aaa_locald_cfg:TaskgroupsUnderUsergroup";
          description "Task group associated with this group";

          list taskgroup-under-usergroup {
            xr:xr-xml-map "aaa_locald_cfg:TaskgroupUnderUsergroup";
            key "name";
            description "Name of the task group";
            leaf name {
              xr:xr-xml-map "aaa_locald_cfg:Name";
              type xr:Cisco-ios-xr-string;
              description "Name of the task group";
            }
          }
        }

        container usergroup-under-usergroups {
          xr:xr-xml-map "aaa_locald_cfg:UsergroupsUnderUsergroup";
          description "User group to be inherited by this group";

          list usergroup-under-usergroup {
            xr:xr-xml-map "aaa_locald_cfg:UsergroupUnderUsergroup";
            key "name";
            description "Name of the user group";
            leaf name {
              xr:xr-xml-map "aaa_locald_cfg:Name";
              type xr:Cisco-ios-xr-string;
              description "Name of the user group";
            }
          }
        }
        leaf description {
          xr:xr-xml-map "aaa_locald_cfg:Description";
          type string;
          description "Description for the user group";
        }
        leaf name {
          xr:xr-xml-map "aaa_locald_cfg:Name";
          type string;
          description "Usergroup name";
        }
      }
    }
    description
      "This augment extends the configuration data of
      'Cisco-IOS-XR-aaa-lib-cfg'";
  }
}
