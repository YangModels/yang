submodule Cisco-IOS-XR-ipv4-io-oper-sub1 {

  belongs-to Cisco-IOS-XR-ipv4-io-oper {
    prefix Cisco-IOS-XR-ipv4-io-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ipv4-io package operational data.

     Copyright (c) 2013-2015 by Cisco Systems, Inc.
     All rights reserved.";

  revision "2015-10-20" {
    description
      "this schema file has all the latest changes.";
  }

  revision "2015-01-07" {
    description
      "IOS XR 5.3.1 revision.";
  }


  grouping IPV4-IO-ICMP-TRAFFIC {
    description "ICMP Traffic Information";
    leaf received {
      xr:xr-xml-map "ipv4_io_traffic:Received";
      type uint32;
      description "ICMP Received";
    }
    leaf checksum-error {
      xr:xr-xml-map "ipv4_io_traffic:ChecksumError";
      type uint32;
      description "ICMP Checksum Errors";
    }
    leaf unknown {
      xr:xr-xml-map "ipv4_io_traffic:Unknown";
      type uint32;
      description "ICMP Unknown";
    }
    leaf output {
      xr:xr-xml-map "ipv4_io_traffic:Output";
      type uint32;
      description "ICMP Transmitted";
    }
    leaf admin-unreachable-sent {
      xr:xr-xml-map "ipv4_io_traffic:AdminUnreachableSent";
      type uint32;
      description "ICMP Admin Unreachable Sent";
    }
    leaf network-unreachable-sent {
      xr:xr-xml-map "ipv4_io_traffic:NetworkUnreachableSent";
      type uint32;
      description "ICMP Network Unreachable Sent";
    }
    leaf host-unreachable-sent {
      xr:xr-xml-map "ipv4_io_traffic:HostUnreachableSent";
      type uint32;
      description "ICMP Host Unreachable Sent";
    }
    leaf protocol-unreachable-sent {
      xr:xr-xml-map "ipv4_io_traffic:ProtocolUnreachableSent";
      type uint32;
      description "ICMP Protocol Unreachable Sent";
    }
    leaf port-unreachable-sent {
      xr:xr-xml-map "ipv4_io_traffic:PortUnreachableSent";
      type uint32;
      description "ICMP Port Unreachable Sent";
    }
    leaf fragment-unreachable-sent {
      xr:xr-xml-map "ipv4_io_traffic:FragmentUnreachableSent";
      type uint32;
      description "ICMP Fragment Unreachable Sent";
    }
    leaf admin-unreachable-received {
      xr:xr-xml-map "ipv4_io_traffic:AdminUnreachableReceived";
      type uint32;
      description "ICMP Admin Unreachable Received";
    }
    leaf network-unreachable-received {
      xr:xr-xml-map "ipv4_io_traffic:NetworkUnreachableReceived";
      type uint32;
      description "ICMP Network Unreachable Received";
    }
    leaf host-unreachable-received {
      xr:xr-xml-map "ipv4_io_traffic:HostUnreachableReceived";
      type uint32;
      description "ICMP Host Unreachable Received";
    }
    leaf protocol-unreachable-received {
      xr:xr-xml-map "ipv4_io_traffic:ProtocolUnreachableReceived";
      type uint32;
      description "ICMP Protocol Unreachable Received";
    }
    leaf port-unreachable-received {
      xr:xr-xml-map "ipv4_io_traffic:PortUnreachableReceived";
      type uint32;
      description "ICMP Port Unreachable Received";
    }
    leaf fragment-unreachable-received {
      xr:xr-xml-map "ipv4_io_traffic:FragmentUnreachableReceived";
      type uint32;
      description "ICMP Fragment Unreachable Received";
    }
    leaf hopcount-sent {
      xr:xr-xml-map "ipv4_io_traffic:HopcountSent";
      type uint32;
      description "ICMP Hopcount Sent";
    }
    leaf reassembly-sent {
      xr:xr-xml-map "ipv4_io_traffic:ReassemblySent";
      type uint32;
      description "ICMP Reassembly Sent";
    }
    leaf hopcount-received {
      xr:xr-xml-map "ipv4_io_traffic:HopcountReceived";
      type uint32;
      description "ICMP Hopcount Received";
    }
    leaf reassebly-received {
      xr:xr-xml-map "ipv4_io_traffic:ReasseblyReceived";
      type uint32;
      description "ICMP Reassembly Received";
    }
    leaf param-error-received {
      xr:xr-xml-map "ipv4_io_traffic:ParamErrorReceived";
      type uint32;
      description "ICMP Parameter Error Received";
    }
    leaf param-error-send {
      xr:xr-xml-map "ipv4_io_traffic:ParamErrorSend";
      type uint32;
      description "ICMP Parameter Error Sent";
    }
    leaf echo-request-sent {
      xr:xr-xml-map "ipv4_io_traffic:EchoRequestSent";
      type uint32;
      description "ICMP Echo Request Sent";
    }
    leaf echo-request-received {
      xr:xr-xml-map "ipv4_io_traffic:EchoRequestReceived";
      type uint32;
      description "ICMP Echo Request Sent";
    }
    leaf echo-reply-sent {
      xr:xr-xml-map "ipv4_io_traffic:EchoReplySent";
      type uint32;
      description "ICMP Echo Reply Sent";
    }
    leaf echo-reply-received {
      xr:xr-xml-map "ipv4_io_traffic:EchoReplyReceived";
      type uint32;
      description "ICMP Echo Reply Received";
    }
    leaf mask-request-sent {
      xr:xr-xml-map "ipv4_io_traffic:MaskRequestSent";
      type uint32;
      description "ICMP Mask Sent";
    }
    leaf mask-request-received {
      xr:xr-xml-map "ipv4_io_traffic:MaskRequestReceived";
      type uint32;
      description "ICMP Mask Received";
    }
    leaf mask-reply-sent {
      xr:xr-xml-map "ipv4_io_traffic:MaskReplySent";
      type uint32;
      description "ICMP Mask Sent";
    }
    leaf mask-reply-received {
      xr:xr-xml-map "ipv4_io_traffic:MaskReplyReceived";
      type uint32;
      description "ICMP Mask Received";
    }
    leaf source-quench-received {
      xr:xr-xml-map "ipv4_io_traffic:SourceQuenchReceived";
      type uint32;
      description "ICMP Source Quench";
    }
    leaf redirect-received {
      xr:xr-xml-map "ipv4_io_traffic:RedirectReceived";
      type uint32;
      description "ICMP Redirect Received";
    }
    leaf redirect-send {
      xr:xr-xml-map "ipv4_io_traffic:RedirectSend";
      type uint32;
      description "ICMP Redirect Sent";
    }
    leaf timestamp-received {
      xr:xr-xml-map "ipv4_io_traffic:TimestampReceived";
      type uint32;
      description "ICMP Timestamp Received";
    }
    leaf timestamp-reply-received {
      xr:xr-xml-map "ipv4_io_traffic:TimestampReplyReceived";
      type uint32;
      description "ICMP Timestamp Reply Received";
    }
    leaf router-advert-received {
      xr:xr-xml-map "ipv4_io_traffic:RouterAdvertReceived";
      type uint32;
      description "ICMP Router Advertisement Received";
    }
    leaf router-solicit-received {
      xr:xr-xml-map "ipv4_io_traffic:RouterSolicitReceived";
      type uint32;
      description "ICMP Router Solicited Received";
    }
  }

  grouping IPV4-IO-TRAFFIC {
    description "IP Traffic Information";
    leaf input-packets {
      xr:xr-xml-map "ipv4_io_traffic:InputPackets";
      type uint32;
      description "Input Packets";
    }
    leaf received-packets {
      xr:xr-xml-map "ipv4_io_traffic:ReceivedPackets";
      type uint32;
      description "Received Packets";
    }
    leaf format-errors {
      xr:xr-xml-map "ipv4_io_traffic:FormatErrors";
      type uint32;
      description "Format Errors";
    }
    leaf bad-hop-count {
      xr:xr-xml-map "ipv4_io_traffic:BadHopCount";
      type uint32;
      description "Bad Hop Count";
    }
    leaf bad-source-address {
      xr:xr-xml-map "ipv4_io_traffic:BadSourceAddress";
      type uint32;
      description "Bad Source Address";
    }
    leaf bad-header {
      xr:xr-xml-map "ipv4_io_traffic:BadHeader";
      type uint32;
      description "Bad Header";
    }
    leaf no-protocol {
      xr:xr-xml-map "ipv4_io_traffic:NoProtocol";
      type uint32;
      description "No Protocol";
    }
    leaf no-gateway {
      xr:xr-xml-map "ipv4_io_traffic:NoGateway";
      type uint32;
      description "No Gateway";
    }
    leaf reassemble-input {
      xr:xr-xml-map "ipv4_io_traffic:ReassembleInput";
      type uint32;
      description "RaInput";
    }
    leaf reassembled {
      xr:xr-xml-map "ipv4_io_traffic:Reassembled";
      type uint32;
      description "Reassembled";
    }
    leaf reassemble-timeout {
      xr:xr-xml-map "ipv4_io_traffic:ReassembleTimeout";
      type uint32;
      description "Reassembly Timeout";
    }
    leaf reassemble-max-drop {
      xr:xr-xml-map "ipv4_io_traffic:ReassembleMaxDrop";
      type uint32;
      description "Reassembly Max Drop";
    }
    leaf reassemble-failed {
      xr:xr-xml-map "ipv4_io_traffic:ReassembleFailed";
      type uint32;
      description "Reassembly Failed";
    }
    leaf options-present {
      xr:xr-xml-map "ipv4_io_traffic:OptionsPresent";
      type uint32;
      description "IP Options Present";
    }
    leaf bad-option {
      xr:xr-xml-map "ipv4_io_traffic:BadOption";
      type uint32;
      description "Bad Option";
    }
    leaf unknown-option {
      xr:xr-xml-map "ipv4_io_traffic:UnknownOption";
      type uint32;
      description "Unknown Option";
    }
    leaf bad-security-option {
      xr:xr-xml-map "ipv4_io_traffic:BadSecurityOption";
      type uint32;
      description "Bad Security Option";
    }
    leaf basic-security-option {
      xr:xr-xml-map "ipv4_io_traffic:BasicSecurityOption";
      type uint32;
      description "Basic Security Option";
    }
    leaf extended-security-option {
      xr:xr-xml-map "ipv4_io_traffic:ExtendedSecurityOption";
      type uint32;
      description "Extended Security Option";
    }
    leaf cipso-option {
      xr:xr-xml-map "ipv4_io_traffic:CipsoOption";
      type uint32;
      description "Cipso Option";
    }
    leaf strict-source-route-option {
      xr:xr-xml-map "ipv4_io_traffic:StrictSourceRouteOption";
      type uint32;
      description "Strict Source Route Option";
    }
    leaf loose-source-route-option {
      xr:xr-xml-map "ipv4_io_traffic:LooseSourceRouteOption";
      type uint32;
      description "Loose Source Route Option";
    }
    leaf record-route-option {
      xr:xr-xml-map "ipv4_io_traffic:RecordRouteOption";
      type uint32;
      description "Record Route Option";
    }
    leaf sid-option {
      xr:xr-xml-map "ipv4_io_traffic:SIDOption";
      type uint32;
      description "SID Option";
    }
    leaf timestamp-option {
      xr:xr-xml-map "ipv4_io_traffic:TimestampOption";
      type uint32;
      description "Timestamp Option";
    }
    leaf router-alert-option {
      xr:xr-xml-map "ipv4_io_traffic:RouterAlertOption";
      type uint32;
      description "Router Alert Option";
    }
    leaf noop-option {
      xr:xr-xml-map "ipv4_io_traffic:NOOPOption";
      type uint32;
      description "Noop Option";
    }
    leaf end-option {
      xr:xr-xml-map "ipv4_io_traffic:EndOption";
      type uint32;
      description "End Option";
    }
    leaf packets-output {
      xr:xr-xml-map "ipv4_io_traffic:PacketsOutput";
      type uint32;
      description "Packets Output";
    }
    leaf packets-forwarded {
      xr:xr-xml-map "ipv4_io_traffic:PacketsForwarded";
      type uint32;
      description "Packets Forwarded";
    }
    leaf packets-fragmented {
      xr:xr-xml-map "ipv4_io_traffic:PacketsFragmented";
      type uint32;
      description "Packets Fragmented";
    }
    leaf fragment-count {
      xr:xr-xml-map "ipv4_io_traffic:FragmentCount";
      type uint32;
      description "Fragment Count";
    }
    leaf encapsulation-failed {
      xr:xr-xml-map "ipv4_io_traffic:EncapsulationFailed";
      type uint32;
      description "Encapsulation Failed";
    }
    leaf no-router {
      xr:xr-xml-map "ipv4_io_traffic:NoRouter";
      type uint32;
      description "No Router";
    }
    leaf packet-too-big {
      xr:xr-xml-map "ipv4_io_traffic:PacketTooBig";
      type uint32;
      description "Packet Too Big";
    }
    leaf multicast-in {
      xr:xr-xml-map "ipv4_io_traffic:MulticastIn";
      type uint32;
      description "Multicast In";
    }
    leaf multicast-out {
      xr:xr-xml-map "ipv4_io_traffic:MulticastOut";
      type uint32;
      description "Multicast Out";
    }
    leaf broadcast-in {
      xr:xr-xml-map "ipv4_io_traffic:BroadcastIn";
      type uint32;
      description "Broadcast In";
    }
    leaf broadcast-out {
      xr:xr-xml-map "ipv4_io_traffic:BroadcastOut";
      type uint32;
      description "Broadcast Out";
    }
    leaf lisp-v4-encap {
      xr:xr-xml-map "ipv4_io_traffic:LispV4Encap";
      type uint32;
      description "Lisp IPv4 encapped packets";
    }
    leaf lisp-v4-decap {
      xr:xr-xml-map "ipv4_io_traffic:LispV4Decap";
      type uint32;
      description "Lisp IPv4 decapped packets";
    }
    leaf lisp-v6-encap {
      xr:xr-xml-map "ipv4_io_traffic:LispV6Encap";
      type uint32;
      description "Lisp IPv6 encapped packets";
    }
    leaf lisp-v6-decap {
      xr:xr-xml-map "ipv4_io_traffic:LispV6Decap";
      type uint32;
      description "Lisp IPv6 decapped packets";
    }
    leaf lisp-encap-error {
      xr:xr-xml-map "ipv4_io_traffic:LispEncapError";
      type uint32;
      description "Lisp encap errors";
    }
    leaf lisp-decap-error {
      xr:xr-xml-map "ipv4_io_traffic:LispDecapError";
      type uint32;
      description "Lisp decap errors";
    }
  }

  grouping IP-TRAFFIC {
    description "IP and ICMP Traffic Information";

    container ipv4-stats {
      description "IPv4 Network Stats";
      uses IPV4-IO-TRAFFIC;
    }

    container icmp-stats {
      description "ICMP Stats";
      uses IPV4-IO-ICMP-TRAFFIC;
    }
  }
}
