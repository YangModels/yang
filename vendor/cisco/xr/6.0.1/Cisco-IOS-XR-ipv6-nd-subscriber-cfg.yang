module Cisco-IOS-XR-ipv6-nd-subscriber-cfg {

  /*** NAMESPACE / PREFIX DEFINITION ***/

  namespace "http://cisco.com/ns/yang"+
    "/Cisco-IOS-XR-ipv6-nd-subscriber-cfg";


  prefix "ipv6-nd-subscriber-cfg";

  /*** LINKAGE (IMPORTS / INCLUDES) ***/

  import Cisco-IOS-XR-types { prefix "xr"; }

  import Cisco-IOS-XR-subscriber-infra-tmplmgr-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ipv6-nd-subscriber package configuration.

     This YANG module augments the
       Cisco-IOS-XR-subscriber-infra-tmplmgr-cfg
     module with configuration data.

     Copyright (c) 2013-2015 by Cisco Systems, Inc.
     All rights reserved.";

  revision "2015-11-09" {
    description
      "IOS XR 6.0 revision.";
  }

  typedef Ipv6-nd-hop-limit {
    type enumeration {
      enum unspecified {
        value 0;
        description "Zero hoplimit value";
      }
    }
    description "Ipv6 nd hop limit";
  }
  typedef Ipv6-nd-router-pref-template {
    type enumeration {
      enum high {
        value 1;
        description "High preference";
      }
      enum medium {
        value 2;
        description "Medium preference";
      }
      enum low {
        value 3;
        description "Low preference";
      }
    }
    description "Ipv6 nd router pref template";
  }

  grouping IPV6-NEIGHBOR {
    description
      "Common node of ip-subscriber, ppp,
      subscriber-service";

    container ipv6-neighbor {
      xr:xr-xml-map "ipv6_nd_dyn_tmpl_cfg:IPv6Neighbor";
      description "Interface IPv6 Network configuration data";

      container framed-prefix {
        xr:xr-xml-map "ipv6_nd_dyn_tmpl_cfg:FramedPrefix";
        presence "Indicates a framed-prefix node is configured.";
        description
          "Set the IPv6 framed ipv6 prefix for a
          subscriber interface ";
        leaf prefix-length {
          xr:xr-xml-map "ipv6_nd_dyn_tmpl_cfg:PrefixLength";
          type xr:Ipv6-prefix-length;
          mandatory true;
          description "IPv6 framed prefix length";
        }
        leaf prefix {
          xr:xr-xml-map "ipv6_nd_dyn_tmpl_cfg:Prefix";
          type string;
          mandatory true;
          description "IPV6 framed prefix address";
        }
      }

      container duplicate-address-detection {
        xr:xr-xml-map "ipv6_nd_dyn_tmpl_cfg:DuplicateAddressDetecti"+
          "on";
        description "Duplicate Address Detection (DAD)";
        leaf attempts {
          xr:xr-xml-map "ipv6_nd_dyn_tmpl_cfg:Attempts";
          type uint32 {
            range "0..600";
          }
          description
            "Set IPv6 duplicate address detection transmits";
        }
      }

      container ra-initial {
        xr:xr-xml-map "ipv6_nd_dyn_tmpl_cfg:RAInitial";
        presence "Indicates a ra-initial node is configured.";
        description "IPv6 ND RA Initial";
        leaf count {
          xr:xr-xml-map "ipv6_nd_dyn_tmpl_cfg:Count";
          type uint32 {
            range "0..32";
          }
          mandatory true;
          description "Initial RA count";
        }
        leaf interval {
          xr:xr-xml-map "ipv6_nd_dyn_tmpl_cfg:Interval";
          type uint32 {
            range "4..1800";
          }
          units "second";
          mandatory true;
          description "Initial RA interval in seconds";
        }
      }
      leaf ra-hop-limit {
        xr:xr-xml-map "ipv6_nd_dyn_tmpl_cfg:RAHopLimit";
        type Ipv6-nd-hop-limit;
        description "IPv6 ND RA HopLimit";
      }
      leaf framed-prefix-pool {
        xr:xr-xml-map "ipv6_nd_dyn_tmpl_cfg:FramedPrefixPool";
        type string;
        description
          "Set the IPv6 framed ipv6 prefix pool for a
          subscriber interface ";
      }
      leaf managed-config {
        xr:xr-xml-map "ipv6_nd_dyn_tmpl_cfg:ManagedConfig";
        type empty;
        description
          "Host to use stateful protocol for address
          configuration";
      }
      leaf other-config {
        xr:xr-xml-map "ipv6_nd_dyn_tmpl_cfg:OtherConfig";
        type empty;
        description
          "Host to use stateful protocol for non-address
          configuration";
      }
      leaf start-ra-on-ipv6-enable {
        xr:xr-xml-map "ipv6_nd_dyn_tmpl_cfg:StartRAOnIpv6Enable";
        type empty;
        description "Start RA on ipv6-enable config";
      }
      leaf nud-enable {
        xr:xr-xml-map "ipv6_nd_dyn_tmpl_cfg:NUDEnable";
        type empty;
        description "NUD enable";
      }
      leaf ra-interval {
        xr:xr-xml-map "ipv6_nd_dyn_tmpl_cfg:RAInterval";
        type uint32 {
          range "3..1800";
        }
        units "second";
        description
          "Set IPv6 Router Advertisement (RA) interval in
          seconds";
      }
      leaf ra-lifetime {
        xr:xr-xml-map "ipv6_nd_dyn_tmpl_cfg:RALifetime";
        type uint32 {
          range "0..9000";
        }
        units "second";
        description
          "Set IPv6 Router Advertisement (RA) lifetime in
          seconds";
      }
      leaf router-preference {
        xr:xr-xml-map "ipv6_nd_dyn_tmpl_cfg:RouterPreference";
        type Ipv6-nd-router-pref-template;
        description "RA Router Preference";
      }
      leaf ra-suppress {
        xr:xr-xml-map "ipv6_nd_dyn_tmpl_cfg:RASuppress";
        type empty;
        description "Enable suppress IPv6 router advertisement";
      }
      leaf ra-unicast {
        xr:xr-xml-map "ipv6_nd_dyn_tmpl_cfg:RAUnicast";
        type empty;
        description "Enable RA unicast Flag";
      }
      leaf ra-suppress-mtu {
        xr:xr-xml-map "ipv6_nd_dyn_tmpl_cfg:RASuppressMTU";
        type empty;
        description "RA suppress MTU flag";
      }
      leaf suppress-cache-learning {
        xr:xr-xml-map "ipv6_nd_dyn_tmpl_cfg:SuppressCacheLearning";
        type empty;
        description "Suppress cache learning flag";
      }
      leaf reachable-time {
        xr:xr-xml-map "ipv6_nd_dyn_tmpl_cfg:ReachableTime";
        type uint32 {
          range "0..3600000";
        }
        units "millisecond";
        description
          "Set advertised reachability time in
          milliseconds";
      }
      leaf ns-interval {
        xr:xr-xml-map "ipv6_nd_dyn_tmpl_cfg:NSInterval";
        type uint32 {
          range "1000..3600000";
        }
        units "millisecond";
        description
          "Set advertised NS retransmission interval in
          milliseconds";
      }
    }
  }

  augment "/a1:dynamic-template/a1:subscriber-services"+
    "/a1:subscriber-service" {
    description
      "This augment extends the configuration data of
      'Cisco-IOS-XR-subscriber-infra-tmplmgr-cfg'";
    uses IPV6-NEIGHBOR;
  }

  augment "/a1:dynamic-template/a1:ppps/a1:ppp" {
    description
      "This augment extends the configuration data of
      'Cisco-IOS-XR-subscriber-infra-tmplmgr-cfg'";
    uses IPV6-NEIGHBOR;
  }

  augment "/a1:dynamic-template/a1:ip-subscribers/a1:ip-subscriber" {
    description
      "This augment extends the configuration data of
      'Cisco-IOS-XR-subscriber-infra-tmplmgr-cfg'";
    uses IPV6-NEIGHBOR;
  }
}
