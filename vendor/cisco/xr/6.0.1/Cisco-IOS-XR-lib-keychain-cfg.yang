module Cisco-IOS-XR-lib-keychain-cfg {

  /*** NAMESPACE / PREFIX DEFINITION ***/

  namespace "http://cisco.com/ns/yang/Cisco-IOS-XR-lib-keychain-cfg";


  prefix "lib-keychain-cfg";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR lib-keychain package configuration.

     This module contains definitions
     for the following management objects:
       keychains: Configure a Key Chain

     Copyright (c) 2013-2015 by Cisco Systems, Inc.
     All rights reserved.";

  revision "2015-07-30" {
    description
      "Descriptions updated.";
  }

  revision "2015-01-07" {
    description
      "IOS XR 5.3.1 revision.";
  }

  typedef Crypto-alg {
    type enumeration {
      enum alg-hmac-sha1-12 {
        value 2;
        description "HMAC SHA 1 12";
      }
      enum alg-md5-16 {
        value 3;
        description "MD5 16";
      }
      enum alg-sha1-20 {
        value 4;
        description "SHA 1 20";
      }
      enum alg-hmac-md5-16 {
        value 5;
        description "HMAC MD5 16";
      }
      enum alg-hmac-sha1-20 {
        value 6;
        description "HMAC SHA 1 20";
      }
    }
    description "Crypto alg";
  }
  typedef Key-chain-month {
    type enumeration {
      enum jan {
        value 0;
        description "January";
      }
      enum feb {
        value 1;
        description "February";
      }
      enum mar {
        value 2;
        description "March";
      }
      enum apr {
        value 3;
        description "April";
      }
      enum may {
        value 4;
        description "May";
      }
      enum jun {
        value 5;
        description "June";
      }
      enum jul {
        value 6;
        description "July";
      }
      enum aug {
        value 7;
        description "August";
      }
      enum sep {
        value 8;
        description "September";
      }
      enum oct {
        value 9;
        description "October";
      }
      enum nov {
        value 10;
        description "November";
      }
      enum dec {
        value 11;
        description "December";
      }
    }
    description "Key chain month";
  }

  container keychains {
    xr:xr-xml-map "lib_keychain_cfg:KeychainTable";
    description "Configure a Key Chain";

    list keychain {
      xr:xr-xml-map "lib_keychain_cfg:Keychain";
      key "chain-name";
      description "Name of the key chain";

      container accept-tolerance {
        xr:xr-xml-map "lib_keychain_cfg:AcceptTolerance";
        must "(value and not(infinite)) or (not(value) and"+
          " infinite)" {
          description "Describes valid combinations of leafs";
        }
        description "Accept Tolerance in seconds or infinite";
        leaf value {
          xr:xr-xml-map "lib_keychain_cfg:Value";
          type uint32 {
            range "1..8640000";
          }
          units "second";
          description "Value in seconds";
        }
        leaf infinite {
          xr:xr-xml-map "lib_keychain_cfg:Infinite";
          type boolean;
          description "Infinite tolerance";
        }
      }

      container keies {
        xr:xr-xml-map "lib_keychain_cfg:KeyTable";
        description "Configure a Key";

        list key {
          xr:xr-xml-map "lib_keychain_cfg:Key";
          key "key-id";
          description "Key Identifier";

          container accept-lifetime {
            xr:xr-xml-map "lib_keychain_cfg:AcceptLifetime";
            description "Configure a key Acceptance Lifetime";
            leaf start-hour {
              xr:xr-xml-map "lib_keychain_cfg:StartHour";
              type uint32 {
                range "0..23";
              }
              description "Start Hour";
            }
            leaf start-minutes {
              xr:xr-xml-map "lib_keychain_cfg:StartMinutes";
              type uint32 {
                range "0..59";
              }
              units "minute";
              description "Start Minutes";
            }
            leaf start-seconds {
              xr:xr-xml-map "lib_keychain_cfg:StartSeconds";
              type uint32 {
                range "0..59";
              }
              units "second";
              description "Start Seconds";
            }
            leaf start-date {
              xr:xr-xml-map "lib_keychain_cfg:StartDate";
              type uint32 {
                range "1..31";
              }
              description "Start Date";
            }
            leaf start-month {
              xr:xr-xml-map "lib_keychain_cfg:StartMonth";
              type Key-chain-month;
              description "Start Month";
            }
            leaf start-year {
              xr:xr-xml-map "lib_keychain_cfg:StartYear";
              type uint32 {
                range "1993..2035";
              }
              description "Start Year";
            }
            leaf life-time {
              xr:xr-xml-map "lib_keychain_cfg:LifeTime";
              type uint32 {
                range "1..2147483647";
              }
              units "second";
              description "Lifetime duration in seconds";
            }
            leaf infinite-flag {
              xr:xr-xml-map "lib_keychain_cfg:InfiniteFlag";
              type boolean;
              description "Infinite Lifetime flag";
            }
            leaf end-hour {
              xr:xr-xml-map "lib_keychain_cfg:EndHour";
              type uint32 {
                range "0..23";
              }
              description "End Hour";
            }
            leaf end-minutes {
              xr:xr-xml-map "lib_keychain_cfg:EndMinutes";
              type uint32 {
                range "0..59";
              }
              units "minute";
              description "End Minutes";
            }
            leaf end-seconds {
              xr:xr-xml-map "lib_keychain_cfg:EndSeconds";
              type uint32 {
                range "0..59";
              }
              units "second";
              description "End Seconds";
            }
            leaf end-date {
              xr:xr-xml-map "lib_keychain_cfg:EndDate";
              type uint32 {
                range "1..31";
              }
              description "End Date";
            }
            leaf end-month {
              xr:xr-xml-map "lib_keychain_cfg:EndMonth";
              type Key-chain-month;
              description "End Month";
            }
            leaf end-year {
              xr:xr-xml-map "lib_keychain_cfg:EndYear";
              type uint32 {
                range "1993..2035";
              }
              description "End Year";
            }
          }

          container send-lifetime {
            xr:xr-xml-map "lib_keychain_cfg:SendLifetime";
            description "Configure a Send Lifetime";
            leaf start-hour {
              xr:xr-xml-map "lib_keychain_cfg:StartHour";
              type uint32 {
                range "0..23";
              }
              description "Start Hour";
            }
            leaf start-minutes {
              xr:xr-xml-map "lib_keychain_cfg:StartMinutes";
              type uint32 {
                range "0..59";
              }
              units "minute";
              description "Start Minutes";
            }
            leaf start-seconds {
              xr:xr-xml-map "lib_keychain_cfg:StartSeconds";
              type uint32 {
                range "0..59";
              }
              units "second";
              description "Start Seconds";
            }
            leaf start-date {
              xr:xr-xml-map "lib_keychain_cfg:StartDate";
              type uint32 {
                range "1..31";
              }
              description "Start Date";
            }
            leaf start-month {
              xr:xr-xml-map "lib_keychain_cfg:StartMonth";
              type Key-chain-month;
              description "Start Month";
            }
            leaf start-year {
              xr:xr-xml-map "lib_keychain_cfg:StartYear";
              type uint32 {
                range "1993..2035";
              }
              description "Start Year";
            }
            leaf life-time {
              xr:xr-xml-map "lib_keychain_cfg:LifeTime";
              type uint32 {
                range "1..2147483647";
              }
              units "second";
              description "Lifetime duration in seconds";
            }
            leaf infinite-flag {
              xr:xr-xml-map "lib_keychain_cfg:InfiniteFlag";
              type boolean;
              description "Infinite Lifetime flag";
            }
            leaf end-hour {
              xr:xr-xml-map "lib_keychain_cfg:EndHour";
              type uint32 {
                range "0..23";
              }
              description "End Hour";
            }
            leaf end-minutes {
              xr:xr-xml-map "lib_keychain_cfg:EndMinutes";
              type uint32 {
                range "0..59";
              }
              units "minute";
              description "End Minutes";
            }
            leaf end-seconds {
              xr:xr-xml-map "lib_keychain_cfg:EndSeconds";
              type uint32 {
                range "0..59";
              }
              units "second";
              description "End Seconds";
            }
            leaf end-date {
              xr:xr-xml-map "lib_keychain_cfg:EndDate";
              type uint32 {
                range "1..31";
              }
              description "End Date";
            }
            leaf end-month {
              xr:xr-xml-map "lib_keychain_cfg:EndMonth";
              type Key-chain-month;
              description "End Month";
            }
            leaf end-year {
              xr:xr-xml-map "lib_keychain_cfg:EndYear";
              type uint32 {
                range "1993..2035";
              }
              description "End Year";
            }
          }
          leaf key-string {
            xr:xr-xml-map "lib_keychain_cfg:KeyString";
            xr:xr-cli-map "key-string (clear <text>)|(password <tex"+
              "t>)|(<text>) ";
            type xr:Proprietary-password;
            description
              "Configure a clear text/encrypted Key string ";
          }
          leaf cryptographic-algorithm {
            xr:xr-xml-map "lib_keychain_cfg:CryptographicAlgorithm";
            xr:xr-cli-map "cryptographic-algorithm (MD5)|(SHA-1)|(H"+
              "MAC-MD5)|(HMAC-SHA1-20)|(HMAC-SHA1-12) ";
            type Crypto-alg;
            description "Configure the cryptographic algorithm";
          }
          leaf key-id {
            xr:xr-xml-map "lib_keychain_cfg:KeyID";
            type xr:Cisco-ios-xr-string;
            description "48-bit Key identifier";
          }
        }
      }
      leaf chain-name {
        xr:xr-xml-map "lib_keychain_cfg:ChainName";
        type xr:Cisco-ios-xr-string;
        description "Name of the key chain";
      }
    }
  }
}
