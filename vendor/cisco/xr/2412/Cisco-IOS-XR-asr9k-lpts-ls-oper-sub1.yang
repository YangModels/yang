submodule Cisco-IOS-XR-asr9k-lpts-ls-oper-sub1 {
  belongs-to Cisco-IOS-XR-asr9k-lpts-ls-oper {
    prefix Cisco-IOS-XR-asr9k-lpts-ls-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR asr9k-lpts-ls package operational data.
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  grouping PL-PIFIB-SHOW-STATIC-POLICE-INFO {
    description
      "PL PIFIB SHOW STATIC POLICE INFO";
    leaf punt-reason {
      type uint32;
      description
        "punt reason";
    }
    leaf sid {
      type uint32;
      description
        "sid";
    }
    leaf flow-rate {
      type uint32;
      description
        "flow rate";
    }
    leaf burst-rate {
      type uint64;
      description
        "burst rate";
    }
    leaf accepted {
      type uint64;
      description
        "accepted";
    }
    leaf dropped {
      type uint64;
      description
        "dropped";
    }
    leaf punt-reason-string {
      type string {
        length "0..50";
      }
      description
        "punt reason string";
    }
    leaf change-type {
      type uint8;
      description
        "change type";
    }
    leaf stream-name {
      type string {
        length "0..50";
      }
      description
        "stream name";
    }
  }

  grouping PL-PIFIB-SHOW-STATIC-POLICE {
    description
      "Pre-IFIB platform specific punt reason data
       structure";
    list static-info {
      description
        "Per punt reason info";
      uses PL-PIFIB-SHOW-STATIC-POLICE-INFO;
    }
  }

  grouping PL-PIFIB-CONTEXT-STATUS {
    description
      "Pre-IFIB platform hardware data context status";
    leaf status {
      type string;
      description
        "The reply status upon the hardware context";
    }
  }

  grouping PL-PIFIB-CONTEXT-NPU-INFO {
    description
      "Pre-IFIB platform hardware npu data context info";
    leaf-list insert {
      type uint64;
      max-elements "5";
      description
        "insert";
    }
    leaf-list failed-insert {
      type uint64;
      max-elements "5";
      description
        "failed insert";
    }
    leaf-list keysel-insert {
      type uint64;
      max-elements "5";
      description
        "keysel insert";
    }
    leaf-list keysel-failed-insert {
      type uint64;
      max-elements "5";
      description
        "keysel failed insert";
    }
    leaf-list delete {
      type uint64;
      max-elements "5";
      description
        "delete";
    }
    leaf-list nonexisting-delete {
      type uint64;
      max-elements "5";
      description
        "nonexisting delete";
    }
    leaf-list keysel-delete {
      type uint64;
      max-elements "5";
      description
        "keysel delete";
    }
    leaf-list keysel-failed-delete {
      type uint64;
      max-elements "5";
      description
        "keysel failed delete";
    }
    leaf-list update {
      type uint64;
      max-elements "5";
      description
        "update";
    }
    leaf-list failed-update {
      type uint64;
      max-elements "5";
      description
        "failed update";
    }
    leaf-list hw-entry {
      type uint64;
      max-elements "5";
      description
        "hw entry";
    }
  }

  grouping PL-PIFIB-CONTEXT-INFO {
    description
      "Pre-IFIB platform hardware data context info";
    leaf pifib-sub-init-done {
      type uint8;
      description
        "Init status";
    }
    leaf max-policers {
      type uint32;
      description
        "Number of HW policers";
    }
    leaf policer-cfg-count {
      type uint32;
      description
        "Number of HW policers used";
    }
    leaf start-offset {
      type uint32;
      description
        "Start offset of HW policers";
    }
    list npu {
      description
        "Per NPU context info";
      uses PL-PIFIB-CONTEXT-NPU-INFO;
    }
  }

  grouping PL-PIFIB-POLICER-INFO {
    description
      "PL PIFIB POLICER INFO";
    leaf avgrate {
      type uint32;
      description
        "avgrate";
    }
    leaf burst {
      type uint32;
      description
        "burst";
    }
    leaf static-avgrate {
      type uint32;
      description
        "static avgrate";
    }
    leaf avgrate-type {
      type uint32;
      description
        "avgrate type";
    }
    leaf flow-type {
      type uint32;
      description
        "flow type";
    }
    leaf accepted-stats {
      type uint64;
      description
        "accepted stats";
    }
    leaf dropped-stats {
      type uint64;
      description
        "dropped stats";
    }
    leaf hw-policer-addr {
      type uint32;
      description
        "hw policer addr";
    }
    leaf sw-police-id {
      type uint16;
      description
        "sw police id";
    }
    leaf accepted-stats-deleted {
      type uint64;
      description
        "accepted stats deleted";
    }
    leaf dropped-stats-deleted {
      type uint64;
      description
        "dropped stats deleted";
    }
    leaf np-disp {
      type boolean;
      description
        "np disp";
    }
    leaf np-num {
      type uint32;
      description
        "np num";
    }
    leaf priority {
      type uint32;
      description
        "priority";
    }
    leaf ip-tos {
      type uint8;
      description
        "ip tos";
    }
  }

  grouping PL-PIFIB-SHOW-POLICER {
    description
      "Pre-IFIB platform specific police data structure";
    list police-info {
      description
        "Per flow type police info";
      uses PL-PIFIB-POLICER-INFO;
    }
  }

  grouping PL-PIFIB-SHOW-STATS {
    description
      "Pre-IFIB global statistics";
    leaf accepted {
      type uint64;
      description
        "Deleted-entry accepted packets counter";
    }
    leaf dropped {
      type uint64;
      description
        "Deleted-entry dropped packets counter";
    }
    leaf clear-ts {
      type uint64;
      description
        "Statistics clear timestamp";
    }
    leaf no-stats-mem-err {
      type uint64;
      description
        "No statistics memory error";
    }
  }
}
