submodule Cisco-IOS-XR-sks-server-oper-sub1 {
  belongs-to Cisco-IOS-XR-sks-server-oper {
    prefix Cisco-IOS-XR-sks-server-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR sks-server package operational data.
     
     Copyright (c) 2013-2022 by Cisco Systems, Inc.
     All rights reserved.";

  revision 2022-12-22 {
    description
      "Added support for http proxy.
       2022-11-22
         Added new fields for refresh reason.
       2022-08-27
         Added new fields for remote profile support.";
    semver:module-version "2.0.0";
  }
  revision 2021-08-11 {
    description
      "Added string bound check.";
    semver:module-version "1.0.0";
  }
  revision 2020-10-14 {
    description
      "Initial yang support for sks oper.";
  }
  revision 2019-04-05 {
    description
      "Establish semantic version baseline.";
  }
  revision 2015-11-09 {
    description
      "IOS XR 6.0 revision.";
  }

  typedef Sks-profile {
    type enumeration {
      enum "profile-type-unknown" {
        description
          "Profile type unknown";
      }
      enum "profile-type-local" {
        description
          "Profile type local";
      }
      enum "profile-type-remote" {
        description
          "Profile type remote";
      }
    }
    description
      "SKS profile Type";
  }

  typedef Sks-httpc-transaction {
    type enumeration {
      enum "transaction-unknown" {
        description
          "Transaction unknown";
      }
      enum "transaction-get-capability" {
        description
          "Transaction get capability";
      }
      enum "transaction-get-key" {
        description
          "Transaction get key";
      }
      enum "transaction-get-key-with-id" {
        description
          "Transaction get key with id";
      }
      enum "transaction-get-entropy" {
        description
          "Transaction get key with entropy";
      }
    }
    description
      "SKS http transaction type";
  }

  typedef Sks-tls-auth {
    type enumeration {
      enum "sks-tls-auth-unknown" {
        description
          "SKS TLS authentication type unknown";
      }
      enum "sks-tls-auth-psk" {
        description
          "SKS TLS authentication type pre-shared key";
      }
      enum "sks-tls-auth-cert" {
        description
          "SKS TLS authentication type certificate";
      }
    }
    description
      "SKS tls authentication Type";
  }

  typedef Sks-httpc-server-refresh-reason {
    type enumeration {
      enum "refresh-unknown" {
        description
          "Refresh reason unknown";
      }
      enum "refresh-vrf-update" {
        description
          "Refresh vrf update";
      }
      enum "refresh-server-update" {
        description
          "Refresh server update";
      }
      enum "refresh-server-removed" {
        description
          "Refresh server removed";
      }
      enum "refresh-src-interface-update" {
        description
          "Refresh src interface updated";
      }
      enum "refresh-src-interface-removed" {
        description
          "Refresh src interface removed";
      }
      enum "refresh-httpc-registration-failed" {
        description
          "Refresh http registration failed";
      }
      enum "refresh-httpc-send-req-failed" {
        description
          "Refresh http send request failed";
      }
      enum "refresh-httpc-send-req" {
        description
          "Refresh http sent request";
      }
      enum "refresh-httpc-recv-res-failed" {
        description
          "Refresh http receive response failed";
      }
      enum "refresh-httpc-recv-res" {
        description
          "Refresh http received response ";
      }
      enum "refresh-httpc-recv-key-res-failed" {
        description
          "Refresh http receive key response failed";
      }
      enum "refresh-httpc-down" {
        description
          "Refresh http client is down";
      }
      enum "refresh-httpc-up" {
        description
          "Refresh http client is now up";
      }
      enum "refresh-proxy-update" {
        description
          "Refresh proxy updated";
      }
      enum "refresh-proxy-removed" {
        description
          "Refresh proxy removed";
      }
      enum "refresh-tls-psk-update" {
        description
          "Refresh TLS Pre-shared key updated";
      }
      enum "refresh-tls-psk-removed" {
        description
          "Refresh TLS Pre-shared key removed";
      }
    }
    description
      "SKS http connection refresh reasons";
  }

  typedef Sks-httpc-server-connection-status {
    type enumeration {
      enum "state-unknown" {
        description
          "Server not configured";
      }
      enum "state-connecting" {
        description
          "Connecting to server";
      }
      enum "state-connected" {
        description
          "Connected to server";
      }
      enum "state-capability-refresh" {
        description
          "Capability refresh needed";
      }
      enum "state-capability-failed" {
        description
          "Capability fetch failed";
      }
      enum "state-registration-failed" {
        description
          "httpc Registration failed";
      }
    }
    description
      "SKS http connection status";
  }

  grouping SKS-MCELIECE-PUBKEY-INFO {
    description
      "Info for a sks pubkey";
    leaf key-label {
      type string;
      description
        "Label for pubkey";
    }
    leaf key-type {
      type string;
      description
        "Type of pubkey";
    }
    leaf key-size {
      type uint32;
      description
        "Size of pubkey";
    }
    leaf key-hash {
      type string;
      description
        "SHA1 hash of pubkey";
    }
  }

  grouping SKS-LOCAL-PROFILE-INFO {
    description
      "SKS local profile information";
    leaf live-keys {
      type uint32;
      description
        "Live keys for this profile";
    }
    leaf single-pool {
      type boolean;
      description
        "Single/Double pool for this profile";
    }
    leaf prf-done {
      type boolean;
      description
        "PRF done for this profile";
    }
  }

  grouping SKS-PEER-INFO {
    description
      "Info for a sks peer";
    leaf peer-name-xr {
      type string;
      description
        "Peer identifier";
    }
    leaf profile-name {
      type string;
      description
        "Profile Name for the peer";
    }
    leaf seed-done {
      type boolean;
      description
        "Seed done for this peer";
    }
    leaf pubkey-imp-done {
      type boolean;
      description
        "Pubkey import done for this peer";
    }
    leaf master {
      type boolean;
      description
        "This peer is master";
    }
  }

  grouping SKS-PROFILE-INFO {
    description
      "Info for a sks profile";
    container local-profile-info {
      description
        "Local profile information";
      uses SKS-LOCAL-PROFILE-INFO;
    }
    container remote-profile-info {
      description
        "Remote profile information";
      uses SKS-REMOTE-PROFILE-INFO;
    }
    leaf profile-name-xr {
      type string;
      description
        "Profile Name";
    }
    leaf my-identifier {
      type string;
      description
        "My identifier";
    }
    leaf reg-client-count {
      type uint32;
      description
        "Number of clients registered for change in this
         profile";
    }
    leaf profile-type {
      type Sks-profile;
      description
        "Type of profile";
    }
    list peer {
      description
        "Peers configured in this profile";
      uses SKS-PEER-INFO;
    }
  }

  grouping SKS-PROFILE-LAST-TRANSACTION-INFO {
    description
      "SKS remote profile last transaction status
       information";
    leaf tid {
      type uint32;
      description
        "Transaction Id";
    }
    leaf trans-type {
      type Sks-httpc-transaction;
      description
        "Transaction type";
    }
    leaf status {
      type uint32;
      description
        "Httpc status";
    }
    leaf status-code {
      type uint32;
      description
        "Http response code";
    }
    leaf status-string {
      type string;
      description
        "Http response code string";
    }
  }

  grouping SKS-REMOTE-PROFILE-RESPONSE-TIME-STATS {
    description
      "SKS remote profile transaction response time
       statistics";
    leaf max-time {
      type uint64;
      description
        "Maximum response time";
    }
    leaf min-time {
      type uint64;
      description
        "Minimum response time";
    }
    leaf avg-time {
      type uint64;
      description
        "Average response time";
    }
    leaf last-time {
      type uint64;
      description
        "Last transaction response time";
    }
  }

  grouping SKS-REMOTE-PROFILE-TRANSACTION-TYPE-COUNTERS {
    description
      "SKS remote profile transaction type counters";
    leaf get-capability {
      type uint32;
      description
        "Total capability count";
    }
    leaf get-key {
      type uint32;
      description
        "Total get key count";
    }
    leaf get-key-with-id {
      type uint32;
      description
        "Total get key with id count";
    }
    leaf get-entropy {
      type uint32;
      description
        "Total get entropy count";
    }
  }

  grouping SKS-REMOTE-PROFILE-GENERIC-COUNTERS {
    description
      "SKS remote profile generic counters";
    leaf request-total {
      type uint32;
      description
        "Total request count";
    }
    leaf request-failed {
      type uint32;
      description
        "Request failed";
    }
    leaf request-success {
      type uint32;
      description
        "Request success";
    }
    leaf response-total {
      type uint32;
      description
        "Total response count";
    }
    leaf response-failed {
      type uint32;
      description
        "Response failed";
    }
    leaf response-success {
      type uint32;
      description
        "Response success";
    }
    leaf retry-count {
      type uint32;
      description
        "Retry count";
    }
    leaf ignored-count {
      type uint32;
      description
        "ignored count";
    }
    leaf cancel-count {
      type uint32;
      description
        "Cancel count";
    }
    leaf validation-failed {
      type uint32;
      description
        "Validation failed";
    }
  }

  grouping SKS-REMOTE-PROFILE-PSK-AUTH-INFO {
    description
      "SKS remote profile Pre-shared key authentication
       information";
    leaf psk-identity {
      type string;
      description
        "Pre-shared key identifier";
    }
  }

  grouping SKS-REMOTE-PROFILE-AUTH-INFO {
    description
      "SKS remote profile authentication information";
    container psk-auth {
      description
        "Pre-shared key authentication information";
      uses SKS-REMOTE-PROFILE-PSK-AUTH-INFO;
    }
    leaf auth-type {
      type Sks-tls-auth;
      description
        "authentication type";
    }
  }

  grouping SKS-REMOTE-PROFILE-HTTP-PROXY-INFO {
    description
      "SKS remote profile http proxy information";
    leaf http-proxy-host-name {
      type string;
      description
        "Http proxy hostname";
    }
    leaf http-proxy-port {
      type uint16;
      description
        "Http proxy port";
    }
  }

  grouping SKS-REMOTE-PROFILE-CAPABILITY-REMOTE-IDS {
    description
      "SKS remote profile capability remote idenfitier
       list";
    leaf remote-identifier {
      type string;
      description
        "Remote Identifier";
    }
  }

  grouping SKS-REMOTE-PROFILE-CAPABILITY {
    description
      "SKS remote profile capability";
    leaf entropy-supported {
      type boolean;
      description
        "Entropy support";
    }
    leaf key-supported {
      type boolean;
      description
        "Key support";
    }
    leaf algorithm {
      type string;
      description
        "Algorithm";
    }
    leaf local-identifier {
      type string;
      description
        "Local identifier";
    }
    list remote-id {
      description
        "Remote identifier list";
      uses SKS-REMOTE-PROFILE-CAPABILITY-REMOTE-IDS;
    }
  }

  grouping SKS-REMOTE-PROFILE-INFO {
    description
      "SKS remote profile information";
    container capability {
      description
        "Server capability";
      uses SKS-REMOTE-PROFILE-CAPABILITY;
    }
    container http-proxy {
      description
        "http proxy information";
      uses SKS-REMOTE-PROFILE-HTTP-PROXY-INFO;
    }
    container auth-info {
      description
        "TLS authentication information";
      uses SKS-REMOTE-PROFILE-AUTH-INFO;
    }
    leaf server-addr {
      type string;
      description
        "Server ip address";
    }
    leaf server-port {
      type uint16;
      description
        "Server port";
    }
    leaf server-vrf {
      type string;
      description
        "Server Vrf";
    }
    leaf server-intf {
      type string;
      description
        "Server source interface";
    }
    leaf state {
      type Sks-httpc-server-connection-status;
      description
        "http session state";
    }
    leaf reason {
      type Sks-httpc-server-refresh-reason;
      description
        "http refresh reason";
    }
  }

  grouping SKS-PROFILE-STATS {
    description
      "Info for a sks profile";
    container remote-profile-info {
      description
        "Remote profile information";
      uses SKS-REMOTE-PROFILE-INFO;
    }
    container http-counters {
      description
        "Remote profile http generic counters";
      uses SKS-REMOTE-PROFILE-GENERIC-COUNTERS;
    }
    container http-transaction-request-counters {
      description
        "Remote profile http transaction type request
         counters";
      uses SKS-REMOTE-PROFILE-TRANSACTION-TYPE-COUNTERS;
    }
    container http-transaction-response-counters {
      description
        "Remote profile http transaction type response
         counters";
      uses SKS-REMOTE-PROFILE-TRANSACTION-TYPE-COUNTERS;
    }
    container response-time {
      description
        "Remote profile http transaction response time";
      uses SKS-REMOTE-PROFILE-RESPONSE-TIME-STATS;
    }
    container last-tran-info {
      description
        "Last transaction status info";
      uses SKS-PROFILE-LAST-TRANSACTION-INFO;
    }
    leaf profile-name-xr {
      type string;
      description
        "Profile Name";
    }
    leaf my-identifier {
      type string;
      description
        "My identifier";
    }
  }
}
