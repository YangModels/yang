module Cisco-IOS-XR-um-logging-correlator-cfg {
  namespace "http://cisco.com/ns/yang/Cisco-IOS-XR-um-logging-correlator-cfg";
  prefix um-logging-correlator-cfg;

  import Cisco-IOS-XR-types {
    prefix xr;
  }
  import Cisco-IOS-XR-um-logging-cfg {
    prefix a1;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR logging-correlator package configuration.
     
     This YANG module augments the
     modules with configuration data.
     
     Copyright (c) 2020-2022 by Cisco Systems, Inc.
     All rights reserved.";

  revision 2022-07-11 {
    description
      "Added missing description statement to nodes";
    semver:module-version "1.0.0";
  }
  revision 2020-09-30 {
    description
      "Initial release";
    semver:module-version "1.0.0";
  }

  augment "/a1:logging" {
    description
      "This augment extends logging nodes configuration";
    container correlator {
      description
        "Configure properties of the event correlator";
      leaf buffer-size {
        type uint32 {
          range "1024..52428800" {
            description
              "Size of the correlator buffer";
          }
        }
        description
          "Configure size of the correlator buffer";
      }
      container rules {
        description
          "Configure a specified correlation rule";
        list rule {
          must
            "type/stateful/timeout or type/stateful/timeout-rootcause or
             type/stateful/context-correlation or type/stateful/reparent or
             type/stateful/reissue-nonbistate or type/stateful/rootcause or
             type/stateful/nonrootcause/alarms/alarm or
             type/nonstateful/timeout or type/nonstateful/timeout-rootcause or
             type/nonstateful/context-correlation or
             type/nonstateful/rootcause or
             type/nonstateful/nonrootcause/alarms/alarm";
          key "rule-name";
          description
            "Configure a specified correlation rule";
          leaf rule-name {
            type xr:Cisco-ios-xr-string {
              length "1..32" {
                description
                  "Rule name";
              }
            }
            description
              "Configure a specified correlation rule";
          }
          container type {
            description
              "type of rule - stateful or nonstateful";
            container stateful {
              description
                "stateful rule type";
              leaf timeout {
                type uint32 {
                  range "1..7200000" {
                    description
                      "Timeout (time the rule is to be active) in milliseconds";
                  }
                }
                description
                  "Specify timeout";
              }
              leaf timeout-rootcause {
                type uint32 {
                  range "1..7200000" {
                    description
                      "Rootcause Timeout (time to wait for rootcause) in milliseconds";
                  }
                }
                description
                  "Specify timeout for root-cause";
              }
              container context-correlation {
                presence "Indicates a context-correlation node is configured.";
                description
                  "Specify enable correlation on context";
              }
              container reparent {
                presence "Indicates a reparent node is configured.";
                description
                  "Specify reparent of alarm on parent clear";
              }
              container reissue-nonbistate {
                presence "Indicates a reissue-nonbistate node is configured.";
                description
                  "Specify reissue of non-bistate alarms on parent clear";
              }
              container rootcause {
                presence "Indicates a rootcause node is configured.";
                description
                  "Specify root cause alarm: Category/Group/Code combos";
                leaf message-category {
                  type xr:Cisco-ios-xr-string {
                    length "1..32" {
                      description
                        "Message category of the root message";
                    }
                  }
                  mandatory true;
                  description
                    "Specify root cause alarm: Category/Group/Code combos";
                }
                leaf group-name {
                  type xr:Cisco-ios-xr-string {
                    length "1..32" {
                      description
                        "Group name of root message";
                    }
                  }
                  mandatory true;
                  description
                    "Group name of root message";
                }
                leaf message-code {
                  type xr:Cisco-ios-xr-string {
                    length "1..32" {
                      description
                        "Message code of root message";
                    }
                  }
                  mandatory true;
                  description
                    "Message code of root message";
                }
              }
              container nonrootcause {
                description
                  "nonrootcause alarm";
                container alarms {
                  description
                    "Specify non-root cause alarm: Category/Group/Code combos";
                  list alarm {
                    key "message-category group-name message-code";
                    description
                      "Specify non-root cause alarm: Category/Group/Code combos";
                    leaf message-category {
                      type string {
                        length "1..32" {
                          description
                            "Message category of the correlated message";
                        }
                      }
                      description
                        "Specify non-root cause alarm: Category/Group/Code combos";
                    }
                    leaf group-name {
                      type string {
                        length "1..32" {
                          description
                            "Group name of correlated message";
                        }
                      }
                      description
                        "Group name of correlated message";
                    }
                    leaf message-code {
                      type string {
                        length "1..32" {
                          description
                            "Message code of correlated message";
                        }
                      }
                      description
                        "Message code of correlated message";
                    }
                  }
                }
              }
            }
            container nonstateful {
              description
                "non-stateful rule type";
              leaf timeout {
                type uint32 {
                  range "1..7200000" {
                    description
                      "Timeout (time the rule is to be active) in milliseconds";
                  }
                }
                description
                  "Specify timeout";
              }
              leaf timeout-rootcause {
                type uint32 {
                  range "1..7200000" {
                    description
                      "Rootcause Timeout (time to wait for rootcause) in milliseconds";
                  }
                }
                description
                  "Specify timeout for root-cause";
              }
              container context-correlation {
                presence "Indicates a context-correlation node is configured.";
                description
                  "Specify enable correlation on context";
              }
              container rootcause {
                presence "Indicates a rootcause node is configured.";
                description
                  "Specify root cause alarm: Category/Group/Code combos";
                leaf message-category {
                  type xr:Cisco-ios-xr-string {
                    length "1..32" {
                      description
                        "Message category of the root message";
                    }
                  }
                  mandatory true;
                  description
                    "Specify root cause alarm: Category/Group/Code combos";
                }
                leaf group-name {
                  type xr:Cisco-ios-xr-string {
                    length "1..32" {
                      description
                        "Group name of root message";
                    }
                  }
                  mandatory true;
                  description
                    "Group name of root message";
                }
                leaf message-code {
                  type xr:Cisco-ios-xr-string {
                    length "1..32" {
                      description
                        "Message code of root message";
                    }
                  }
                  mandatory true;
                  description
                    "Message code of root message";
                }
              }
              container nonrootcause {
                description
                  "nonrootcause alarm";
                container alarms {
                  description
                    "Specify non-root cause alarm: Category/Group/Code combos";
                  list alarm {
                    key "message-category group-name message-code";
                    description
                      "Specify non-root cause alarm: Category/Group/Code combos";
                    leaf message-category {
                      type string {
                        length "1..32" {
                          description
                            "Message category of the correlated message";
                        }
                      }
                      description
                        "Specify non-root cause alarm: Category/Group/Code combos";
                    }
                    leaf group-name {
                      type string {
                        length "1..32" {
                          description
                            "Group name of correlated message";
                        }
                      }
                      description
                        "Group name of correlated message";
                    }
                    leaf message-code {
                      type string {
                        length "1..32" {
                          description
                            "Message code of correlated message";
                        }
                      }
                      description
                        "Message code of correlated message";
                    }
                  }
                }
              }
            }
          }
          container apply {
            description
              "Apply rule";
            container all-of-router {
              presence "Indicates a all-of-router node is configured.";
              description
                "Apply the rule to all of the router";
            }
            container locations {
              description
                "Apply rule to specified location";
              list location {
                key "location-name";
                description
                  "Apply rule to specified location";
                leaf location-name {
                  type xr:Node-id;
                  description
                    "Apply rule to specified location";
                }
              }
            }
            container contexts {
              description
                "Apply rule to specified context";
              list context {
                key "context-name";
                description
                  "Apply rule to specified context";
                leaf context-name {
                  type xr:Cisco-ios-xr-string {
                    length "1..32" {
                      description
                        "Context name";
                    }
                  }
                  description
                    "Apply rule to specified context";
                }
              }
            }
          }
        }
      }
      container rulesets {
        description
          "Configure a specified correlation ruleset";
        list ruleset {
          key "ruleset-name";
          description
            "Configure a specified correlation ruleset";
          leaf ruleset-name {
            type string {
              length "1..32" {
                description
                  "Ruleset name";
              }
            }
            description
              "Configure a specified correlation ruleset";
          }
          container rulenames {
            description
              "Specify rule name";
            list rulename {
              key "rulename-name";
              description
                "Specify rule name";
              leaf rulename-name {
                type string {
                  length "1..32" {
                    description
                      "Rule name";
                  }
                }
                description
                  "Specify rule name";
              }
            }
          }
          container apply {
            description
              "Apply ruleset";
            container all-of-router {
              presence "Indicates a all-of-router node is configured.";
              description
                "Apply the rule to all of the router";
            }
            container locations {
              description
                "Apply rule to specified location";
              list location {
                key "location-name";
                description
                  "Apply rule to specified location";
                leaf location-name {
                  type xr:Node-id;
                  description
                    "Apply rule to specified location";
                }
              }
            }
            container contexts {
              description
                "Apply rule to specified context";
              list context {
                key "context-name";
                description
                  "Apply rule to specified context";
                leaf context-name {
                  type xr:Cisco-ios-xr-string {
                    length "1..32" {
                      description
                        "Context name";
                    }
                  }
                  description
                    "Apply rule to specified context";
                }
              }
            }
          }
        }
      }
    }
    container suppress {
      description
        "Configure properties for the event suppression";
      container rules {
        description
          "Configure a specified suppression rule";
        list rule {
          must "alarms/alarm or all-alarms";
          key "rule-name";
          description
            "Configure a specified suppression rule";
          leaf rule-name {
            type string {
              length "1..32" {
                description
                  "Rule name";
              }
            }
            description
              "Configure a specified suppression rule";
          }
          container alarms {
            description
              "Specify alarm: Category/Group/Code combos";
            list alarm {
              key "message-category group-name message-code";
              description
                "Specify alarm: Category/Group/Code combos";
              leaf message-category {
                type string {
                  length "1..32" {
                    description
                      "Message category of the suppressed message";
                  }
                }
                description
                  "Specify alarm: Category/Group/Code combos";
              }
              leaf group-name {
                type string {
                  length "1..32" {
                    description
                      "Group name of suppressed message";
                  }
                }
                description
                  "Group name of suppressed message";
              }
              leaf message-code {
                type string {
                  length "1..32" {
                    description
                      "Message code of suppressed message";
                  }
                }
                description
                  "Message code of suppressed message";
              }
            }
          }
          container all-alarms {
            presence "Indicates a all-alarms node is configured.";
            description
              "All alarms of any Category/Group/Code combo";
          }
          container apply {
            description
              "Apply suppression rule";
            container all-of-router {
              presence "Indicates a all-of-router node is configured.";
              description
                "Apply the rule to all of the router";
            }
            container source {
              description
                "Apply rule to specified source";
              container locations {
                description
                  "Apply rule to specified location";
                list location {
                  key "location-name";
                  description
                    "Apply rule to specified location";
                  leaf location-name {
                    type xr:Node-id;
                    description
                      "Apply rule to specified location";
                  }
                }
              }
            }
          }
        }
      }
    }
  }
}
