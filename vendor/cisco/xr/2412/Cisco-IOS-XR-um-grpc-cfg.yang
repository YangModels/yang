module Cisco-IOS-XR-um-grpc-cfg {
  namespace "http://cisco.com/ns/yang/Cisco-IOS-XR-um-grpc-cfg";
  prefix um-grpc-cfg;

  import Cisco-IOS-XR-types {
    prefix xr;
  }
  import ietf-inet-types {
    prefix inet;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco grpc package configuration.
     
     Copyright (c) 2024 by Cisco Systems, Inc.
     All rights reserved.";

  revision 2024-03-05 {
    description
      "Added support for aaa accounting
       2023-12-14
         Added support for max concurrent streams per connection
       2023-11-28
         Added support for service layer and updated gnsi
       2023-09-15
         Updating model for um2 changes
       2023-06-28
         Added certificate common name
       2023-06-15
         Added support for IANA defined gRPC ports.
       2023-04-16
         Added container memory
       2023-03-22
         Added container keepalive
       2023-01-23
         Added support for virtual IP as gRPC tunnel source address and domain name as gRPC tunnel destination.
       2023-01-05
         Added p4rt container.
       2022-11-07
         Added gRPC SRTE service
       2022-09-26
         Added TTL leaf.
       2022-08-24
         Added tls-v1-disable container.";
    semver:module-version "3.0.0";
  }
  revision 2021-09-29 {
    description
      "Added certificate-authentication & local-connection containers
       2021-07-28
          Added tunnel container.";
    semver:module-version "2.1.0";
  }
  revision 2021-05-20 {
    description
      "Added leaf min-keepalive-interval.
       2020-08-01
           Added aaa container.";
    semver:module-version "2.0.0";
  }
  revision 2019-06-10 {
    description
      "Establish semantic version baseline.";
    semver:module-version "1.1.0";
  }
  revision 2019-03-30 {
    description
      "Initial version";
  }

  container grpc {
    presence "grpc configuration commands";
    description
      "grpc configuration commands";
    leaf certificate-authentication {
      type empty;
      description
        "Enables Certificate based Authentication";
    }
    leaf tls-mutual {
      type empty;
      description
        "Mutual Authentication";
    }
    leaf tlsv1-disable {
      type empty;
      description
        "Disable support for TLS version 1.0";
    }
    leaf max-request-total {
      type uint32 {
        range "1..256" {
          description
            "Maximum concurrent requests in total";
        }
      }
      description
        "Maximum concurrent requests in total";
    }
    leaf max-request-per-user {
      type uint32 {
        range "1..32" {
          description
            "Maximum concurrent requests per user";
        }
      }
      description
        "Maximum concurrent requests per user";
    }
    leaf max-streams {
      type uint32 {
        range "1..128" {
          description
            "Maximum number of streaming gRPCs (Default: 32)";
        }
      }
      description
        "Maximum number of streaming gRPCs (Default: 32)";
    }
    leaf max-streams-per-user {
      type uint32 {
        range "1..128" {
          description
            "Maximum number of streaming gRPCs per user (Default: 32)";
        }
      }
      description
        "Maximum number of streaming gRPCs per user (Default: 32)";
    }
    leaf port {
      type uint32 {
        range "57344..57999" {
          description
            "Server listening port";
        }
      }
      description
        "Server listening port";
    }
    leaf vrf {
      type xr:Cisco-ios-xr-string {
        length "1..1024" {
          description
            "vrf name";
        }
      }
      description
        "Server vrf";
    }
    leaf certificate-id {
      type xr:Cisco-ios-xr-string {
        length "1..1024" {
          description
            "Certificate ID";
        }
      }
      description
        "Active Certificate";
    }
    leaf name {
      type xr:Cisco-ios-xr-string {
        length "1..64" {
          description
            "gRPC server name";
        }
      }
      description
        "gRPC server name";
    }
    container aaa {
      description
        "AAA authorization and authentication for gRPC";
      container authorization {
        description
          "AAA authorization methodlist for gRPC";
        leaf exec {
          type xr:Cisco-ios-xr-string {
            length "1..1024" {
              description
                "AAA methodlist name";
            }
          }
          description
            "AAA authorization exec method list";
        }
      }
      container accounting {
        description
          "Accounting configurations for gRPC";
        leaf queue-size {
          type uint32 {
            range "1..512" {
              description
                "Queue size, values: 1-512. (default 100)";
            }
          }
          description
            "Maximum configurable size of the accounting queue";
        }
      }
      container authentication {
        description
          "AAA authentication methodlist for gRPC";
        leaf login {
          type xr:Cisco-ios-xr-string {
            length "1..1024" {
              description
                "AAA methodlist name";
            }
          }
          description
            "AAA authentication login method list";
        }
      }
    }
    container address-family {
      description
        "Address family identifier type";
      choice ADDRESS-FAMILY {
        description
          "Address family identifier type";
        case IPV4 {
          leaf ipv4 {
            type empty;
            description
              "IPv4 address-family";
          }
        }
        case IPV6 {
          leaf ipv6 {
            type empty;
            description
              "IPv6 address-family";
          }
        }
        case DUAL {
          leaf dual {
            type empty;
            description
              "dual stackaddress-family";
          }
        }
      }
    }
    leaf min-keepalive-interval {
      type uint32 {
        range "1..10000" {
          description
            "Keepalive interval in seconds";
        }
      }
      description
        "Minimum client keepalive interval";
    }
    leaf max-concurrent-streams {
      type uint32 {
        range "1..128" {
          description
            "gRPC concurrent stream limit, default 32";
        }
      }
      description
        "gRPC server maximum concurrent streams per connection";
    }
    container keepalive {
      description
        "Server keepalive time and timeout";
      leaf time {
        type uint32 {
          range "1..10000" {
            description
              "Server keepalive time in seconds (default 30)";
          }
        }
        description
          "Server keepalive time";
      }
      leaf timeout {
        type uint32 {
          range "1..10000" {
            description
              "Server keepalive timeout in seconds (default 20)";
          }
        }
        description
          "Server keepalive timeout";
      }
    }
    container memory {
      description
        "EMSd-Go soft memory limit in MB";
      leaf limit {
        type uint32 {
          range "600..1400" {
            description
              "Soft memory limit in MB, default 1024MB";
          }
        }
        description
          "Soft memory limit in MB";
      }
    }
    leaf local-connection {
      type empty;
      description
        "Enable gRPC server over Unix socket";
    }
    leaf ttl {
      type uint32 {
        range "0..255" {
          description
            "gRPC packets TTL value";
        }
      }
      description
        "gRPC packets TTL value";
    }
    container service-layer {
      presence "grpc service layer configuration";
      description
        "grpc service layer configuration";
      leaf auto-register {
        type empty;
        description
          "Enable service-layer auto-register";
      }
    }
    container certificate {
      description
        "gRPC server certificate";
      leaf common-name {
        type xr:Cisco-ios-xr-string {
          length "1..64" {
            description
              "Common name when generate certificates, default: ems.cisco.com";
          }
        }
        description
          "Common name when generate certificates";
      }
    }
    container segment-routing {
      presence "segment-routing";
      description
        "gRPC segment-routing configuration";
      container traffic-eng {
        presence "traffic-eng";
        description
          "gRPC segment-routing traffic-eng configuration";
        leaf policy-service {
          type empty;
          description
            "Enable SRTE policy services";
        }
      }
    }
    leaf tls-trustpoint {
      type string {
        length "1..1024" {
          description
            "trustpoint name";
        }
      }
      description
        "Configure trustpoint";
    }
    leaf dscp {
      type union {
        type uint32 {
          range "0..63" {
            description
              "Differentiated services code point";
          }
        }
        type enumeration {
          enum "af11" {
            value 10;
            description
              "AF11 (DSCP 001010)";
          }
          enum "af12" {
            value 12;
            description
              "AF12 (DSCP 001100)";
          }
          enum "af13" {
            value 14;
            description
              "AF13 (DSCP 001110)";
          }
          enum "af21" {
            value 18;
            description
              "AF21 (DSCP 010010)";
          }
          enum "af22" {
            value 20;
            description
              "AF22 (DSCP 010100)";
          }
          enum "af23" {
            value 22;
            description
              "AF23 (DSCP 010110)";
          }
          enum "af31" {
            value 26;
            description
              "AF31 (DSCP 011010)";
          }
          enum "af32" {
            value 28;
            description
              "AF32 (DSCP 011100)";
          }
          enum "af33" {
            value 30;
            description
              "AF33 (DSCP 011110)";
          }
          enum "af41" {
            value 34;
            description
              "AF41 (DSCP 100010)";
          }
          enum "af42" {
            value 36;
            description
              "AF42 (DSCP 100100)";
          }
          enum "af43" {
            value 38;
            description
              "AF43 (DSCP 100110)";
          }
          enum "cs1" {
            value 8;
            description
              "CS1 (Precedence 1) (DSCP 001000)";
          }
          enum "cs2" {
            value 16;
            description
              "CS2 (Precedence 2) (DSCP 010000)";
          }
          enum "cs3" {
            value 24;
            description
              "CS3 (Precedence 3) (DSCP 011000)";
          }
          enum "cs4" {
            value 32;
            description
              "CS4 (Precedence 4) (DSCP 100000)";
          }
          enum "cs5" {
            value 40;
            description
              "CS5 (Precedence 5) (DSCP 101000)";
          }
          enum "cs6" {
            value 48;
            description
              "CS6 (Precedence 6) (DSCP 110000)";
          }
          enum "cs7" {
            value 56;
            description
              "CS7 (Precedence 7) (DSCP 111000)";
          }
          enum "default" {
            value 0;
            description
              "Default (DSCP 000000)";
          }
          enum "ef" {
            value 46;
            description
              "EF (DSCP 101110)";
          }
        }
      }
      description
        "QoS marking DSCP to be set on transmitted gRPC";
    }
    container listen-addresses {
      description
        "gRPC server listening addresses";
      leaf-list listen-addresses-argument {
        type inet:ip-address-no-zone;
        max-elements "32";
        description
          "gRPC server listening addresses";
      }
    }
    container tunnel {
      description
        "grpc tunnel service";
      container destinations {
        description
          "gRPC tunnel destination";
        list destination {
          key "grpc-tunnel-destination port-number";
          description
            "gRPC tunnel destination";
          leaf grpc-tunnel-destination {
            type xr:Cisco-ios-xr-string {
              length "1..1024" {
                description
                  "IPv4/IPv6 address or domain name";
              }
            }
            description
              "gRPC tunnel destination";
          }
          leaf port-number {
            type uint32 {
              range "1..65535" {
                description
                  "Port number";
              }
            }
            description
              "Destination port";
          }
          leaf vrf {
            type xr:Cisco-ios-xr-string {
              length "1..1024" {
                description
                  "VRF name";
              }
            }
            description
              "VRF for the dial-out";
          }
          leaf source-interface {
            type xr:Interface-name;
            description
              "Source interface";
          }
          leaf target {
            type xr:Cisco-ios-xr-string {
              length "1..1024" {
                description
                  "Target name";
              }
            }
            description
              "Target name to register tunnel service";
          }
          leaf address-family {
            type enumeration {
              enum "ipv4" {
                value 1;
                description
                  "IPv4";
              }
              enum "ipv6" {
                value 2;
                description
                  "IPv6";
              }
            }
            description
              "Specify the AF for the returned addresses from DNS. Only applicable to domain name.";
          }
          container source {
            description
              "Virtual IP address family";
            container ipv6 {
              description
                "IPv6 address family";
              container virtual {
                description
                  "Virtual address";
                leaf address {
                  type empty;
                  description
                    "Virtual address";
                }
              }
            }
            container ipv4 {
              description
                "IPv4 address family";
              container virtual {
                description
                  "Virtual address";
                leaf address {
                  type empty;
                  description
                    "Virtual address";
                }
              }
            }
          }
        }
      }
    }
    container tls-cipher {
      description
        "gRPC TLS cipher suites";
      leaf default-all-ciphers {
        type enumeration {
          enum "enable" {
            value 2;
            description
              "Enable all ciphers";
          }
          enum "disable" {
            value 1;
            description
              "Disable all ciphers";
          }
        }
        description
          "Default of all ciphers";
      }
      leaf enable {
        type xr:Cisco-ios-xr-string {
          length "1..1024" {
            description
              "List of comma separated ciphers";
          }
        }
        description
          "Enable ciphers if 'default disable'";
      }
      leaf disable {
        type xr:Cisco-ios-xr-string {
          length "1..1024" {
            description
              "List of comma separated ciphers";
          }
        }
        description
          "Disable ciphers if 'default enable'";
      }
    }
    leaf no-tls {
      type empty;
      description
        "No TLS";
    }
    container gribi {
      presence "gRIBI service configuration";
      description
        "gRIBI service configuration";
      leaf port {
        type uint32 {
          range "1..65535" {
            description
              "gRIBI service port, values: 9340,57344-57999; default: 9340";
          }
        }
        description
          "gRIBI service listening port";
      }
    }
    container p4rt {
      presence "gRPC p4 runtime configuration";
      description
        "gRPC p4 runtime configuration";
      leaf port {
        type uint32 {
          range "1..65535" {
            description
              "p4 runtime service port, values: 9559,57344-57999; default: 9559";
          }
        }
        description
          "p4 runtime service listening port";
      }
      container interfaces {
        description
          "Configure p4rt interface attributes";
        list interface {
          key "interface-name";
          description
            "Interface to configure";
          leaf interface-name {
            type xr:Interface-name;
            description
              "Interface to configure";
          }
          leaf port-id {
            type uint32 {
              range "1..4294967039" {
                description
                  "Port identifier as a decimal value";
              }
            }
            description
              "Configure p4rt port identifier";
          }
        }
      }
      container locations {
        description
          "NPU location";
        list location {
          key "npu-location npu-id";
          description
            "NPU location";
          leaf npu-location {
            type xr:Node-id;
            description
              "NPU location";
          }
          leaf npu-id {
            type uint32 {
              range "0..7" {
                description
                  "NPU id";
              }
            }
            description
              "NPU id";
          }
          leaf device-id {
            type uint64 {
              range "1..18446744073709551615" {
                description
                  "Device identifier as a decimal value";
              }
            }
            mandatory true;
            description
              "Configure p4rt device identifier";
          }
        }
      }
    }
    container gnsi {
      description
        "gNSI";
      container service {
        description
          "gNSI service-level configuration";
        container certz {
          description
            "gNSI certificate management";
          leaf ssl-profile-id {
            type string {
              length "1..256" {
                description
                  "SSL profile name";
              }
            }
            description
              "SSL profile to be consumed by gRPC server";
          }
        }
      }
    }
    container gnmi {
      presence "gNMI service configuration";
      description
        "gNMI service configuration";
      leaf port {
        type uint32 {
          range "1..65535" {
            description
              "gNMI service port, values: 9339,57344-57999; default: 9339";
          }
        }
        description
          "gNMI service listening port";
      }
    }
  }
}
