submodule Cisco-IOS-XR-ptp-pd-oper-sub1 {
  belongs-to Cisco-IOS-XR-ptp-pd-oper {
    prefix Cisco-IOS-XR-ptp-pd-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR ptp-pd package operational data.
     
     Copyright (c) 2013-2023 by Cisco Systems, Inc.
     All rights reserved.";

  revision 2023-02-13 {
    description
      "Schema added for PTP monitor sessions.
       2021-08-08
         Schema added for APR log.";
    semver:module-version "1.2.0";
  }
  revision 2021-08-04 {
    description
      "Schema added for PTP statistics.
       2021-01-25
          Schema added for timestamps logger.";
    semver:module-version "1.1.0";
  }
  revision 2019-04-05 {
    description
      "Establish semantic version baseline.";
    semver:module-version "1.0.1";
  }
  revision 2016-06-08 {
    description
      "Schema added.";
  }
  revision 2015-11-09 {
    description
      "IOS XR 6.0 revision.";
  }

  grouping PTP-PD-SERVO-SESSION {
    description
      "Servo session";
    container last-received-t1 {
      description
        "last T1 timestamp received";
      uses PTP-PD-BAG-TIMESTAMP;
    }
    container last-received-t2 {
      description
        "last T2 timestamp received";
      uses PTP-PD-BAG-TIMESTAMP;
    }
    container last-received-t3 {
      description
        "last T3 timestamp received";
      uses PTP-PD-BAG-TIMESTAMP;
    }
    container last-received-t4 {
      description
        "last T4 timestamp received";
      uses PTP-PD-BAG-TIMESTAMP;
    }
    container pre-received-t1 {
      description
        "pre T1 timestamp received";
      uses PTP-PD-BAG-TIMESTAMP;
    }
    container pre-received-t2 {
      description
        "pre T2 timestamp received";
      uses PTP-PD-BAG-TIMESTAMP;
    }
    container pre-received-t3 {
      description
        "pre T3 timestamp received";
      uses PTP-PD-BAG-TIMESTAMP;
    }
    container pre-received-t4 {
      description
        "pre T4 timestamp received";
      uses PTP-PD-BAG-TIMESTAMP;
    }
    leaf clock-id {
      type uint32;
      description
        "Clock Id";
    }
    leaf steps-removed {
      type uint32;
      description
        "Steps removed";
    }
    leaf receiving-port {
      type uint32;
      description
        "Receiving port";
    }
    leaf servo-running {
      type boolean;
      description
        "Is Servo running";
    }
    leaf source-type {
      type uint32;
      description
        "Best source";
    }
    leaf has-freq {
      type boolean;
      description
        "Does source provide frequency";
    }
    leaf has-time {
      type boolean;
      description
        "Does source provide time";
    }
    leaf timescale {
      type uint8;
      description
        "Source's timescale";
    }
    leaf ifhandle {
      type uint32;
      description
        "Source's interface handle";
    }
    leaf delay-asymmetry {
      type int32;
      description
        "Asymmetry on interface";
    }
    leaf is-primary {
      type boolean;
      description
        "Is this a primary session";
    }
    leaf phase-offset {
      type int64;
      description
        "Offset from primary session";
    }
    leaf clock-error {
      type string {
        length "0..64";
      }
      description
        "Drift in PTP w.r.t source";
    }
    leaf clock-error-valid {
      type boolean;
      description
        "Is clock error valid";
    }
  }

  grouping PTP-PD-SERVO-SESSIONS {
    description
      "Servo sessions";
    list servo-session {
      description
        "Servo sessions";
      uses PTP-PD-SERVO-SESSION;
    }
  }

  grouping PTP-PD-TS-LOGGER-INFO {
    description
      "PTP PD timestamps logger info";
    leaf memory-buffer {
      type uint64;
      description
        "Memory buffer used for timestamps logging";
    }
    leaf redzone {
      type uint64;
      description
        "Red zone start offset";
    }
    leaf disk-fp {
      type uint64;
      description
        "Disk file pointer";
    }
    leaf next-rotating-file-index {
      type uint16;
      description
        "Next rotating file index";
    }
    leaf max-rotating-files {
      type uint16;
      description
        "Max rotating files";
    }
    leaf mem-fp {
      type uint64;
      description
        "Memory File pointer";
    }
    leaf dump-fp {
      type uint64;
      description
        "File pointer to which logs need to be dumped";
    }
    leaf current-offset {
      type uint64;
      description
        "Current offset in memory buffer";
    }
    leaf end-offset {
      type uint64;
      description
        "Log end offset in red-zone";
    }
    leaf mem-buf-size {
      type uint32;
      description
        "Size of Memory buffer";
    }
    leaf dumping-to-disk {
      type boolean;
      description
        "Logger dumping logs to disk";
    }
    leaf dumping-complete {
      type boolean;
      description
        "Dumping to disk complete";
    }
    leaf memory-logging-capable {
      type boolean;
      description
        "Logger capable of in-memory logging";
    }
    leaf platform-logging-capable {
      type boolean;
      description
        "Platform capable of in-memory logging";
    }
    leaf initialized {
      type boolean;
      description
        "Logger initialized";
    }
    leaf buffer-monitor-cnt {
      type uint32;
      description
        "Main thread health check for periodic buffer
         monitoring";
    }
    leaf buf-mon-discard-cnt {
      type uint32;
      description
        "Main thread discarded buffer monitoring";
    }
    leaf buffer-wraps {
      type uint32;
      description
        "Number of times the in-memory buffer wrapped";
    }
    leaf curr-ptr-adv-cnt {
      type uint32;
      description
        "Health check for in-memory logging offset
         advancing";
    }
    leaf dump-disk-req-check {
      type uint32;
      description
        "Health check for dumper-thread to check for dump
         req";
    }
    leaf red-zone-max-offset {
      type uint32;
      description
        "Max penetration into the red-zone";
    }
    leaf red-zone-over-err {
      type uint32;
      description
        "Red-Zone overflow";
    }
    leaf num-entries-discard {
      type uint32;
      description
        "Num entries discarded in last dump to disk file";
    }
    leaf num-entries-processed {
      type uint32;
      description
        "Num entries processed";
    }
    leaf dump-disk-req {
      type uint32;
      description
        "Number of requests to dump the logs to disk";
    }
    leaf dump-disk-completes {
      type uint32;
      description
        "Number of times logs dumped to disk";
    }
    leaf disk-write-fails {
      type uint32;
      description
        "Number of failures in writing to disk";
    }
    leaf last-disk-dump-size {
      type uint32;
      units "byte";
      description
        "Number of bytes written in last dump request";
    }
  }

  grouping PTP-PD-APR-LOGS {
    description
      "APR logs";
    leaf apr-logs {
      type string;
      description
        "APR logs";
    }
  }

  grouping PTP-PD-STAT-UNIT {
    description
      "PTP PD statistics unit";
    leaf min {
      type int64;
      description
        "Minimum value";
    }
    leaf max {
      type int64;
      description
        "Maximum value";
    }
    leaf mean {
      type int64;
      description
        "Mean value";
    }
    leaf num-entries {
      type uint32;
      description
        "Number of entries used to calculate the bucket";
    }
  }

  grouping PTP-PD-SERVO-STAT-LIST {
    description
      "Servo statistics list";
    container delta-t1 {
      description
        "T1 timestamp difference";
      uses PTP-PD-STAT-UNIT;
    }
    container delta-t2 {
      description
        "T2 timestamp difference";
      uses PTP-PD-STAT-UNIT;
    }
    container delta-t3 {
      description
        "T3 timestamp difference";
      uses PTP-PD-STAT-UNIT;
    }
    container delta-t4 {
      description
        "T4 timestamp difference";
      uses PTP-PD-STAT-UNIT;
    }
    container fwd-delay {
      description
        "Forward path delay";
      uses PTP-PD-STAT-UNIT;
    }
    container rev-delay {
      description
        "Reverse path delay";
      uses PTP-PD-STAT-UNIT;
    }
    container offset-from-master {
      description
        "Offset from Master";
      uses PTP-PD-STAT-UNIT;
    }
    container mean-path-delay {
      description
        "Mean path delay";
      uses PTP-PD-STAT-UNIT;
    }
  }

  grouping PTP-PD-SERVO-STAT-BUCKETS {
    description
      "Servo statistics buckets";
    container bucket5-sec {
      description
        "5 second bucket";
      uses PTP-PD-SERVO-STAT-LIST;
    }
    container bucket10-sec {
      description
        "10 second bucket";
      uses PTP-PD-SERVO-STAT-LIST;
    }
    container bucket1-min {
      description
        "1 minute bucket";
      uses PTP-PD-SERVO-STAT-LIST;
    }
  }

  grouping PTP-PD-BAG-TIMESTAMP {
    description
      "PTP PD timestamp";
    leaf second {
      type uint32;
      description
        "value of second";
    }
    leaf nano-second {
      type uint32;
      description
        "value of nano second";
    }
  }

  grouping PTP-PD-SERVO-INFO {
    description
      "PTP PD servo status";
    container last-set-time {
      description
        "last input of setTime";
      uses PTP-PD-BAG-TIMESTAMP;
    }
    container last-received-t1 {
      description
        "last T1 timestamp received";
      uses PTP-PD-BAG-TIMESTAMP;
    }
    container last-received-t2 {
      description
        "last T2 timestamp received";
      uses PTP-PD-BAG-TIMESTAMP;
    }
    container last-received-t3 {
      description
        "last T3 timestamp received";
      uses PTP-PD-BAG-TIMESTAMP;
    }
    container last-received-t4 {
      description
        "last T4 timestamp received";
      uses PTP-PD-BAG-TIMESTAMP;
    }
    container pre-received-t1 {
      description
        "pre T1 timestamp received";
      uses PTP-PD-BAG-TIMESTAMP;
    }
    container pre-received-t2 {
      description
        "pre T2 timestamp received";
      uses PTP-PD-BAG-TIMESTAMP;
    }
    container pre-received-t3 {
      description
        "pre T3 timestamp received";
      uses PTP-PD-BAG-TIMESTAMP;
    }
    container pre-received-t4 {
      description
        "pre T4 timestamp received";
      uses PTP-PD-BAG-TIMESTAMP;
    }
    leaf lock-status {
      type uint16;
      description
        "lock status of device";
    }
    leaf running {
      type boolean;
      description
        "running status of apr";
    }
    leaf device-status {
      type string {
        length "0..50";
      }
      description
        "status of device";
    }
    leaf log-level {
      type uint16;
      description
        "log level of apr";
    }
    leaf phase-accuracy-last {
      type int64;
      description
        " last phase alignment accuracy";
    }
    leaf num-sync-timestamp {
      type uint32;
      description
        "number of sync timestamp received";
    }
    leaf num-delay-timestamp {
      type uint32;
      description
        "number of delay timestamp received";
    }
    leaf num-set-time {
      type uint32;
      description
        "number of setTime() been called";
    }
    leaf num-step-time {
      type uint32;
      description
        "number of stepTime() been called";
    }
    leaf num-adjust-freq {
      type uint32;
      description
        "number of adjustFreq() been called";
    }
    leaf num-adjust-freq-time {
      type uint32;
      description
        "number of adjustFreqTime() been called";
    }
    leaf last-adjust-freq {
      type int32;
      description
        "last input of adjustFreq";
    }
    leaf last-step-time {
      type int32;
      description
        "last input of stepTime";
    }
    leaf num-discard-sync-timestamp {
      type uint32;
      description
        "number of sync timestamp discarded";
    }
    leaf num-discard-delay-timestamp {
      type uint32;
      description
        "number of delay timestamp discarded";
    }
    leaf flagof-last-set-time {
      type boolean;
      description
        "last input flag of setTime";
    }
    leaf offset-from-master {
      type int64;
      description
        "Time Offset From Master";
    }
    leaf mean-path-delay {
      type int64;
      description
        "Mean Path Delay";
    }
    leaf servo-mode {
      type int32;
      description
        "Servo Mode";
    }
  }
}
