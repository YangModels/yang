submodule Cisco-IOS-XR-cnbng-nal-oper-sub1 {
  belongs-to Cisco-IOS-XR-cnbng-nal-oper {
    prefix Cisco-IOS-XR-cnbng-nal-oper;
  }

  import ietf-inet-types {
    prefix inet;
  }
  import ietf-yang-types {
    prefix yang;
  }
  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR cnbng-nal package operational data.
     
     Copyright (c) 2013-2023 by Cisco Systems, Inc.
     All rights reserved.";

  revision 2023-10-24 {
    description
      "Removed SRG role change counters.
       2023-10-12
         Updated CP-UP connection information to include PFCP and GTPu socket bind result.
       2023-10-03
         Interface name length size is updated.
       2023-07-24
         Annotated process readiness and control-plane/user-plane connection data for EDT support.
       2023-04-07
         Added field to display api-stats viz err status, last fail time, upid for all API used by cnbng nal.
       2023-03-30
         Changed String in dynamic route bag
       2023-03-28
         Reduced failed entry bag description length from 256 to 65 bytes.
       2023-01-11
         Added counters for cp-up spa recon stats.
       2022-12-14
         Added the new field desciption in auto-loopback vrf and srg group configuration.
       2022-12-02
         Updated the data type of node feature-id to String.
       2022-11-21
         Added block size in chunk statistics and session replay response as dynamic data in bag.
       2022-11-03
         Updated binary data associated with each event in event history entry as private.
       2022-10-20
         Changed readable strings like interface/vrf names from type char to string.
       2022-09-06
         Renamed structure in bag file.
       2022-08-31
         Migrated XR library event history to internal history library.
       2022-08-30
         Added key meta-data into oper yang lists.
       2022-08-08
         Added new element outstanding_ka_expiry_cnt in bag file.
       2022-08-04
         Removed dynamic route history query from schema.
       2022-07-27
         Updated SRG group admin state datatype
       2022-07-21
         Updated nal_subscriber_session_info gateway IP format from uint32_t to in_addr_t
       2022-05-16
         added new elements in bag
       2022-03-16
         Added SRG group summary support
       2022-03-15
         Counters arrays made dynamic.
       2022-03-15
         Added counter for fast switchover timer expiry.
       2022-03-10
         Added counters for SRG group recon start and end.
       2022-03-07
         Added additional NAL disconnect types
       2022-03-04
         Added counter for zero subscribers in recon replay request.
       2022-03-02
         Added new counters for SRG stats retry enqueue.
       2022-03-02
         Added new counter for SRG group state is not ready.
       2022-02-23
         Updated SRG show command bag with reconciliation information.
       2022-02-10
         Added SRG show commands.
       2022-01-27
         Updated length of interface name string length from 64 to 72
       2022-01-20
         Updated process info bag with in-flight configuration values
       2021-12-21
         Added access interface event history
       2021-12-01
         Updated xml tree definitions
       2021-11-11
         Dynamic Route info addition in route provision flow.
       2021-10-20
         AIPC server stats display command updated.
       2021-10-10
         Added schema support for multiple show CLIs
       2021-09-30
         Added new counter for tracking empty pulses in nal_main_edm_nal_counters lac_stats.
       2021-09-29
         Added batch counter for spio resync";
    semver:module-version "3.0.0";
  }
  revision 2021-09-27 {
    description
      "Updated transport and association status enum in yang model.
       2021-07-22
          Updated nal_main_edm_process_info to include SPIO connection information.
       2021-07-06
          Added schema support for all address family in show dynamic route command.
       2021-07-02
          Added connection status information and interface counters.
       2021-06-30
          Added process readiness and transaction pending flags in nal_main_edm_process_readiness.
       2021-06-26
          Updated nal_main_edm_process_info bag to include features supported from platform.
       2021-06-20
          Added new path for getting subscriber summary based on VRF name.
       2021-06-14
          Added tunnel vrf for LAC/LNS subscriber bag
       2021-06-11
          Updated subscriber brief bag with subscriber interface handle.
       2021-05-31
          Added new NAL counter type client api
       2021-05-29
          Added new bag for getting subscriber count and global routes installed.
       2021-05-05
          Added tr459 mode enable flag in bag structure.
       2021-04-01
          added LNS subcriber info in bag
       2021-03-15
          added details for LAC subcriber in bag";
    semver:module-version "2.0.0";
  }
  revision 2021-02-17 {
    description
      "Added AFI only filters";
    semver:module-version "1.0.0";
  }
  revision 2021-02-10 {
    description
      "Removed redundant fail route index";
  }
  revision 2021-02-04 {
    description
      "Added multi framed route support, metric and tag";
  }
  revision 2021-01-23 {
    description
      "Added new NAL counter type thread_stats";
  }
  revision 2020-12-13 {
    description
      "NAL SVM service final timestamp.";
  }
  revision 2020-12-08 {
    description
      "modify Disconnect History Filter keys.";
  }
  revision 2020-11-27 {
    description
      "NAL counters.";
  }
  revision 2020-11-10 {
    description
      "Update bgen path for dynamic routes and removed schema for dynamic routes history.";
  }
  revision 2020-10-26 {
    description
      "Update bag type for AIPC server stats.";
  }
  revision 2020-10-15 {
    description
      "Added schema support for cnbng-nal filter oper commands.";
  }
  revision 2020-10-08 {
    description
      "Moved counter and AIPC stats to new bag files.";
  }
  revision 2020-10-02 {
    description
      "Modified alter gen script to modify leaf list to list.";
  }
  revision 2020-09-18 {
    description
      "Added schema support for cnbng-nal access-interface oper commands.";
  }
  revision 2020-09-15 {
    description
      "adding schema support for NAL chunk statistics oper bag.";
  }
  revision 2020-09-10 {
    description
      "Updated schema for filtering subscriber summary.";
  }
  revision 2020-09-03 {
    description
      "adding schema support for NAL Counters, Dynamic routes, summary and history bag.";
  }
  revision 2020-07-24 {
    description
      "adding schema support for disconect uniuqe and modifying unique summary.";
  }
  revision 2020-06-06 {
    description
      "adding schema support for NAL Process-Info Bag";
  }
  revision 2020-05-29 {
    description
      "adding schema support for Disconnect History Filter.";
  }
  revision 2020-05-15 {
    description
      "adding schema support for NAL CP Transport Connection Status Bag";
  }
  revision 2020-04-30 {
    description
      "adding schema support for NAL VRF Table records";
  }
  revision 2020-04-23 {
    description
      "added new elements in bag";
  }
  revision 2020-04-09 {
    description
      "modified class name for FADB records";
  }
  revision 2020-04-03 {
    description
      "adding schema support for subsriber summary and FADB records";
  }
  revision 2020-04-02 {
    description
      "adding schema support for service profiles and process readiness";
  }
  revision 2020-03-30 {
    description
      "adding schema support for v4 and v6 framed route";
  }
  revision 2019-04-05 {
    description
      "Establish semantic version baseline.";
  }
  revision 2015-11-09 {
    description
      "IOS XR 6.0 revision.";
  }

  typedef Nal-main-edm-oc-state {
    type enumeration {
      enum "nal-main-edm-oc-state-init" {
        description
          "Initial state";
      }
      enum "nal-main-edm-oc-state-sent" {
        description
          "OC request sent to IM";
      }
      enum "nal-main-edm-oc-state-complete" {
        description
          "OC response received";
      }
      enum "nal-main-edm-oc-state-rib-req-queued" {
        description
          "RIB route request queued";
      }
      enum "nal-main-edm-oc-state-rib-req-sent" {
        description
          "RIB route request sent";
      }
      enum "nal-main-edm-oc-state-rib-req-complete" {
        description
          "RIB response received";
      }
      enum "nal-main-edm-oc-state-rib-inactive" {
        description
          "VRF deleted";
      }
    }
    description
      "Nal main edm oc state";
  }

  typedef Nal-cp-assoc-status {
    type enumeration {
      enum "nal-spa-assoc-no-init" {
        value 0;
        description
          "Association status not initialized";
      }
      enum "nal-spa-assoc-init" {
        value 1;
        description
          "Association status init";
      }
      enum "nal-spa-assoc-done" {
        value 2;
        description
          "Association status done";
      }
      enum "nal-spa-assoc-not-done" {
        value 3;
        description
          "Association status not-done";
      }
    }
    description
      "Nal cp assoc status";
  }

  typedef Nal-cp-connection-status {
    type enumeration {
      enum "nal-spa-transport-no-init" {
        value 0;
        description
          "Transport status not initialized";
      }
      enum "nal-spa-transport-init" {
        value 1;
        description
          "Transport status Init";
      }
      enum "nal-spa-transport-up" {
        value 2;
        description
          "Transport status Up";
      }
      enum "nal-spa-transport-down" {
        value 3;
        description
          "Transport status Down";
      }
    }
    description
      "Nal cp connection status";
  }

  typedef Nal-sir-history-event {
    type enumeration {
      enum "nal-sir-history-event-proc-ready" {
        description
          "nal sir history event proc ready";
      }
      enum "nal-sir-history-event-sir-state" {
        description
          "nal sir history event sir state";
      }
      enum "nal-sir-history-event-max" {
        description
          "nal sir history event max";
      }
    }
    description
      "SIR history event types";
  }

  typedef Nal-main-edm-srg-group-upd-req-state {
    type enumeration {
      enum "nal-main-edm-srg-upd-req-state-send-in-progress" {
        value 1;
        description
          "Role update requests are getting sent";
      }
      enum "nal-main-edm-srg-upd-req-state-idle" {
        value 2;
        description
          "No activities in progress";
      }
    }
    description
      "Role update request state during role change";
  }

  typedef Nal-main-edm-srg-trans-state {
    type enumeration {
      enum "nal-main-edm-srg-trans-state-invalid" {
        value 0;
        description
          "SRG FSM transaction state Invalid";
      }
      enum "nal-main-edm-srg-trans-state-init" {
        value 1;
        description
          "SRG FSM transaction state Init";
      }
      enum "nal-main-edm-srg-trans-state-queued" {
        value 2;
        description
          "SRG FSM transaction state queued";
      }
      enum "nal-main-edm-srg-trans-state-role-change" {
        value 3;
        description
          "SRG FSM transaction state role change";
      }
      enum "nal-main-edm-srg-trans-state-paused" {
        value 4;
        description
          "SRG FSM transaction state paused";
      }
      enum "nal-main-edm-srg-trans-state-complete" {
        value 5;
        description
          "SRG FSM transaction state complete";
      }
      enum "nal-main-edm-srg-trans-state-max" {
        value 6;
        description
          "SRG FSM transaction state max";
      }
    }
    description
      "SRG FSM transaction states";
  }

  typedef Nal-main-edm-srg-group-admin-state {
    type enumeration {
      enum "nal-main-edm-srg-group-admin-state-unknown" {
        description
          "nal main edm srg group admin state unknown";
      }
      enum "nal-main-edm-srg-group-admin-state-up-configured" {
        description
          "nal main edm srg group admin state up
           configured";
      }
      enum "nal-main-edm-srg-group-admin-state-cp-configured" {
        description
          "nal main edm srg group admin state cp
           configured";
      }
      enum "nal-main-edm-srg-group-admin-state-up-cp-configured" {
        description
          "nal main edm srg group admin state up cp
           configured";
      }
    }
    description
      "Nal main edm srg group admin state";
  }

  typedef Nal-main-edm-srg-group-state {
    type enumeration {
      enum "nal-main-edm-srg-group-state-invalid" {
        description
          "nal main edm srg group state invalid";
      }
      enum "nal-main-edm-srg-group-state-up" {
        description
          "nal main edm srg group state up";
      }
      enum "nal-main-edm-srg-group-state-down" {
        description
          "nal main edm srg group state down";
      }
      enum "nal-main-edm-srg-group-state-not-ready" {
        description
          "nal main edm srg group state not ready";
      }
    }
    description
      "SRG group states";
  }

  typedef Nal-main-edm-srg-group-stats-state {
    type enumeration {
      enum "nal-main-edm-srg-group-stats-state-req" {
        value 1;
        description
          "Queued in flow control queue";
      }
      enum "nal-main-edm-srg-group-stats-state-req-comp" {
        value 2;
        description
          "Requests are complete. Waiting for responses.";
      }
      enum "nal-main-edm-srg-group-stats-state-idle" {
        value 3;
        description
          "No activities in progress";
      }
    }
    description
      "SRG stats state during role change";
  }

  typedef Svm-service-state {
    type enumeration {
      enum "nal-oper-svm-service-state-unknown" {
        value 0;
        description
          "nal oper svm service state unknown";
      }
      enum "nal-oper-svm-service-state-created" {
        value 1;
        description
          "nal oper svm service state created";
      }
      enum "nal-oper-svm-service-state-install-request-ed" {
        value 2;
        description
          "nal oper svm service state install request ed";
      }
      enum "nal-oper-svm-service-state-install-req-failed" {
        value 3;
        description
          "nal oper svm service state install req failed";
      }
      enum "nal-oper-svm-service-state-install-failed" {
        value 4;
        description
          "nal oper svm service state install failed";
      }
      enum "nal-oper-svm-service-state-installed" {
        value 5;
        description
          "nal oper svm service state installed";
      }
      enum "nal-oper-svm-service-state-un-install-request-ed" {
        value 6;
        description
          "nal oper svm service state un install request
           ed";
      }
      enum "nal-oper-svm-service-state-un-install-req-failed" {
        value 7;
        description
          "nal oper svm service state un install req
           failed";
      }
      enum "nal-oper-svm-service-state-un-install-failed" {
        value 8;
        description
          "nal oper svm service state un install failed";
      }
      enum "nal-oper-svm-service-state-un-installed" {
        value 9;
        description
          "nal oper svm service state un installed";
      }
      enum "nal-oper-svm-service-state-check-point-ed" {
        value 10;
        description
          "nal oper svm service state check point ed";
      }
      enum "nal-oper-svm-service-state-restored" {
        value 11;
        description
          "nal oper svm service state restored";
      }
      enum "nal-oper-svm-service-state-re-conc-iled" {
        value 12;
        description
          "nal oper svm service state re conc iled";
      }
      enum "nal-oper-svm-service-state-replace-request-ed" {
        value 13;
        description
          "nal oper svm service state replace request ed";
      }
      enum "nal-oper-svm-service-state-replace-req-failed" {
        value 14;
        description
          "nal oper svm service state replace req failed";
      }
      enum "nal-oper-svm-service-state-max" {
        value 15;
        description
          "nal oper svm service state max";
      }
    }
    description
      "NAL SVM Service profile state";
  }

  typedef Nal-trans-client-data {
    type enumeration {
      enum "oper-nal-trans-client-server" {
        value 0;
        description
          "oper nal trans client server";
      }
      enum "oper-nal-trans-client-edm-hand-ler" {
        value 1;
        description
          "oper nal trans client edm hand ler";
      }
      enum "oper-nal-trans-client-nal-internal" {
        value 2;
        description
          "oper nal trans client nal internal";
      }
      enum "oper-nal-trans-client-nal-db-restore" {
        value 3;
        description
          "oper nal trans client nal db restore";
      }
      enum "oper-nal-trans-client-nal-sbydb-restore" {
        value 4;
        description
          "oper nal trans client nal sbydb restore";
      }
      enum "oper-nal-trans-client-dhcpv4" {
        value 5;
        description
          "oper nal trans client dhcpv4";
      }
      enum "oper-nal-trans-client-dhcpv6" {
        value 6;
        description
          "oper nal trans client dhcpv6";
      }
      enum "oper-nal-trans-client-spio" {
        value 7;
        description
          "oper nal trans client spio";
      }
      enum "oper-nal-trans-client-bdx" {
        value 8;
        description
          "oper nal trans client bdx";
      }
      enum "oper-nal-trans-cleint-im-notify" {
        value 9;
        description
          "oper nal trans cleint im notify";
      }
      enum "oper-nal-trans-client-statd" {
        value 10;
        description
          "oper nal trans client statd";
      }
      enum "oper-nal-trans-cleint-rib-notify" {
        value 11;
        description
          "oper nal trans cleint rib notify";
      }
      enum "oper-nal-trans-cleint-vrf-notify" {
        value 12;
        description
          "oper nal trans cleint vrf notify";
      }
      enum "oper-nal-trans-cleint-statsd-notify" {
        value 13;
        description
          "oper nal trans cleint statsd notify";
      }
      enum "oper-nal-trans-client-sub-db-recon" {
        value 14;
        description
          "oper nal trans client sub db recon";
      }
      enum "oper-nal-trans-client-rib-recon" {
        value 15;
        description
          "oper nal trans client rib recon";
      }
      enum "oper-nal-trans-client-im-recon" {
        value 16;
        description
          "oper nal trans client im recon";
      }
      enum "oper-nal-trans-client-ut-test" {
        value 17;
        description
          "oper nal trans client ut test";
      }
      enum "oper-nal-trans-client-max" {
        value 18;
        description
          "oper nal trans client max";
      }
    }
    description
      "nal transaction client type";
  }

  typedef Nal-trans-state {
    type enumeration {
      enum "oper-nal-trans-state-init" {
        value 0;
        description
          "oper nal trans state init";
      }
      enum "oper-nal-trans-state-subscriber" {
        value 1;
        description
          "oper nal trans state subscriber";
      }
      enum "oper-nal-trans-state-subscriber-wait" {
        value 2;
        description
          "oper nal trans state subscriber wait";
      }
      enum "oper-nal-trans-state-invalid" {
        value 3;
        description
          "oper nal trans state invalid";
      }
      enum "oper-nal-trans-state-queued" {
        value 4;
        description
          "oper nal trans state queued";
      }
      enum "oper-nal-trans-state-subscriber-response" {
        value 5;
        description
          "oper nal trans state subscriber response";
      }
      enum "oper-nal-trans-state-check-point-wait" {
        value 6;
        description
          "oper nal trans state check point wait";
      }
      enum "oper-nal-trans-state-end" {
        value 7;
        description
          "oper nal trans state end";
      }
    }
    description
      "Nal transaction subscriber state";
  }

  typedef Nal-intf-oper {
    type enumeration {
      enum "oper-nal-ip-sub-o-per-unknown" {
        value 0;
        description
          "oper nal ip sub o per unknown";
      }
      enum "oper-nal-ip-sub-o-per-create" {
        value 1;
        description
          "oper nal ip sub o per create";
      }
      enum "oper-nal-ip-sub-o-per-update" {
        value 2;
        description
          "oper nal ip sub o per update";
      }
      enum "oper-nal-ip-sub-o-per-rollback" {
        value 3;
        description
          "oper nal ip sub o per rollback";
      }
      enum "oper-nal-ip-sub-o-per-delete" {
        value 4;
        description
          "oper nal ip sub o per delete";
      }
    }
    description
      "Ipsub operation types";
  }

  typedef Svm-reconcile-state {
    type enumeration {
      enum "oper-svm-recon-state-idle" {
        value 0;
        description
          "oper svm recon state idle";
      }
      enum "oper-svm-recon-state-created" {
        value 1;
        description
          "oper svm recon state created";
      }
      enum "oper-svm-recon-state-dt-associated" {
        value 2;
        description
          "oper svm recon state dt associated";
      }
      enum "oper-svm-recon-state-up-installed" {
        value 3;
        description
          "oper svm recon state up installed";
      }
      enum "oper-svm-recon-state-up-associated" {
        value 4;
        description
          "oper svm recon state up associated";
      }
      enum "oper-svm-recon-state-pd-request-ed" {
        value 5;
        description
          "oper svm recon state pd request ed";
      }
      enum "oper-svm-recon-state-max" {
        value 6;
        description
          "oper svm recon state max";
      }
    }
    description
      "SVM reconcile state";
  }

  typedef Nal-spa-oper {
    type enumeration {
      enum "oper-spa-o-per-type-create" {
        value 1;
        description
          "oper spa o per type create";
      }
      enum "oper-spa-o-per-type-modify" {
        value 2;
        description
          "oper spa o per type modify";
      }
      enum "oper-spa-o-per-type-delete" {
        value 3;
        description
          "oper spa o per type delete";
      }
      enum "oper-spa-o-per-type-max" {
        value 4;
        description
          "oper spa o per type max";
      }
    }
    description
      "SPA oper type";
  }

  typedef Svn-sub-state {
    type enumeration {
      enum "oper-nal-svm-state-unknown" {
        value 0;
        description
          "oper nal svm state unknown";
      }
      enum "oper-nal-svm-state-created" {
        value 1;
        description
          "oper nal svm state created";
      }
      enum "oper-nal-svm-state-install-request-ed" {
        value 2;
        description
          "oper nal svm state install request ed";
      }
      enum "oper-nal-svm-state-install-req-failed" {
        value 3;
        description
          "oper nal svm state install req failed";
      }
      enum "oper-nal-svm-state-install-failed" {
        value 4;
        description
          "oper nal svm state install failed";
      }
      enum "oper-nal-svm-state-installed" {
        value 5;
        description
          "oper nal svm state installed";
      }
      enum "oper-nal-svm-state-un-install-request-ed" {
        value 6;
        description
          "oper nal svm state un install request ed";
      }
      enum "oper-nal-svm-state-un-install-req-failed" {
        value 7;
        description
          "oper nal svm state un install req failed";
      }
      enum "oper-nal-svm-state-un-install-failed" {
        value 8;
        description
          "oper nal svm state un install failed";
      }
      enum "oper-nal-svm-state-un-installed" {
        value 9;
        description
          "oper nal svm state un installed";
      }
      enum "oper-nal-svm-state-up-assoc-request-ed" {
        value 10;
        description
          "oper nal svm state up assoc request ed";
      }
      enum "oper-nal-svm-state-up-assoc-req-failed" {
        value 11;
        description
          "oper nal svm state up assoc req failed";
      }
      enum "oper-nal-svm-state-up-assoc-failed" {
        value 12;
        description
          "oper nal svm state up assoc failed";
      }
      enum "oper-nal-svm-state-up-unassoc-request-ed" {
        value 13;
        description
          "oper nal svm state up unassoc request ed";
      }
      enum "oper-nal-svm-state-up-unassoc-req-failed" {
        value 14;
        description
          "oper nal svm state up unassoc req failed";
      }
      enum "oper-nal-svm-state-up-unassoc-failed" {
        value 15;
        description
          "oper nal svm state up unassoc failed";
      }
      enum "oper-nal-svm-state-srv-assoc-request-ed" {
        value 16;
        description
          "oper nal svm state srv assoc request ed";
      }
      enum "oper-nal-svm-state-srv-assoc-req-failed" {
        value 17;
        description
          "oper nal svm state srv assoc req failed";
      }
      enum "oper-nal-svm-state-srv-assoc-failed" {
        value 18;
        description
          "oper nal svm state srv assoc failed";
      }
      enum "oper-nal-svm-state-srv-unassoc-request-ed" {
        value 19;
        description
          "oper nal svm state srv unassoc request ed";
      }
      enum "oper-nal-svm-state-srv-unassoc-req-failed" {
        value 20;
        description
          "oper nal svm state srv unassoc req failed";
      }
      enum "oper-nal-svm-state-srv-unassoc-failed" {
        value 21;
        description
          "oper nal svm state srv unassoc failed";
      }
      enum "oper-nal-svm-state-pd-request-ed" {
        value 22;
        description
          "oper nal svm state pd request ed";
      }
      enum "oper-nal-svm-state-pd-req-failed" {
        value 23;
        description
          "oper nal svm state pd req failed";
      }
      enum "oper-nal-svm-state-rb-pd-request-ed" {
        value 24;
        description
          "oper nal svm state rb pd request ed";
      }
      enum "oper-nal-svm-state-rb-pd-req-failed" {
        value 25;
        description
          "oper nal svm state rb pd req failed";
      }
      enum "oper-nal-svm-state-pd-cfg-generated" {
        value 26;
        description
          "oper nal svm state pd cfg generated";
      }
      enum "oper-nal-svm-state-pd-cfg-gen-failed" {
        value 27;
        description
          "oper nal svm state pd cfg gen failed";
      }
      enum "oper-nal-svm-state-activate-request-ed" {
        value 28;
        description
          "oper nal svm state activate request ed";
      }
      enum "oper-nal-svm-state-activate-req-fail" {
        value 29;
        description
          "oper nal svm state activate req fail";
      }
      enum "oper-nal-svm-state-activate-fail" {
        value 30;
        description
          "oper nal svm state activate fail";
      }
      enum "oper-nal-svm-state-activated" {
        value 31;
        description
          "oper nal svm state activated";
      }
      enum "oper-nal-svm-state-pd-failed" {
        value 32;
        description
          "oper nal svm state pd failed";
      }
      enum "oper-nal-svm-state-pd-complete" {
        value 33;
        description
          "oper nal svm state pd complete";
      }
      enum "oper-nal-svm-state-destroy-request-ed" {
        value 34;
        description
          "oper nal svm state destroy request ed";
      }
      enum "oper-nal-svm-state-destroy-req-failed" {
        value 35;
        description
          "oper nal svm state destroy req failed";
      }
      enum "oper-nal-svm-state-destroy-failed" {
        value 36;
        description
          "oper nal svm state destroy failed";
      }
      enum "oper-nal-svm-state-destroyed" {
        value 37;
        description
          "oper nal svm state destroyed";
      }
      enum "oper-nal-svm-state-rollback" {
        value 38;
        description
          "oper nal svm state rollback";
      }
      enum "oper-nal-svm-state-replace-req-failed" {
        value 39;
        description
          "oper nal svm state replace req failed";
      }
      enum "oper-nal-svm-state-replace-request-ed" {
        value 40;
        description
          "oper nal svm state replace request ed";
      }
      enum "oper-nal-svm-state-max" {
        value 41;
        description
          "oper nal svm state max";
      }
    }
    description
      "SVM state of a subscriber";
  }

  typedef Svm-sub-oper {
    type enumeration {
      enum "oper-nal-svm-sub-o-per-unknown" {
        value 0;
        description
          "oper nal svm sub o per unknown";
      }
      enum "oper-nal-svm-sub-o-per-create" {
        value 1;
        description
          "oper nal svm sub o per create";
      }
      enum "oper-nal-svm-sub-o-per-update" {
        value 2;
        description
          "oper nal svm sub o per update";
      }
      enum "oper-nal-svm-sub-o-per-delete" {
        value 3;
        description
          "oper nal svm sub o per delete";
      }
      enum "oper-nal-svm-sub-o-per-rollback" {
        value 4;
        description
          "oper nal svm sub o per rollback";
      }
      enum "oper-nal-svm-sub-o-per-cleanup" {
        value 5;
        description
          "oper nal svm sub o per cleanup";
      }
      enum "oper-nal-svm-sub-o-per-save" {
        value 6;
        description
          "oper nal svm sub o per save";
      }
      enum "oper-nal-svm-sub-o-per-max" {
        value 7;
        description
          "oper nal svm sub o per max";
      }
    }
    description
      "Operation types from FSM to SVM";
  }

  typedef Nal-main-edm-track-obj-state {
    type enumeration {
      enum "nal-main-edm-track-obj-state-unknown" {
        description
          "nal main edm track obj state unknown";
      }
      enum "nal-main-edm-track-obj-state-up" {
        description
          "nal main edm track obj state up";
      }
      enum "nal-main-edm-track-obj-state-down" {
        description
          "nal main edm track obj state down";
      }
      enum "nal-main-edm-track-obj-state-invalid" {
        description
          "nal main edm track obj state invalid";
      }
    }
    description
      "Tracking object state";
  }

  typedef Nal-main-edm-srg-role {
    type enumeration {
      enum "nal-main-edm-srg-role-none" {
        description
          "SRG role none";
      }
      enum "nal-main-edm-srg-role-active" {
        description
          "SRG role active";
      }
      enum "nal-main-edm-srg-role-standby" {
        description
          "SRG role standby";
      }
      enum "nal-main-edm-srg-role-max" {
        description
          "SRG role max";
      }
    }
    description
      "NAL SRG role";
  }

  typedef Oper-nal-db-subscriber {
    type enumeration {
      enum "invalid" {
        value 0;
        description
          "Invalid";
      }
      enum "ipoe" {
        value 1;
        description
          "IPoE";
      }
      enum "pppoe" {
        value 2;
        description
          "PPPoE";
      }
      enum "lac" {
        value 3;
        description
          "LAC";
      }
      enum "lns" {
        value 4;
        description
          "LNS";
      }
    }
    description
      "Nal Subscriber type";
  }

  typedef In6-addr {
    type inet:ipv6-address;
    description
      "In6 addr";
  }

  typedef Oper-nal-db-subscriber-state {
    type enumeration {
      enum "init" {
        value 0;
        description
          "Invalid";
      }
      enum "connecting" {
        value 1;
        description
          "connecting";
      }
      enum "connected" {
        value 2;
        description
          "connected";
      }
      enum "activated" {
        value 3;
        description
          "activated";
      }
      enum "idle" {
        value 4;
        description
          "idle";
      }
      enum "disconnecting" {
        value 5;
        description
          "disconnecting";
      }
      enum "end" {
        value 6;
        description
          "end";
      }
    }
    description
      "Nal Subscriber State";
  }

  grouping NAL-MAIN-EDM-PARENT-INTF-INITIATOR-DATA {
    description
      "NAL MAIN EDM PARENT INTF INITIATOR DATA";
    leaf is-configured {
      type boolean;
      description
        "Ture if the initiator is configred";
    }
  }

  grouping NAL-MAIN-EDM-PARENT-INTF-INITIATORS {
    description
      "Initiator protocol details";
    container intiator-type {
      description
        "DHCP information";
      uses NAL-MAIN-EDM-PARENT-INTF-INITIATOR-DATA;
    }
  }

  grouping NAL-MAIN-EDM-PARENT-INTF-DATA {
    description
      "Parent interface data";
    container initiators {
      description
        "Configurational state-statistics for each
         initiating protocol enabled on this parent
         interface";
      uses NAL-MAIN-EDM-PARENT-INTF-INITIATORS;
    }
    container event-history {
      description
        "Parent Caps Event History";
      uses NAL-EVENT-HISTORY;
    }
    leaf parent-interface {
      type xr:Interface-name;
      description
        "Ifhandle of parent interface";
    }
    leaf interface-creation-time {
      type string;
      description
        "Interface creation time in Month Date HH:MM:SS
         format";
    }
    leaf age {
      type string;
      description
        "Age in HH:MM:SS format";
    }
    leaf parent-intf-flags {
      type uint32;
      description
        "Access Interface flags";
    }
    leaf nal-ether-encap {
      type yang:hex-string;
      description
        "Ether Encap Attribute";
    }
    leaf effective-bandwidth {
      type uint32;
      description
        "Effective Bandwidth";
    }
    leaf max-bandwidth {
      type uint32;
      description
        "Maximum Bandwidth";
    }
    leaf link-local {
      type inet:ipv6-address;
      description
        "link local address";
    }
    leaf srg-group-name {
      type string {
        length "0..65";
      }
      description
        "SRG group name";
    }
    leaf srg-role {
      type Nal-main-edm-srg-role;
      description
        "SRG role";
    }
    leaf nd-flags {
      type uint32;
      description
        "ND config related flags";
    }
    leaf parent-intf-flags2 {
      type uint32;
      description
        "Access Interface additional flags";
    }
    list counter {
      max-elements "10";
      description
        "Packet statistics";
      uses NAL-MAIN-EDM-COUNTER;
    }
  }

  grouping NAL-MAIN-EDM-OC-ENTRY {
    description
      "NAL owner-channel entries";
    container event-history {
      description
        "Routes event history";
      uses NAL-EVENT-HISTORY;
    }
    leaf afi {
      type uint8;
      description
        "Address family for this route";
    }
    leaf ipv6-prefix {
      type inet:ipv6-address;
      description
        "ipv6 prefix address";
    }
    leaf ipv4-prefix {
      type inet:ipv4-address;
      description
        "ipv4 prefix address";
    }
    leaf prefix-length {
      type uint32;
      description
        "Prefix length";
    }
    leaf secondary-address {
      type inet:ipv4-address;
      description
        "Secondary address";
    }
    leaf state {
      type Nal-main-edm-oc-state;
      description
        "Status";
    }
    leaf vrf-xr {
      type string {
        length "0..33";
      }
      description
        "VRF name";
    }
    leaf if-name {
      type string {
        length "0..80";
      }
      description
        "Interface name";
    }
    leaf tag {
      type uint32;
      description
        "Route tag";
    }
    leaf flags {
      type uint32;
      description
        "Checkpoint flags";
    }
    leaf srg-group-name {
      type string {
        length "0..65";
      }
      description
        "SRG group name";
    }
    leaf route-metric {
      type uint32;
      description
        "Route metric";
    }
  }

  grouping NAL-PLATFORM-FEATURE-CAPABILITIES {
    description
      "NAL feature capabilities";
    leaf ipoe-terminated {
      type boolean;
      description
        "IPoE terminated";
    }
    leaf pppoe-pta {
      type boolean;
      description
        "PPPoE PTA support";
    }
    leaf l2tp-lac {
      type boolean;
      description
        "L2TP LAC support";
    }
    leaf l2tp-lns {
      type boolean;
      description
        "L2TP LNS";
    }
  }

  grouping NAL-MAIN-EDM-PROCESS-INFO {
    description
      "Process information";
    container platform-capabilities {
      description
        "Feature capabilities on the platform";
      uses NAL-PLATFORM-FEATURE-CAPABILITIES;
    }
    container create-peak-timestamp {
      description
        "Timestamp value for max create subscriber in
         transaction";
      uses NAL-TIMESPEC;
    }
    container delete-peak-timestamp {
      description
        "Timestamp value for max delete subscriber in
         transaction";
      uses NAL-TIMESPEC;
    }
    container update-peak-timestamp {
      description
        "Timestamp value for max update subscriber in
         transaction";
      uses NAL-TIMESPEC;
    }
    container total-peak-timestamp {
      description
        "Timestamp value for total peak of subs in
         transaction";
      uses NAL-TIMESPEC;
    }
    container srg-stats-peak-ts {
      description
        "Timestamp when srg_stats_peak is updated";
      uses NAL-TIMESPEC;
    }
    leaf nal-process-restart-flag {
      type boolean;
      description
        "NAL Process's restart flag";
    }
    leaf nalot-connection-sts-flag {
      type boolean;
      description
        "NAL Object-tracking connection up status flag";
    }
    leaf nal-clear-session-timer-flag {
      type boolean;
      description
        "NAL Clear-Session Timer Flag";
    }
    leaf nal-clear-feature-timer-flag {
      type boolean;
      description
        "NAL Clear-Feature Timer Flag";
    }
    leaf disconnect-history-file-logg-enable-flag {
      type boolean;
      description
        "Subscriber Disconnect-history file-logging
         disable feature flag";
    }
    leaf test-client-cfg-enabled-flag {
      type boolean;
      description
        "NAL Test Client config enabled flag";
    }
    leaf nal-pre-init-role {
      type uint8;
      description
        "NAL Process's HA PreInit Role";
    }
    leaf nal-role {
      type uint8;
      description
        "NAL Process's HA Role";
    }
    leaf node-id {
      type uint32;
      description
        "NAL Process's running-instance location node-id";
    }
    leaf nalrsi-ctx-file-descriptor {
      type int32;
      description
        "NAL RSI contex file-desc value";
    }
    leaf nal-pid-misc-flags {
      type uint32;
      description
        "NAL Main context Miscellaneous flags";
    }
    leaf nalsvm-subdb-conn-sts-flag {
      type uint8;
      description
        "NAL Process's SVM context SUBDB
         connection-status flag";
    }
    leaf nalsvmp-done-req-id {
      type uint32;
      description
        "NAL Process's SVM Produce-Done req-id";
    }
    leaf nalsvm-recon-last-upid {
      type uint32;
      description
        "NAL SVM Reconciliation Last UPID";
    }
    leaf nalsvm-reconn-pending-req {
      type uint32;
      description
        "NAL SVM Reconciliation Pending Requests";
    }
    leaf nalsvm-reconn-max-req {
      type uint32;
      description
        "NAL SVM Reconciliation Max Requests";
    }
    leaf nal-sub-ctx-replay-in-progress {
      type uint32;
      description
        "NAL Subscriber context replay in progress";
    }
    leaf nal-subs-ctx-cache-queue-size {
      type uint32;
      description
        "NAL Subscriber context cache queue size";
    }
    leaf nal-subs-ctx-stale-queue-size {
      type uint32;
      description
        "NAL Subscriber context stale queue-size";
    }
    leaf disconnect-queue-size {
      type uint32;
      description
        "NAL Subscriber disconnect queue size";
    }
    leaf nal-msg-local-seq-no {
      type uint32;
      description
        "NAL Message locally generated seq_no";
    }
    leaf nal-msg-seq-no {
      type uint32;
      description
        "NAL message seq_no towards SPA";
    }
    leaf nal-bulk-disc-invoke-time {
      type uint64;
      description
        "NAL Bulk Disconnect-session start time";
    }
    leaf nal-statistics-hold-timeout-val {
      type uint32;
      description
        "NAL Stats Hold-Timeout value";
    }
    leaf nal-statistics-hold-req-count {
      type uint32;
      description
        "NAL Stats Hold-Request Count";
    }
    leaf nal-statistics-hold-req-max {
      type uint32;
      description
        "NAL Stats Hold-Request Max-threshold";
    }
    leaf nal-statistics-stop-req-count {
      type uint32;
      description
        "NAL Stats Stop-Request counter";
    }
    leaf nal-statistics-interim-req-count {
      type uint32;
      description
        "NAL Stats Interim-Request counter";
    }
    leaf nal-clear-session-stats-req-count {
      type uint32;
      description
        "NAL Clear-Session Stats Request counter";
    }
    leaf nal-clear-feature-stats-req-count {
      type uint32;
      description
        "NAL Clear-Feature Stats Request counter";
    }
    leaf nal-stats-processing-flags {
      type uint32;
      description
        "NAL Statistics miscelleaneous flags";
    }
    leaf create-in-progress {
      type uint32;
      description
        "Number of subscriber create in progress";
    }
    leaf delete-in-progress {
      type uint32;
      description
        "Number of subscriber delete in progress";
    }
    leaf update-in-progress {
      type uint32;
      description
        "Number of subscriber update in progress";
    }
    leaf cp-recon-duration {
      type uint32;
      description
        "CP recon duration";
    }
    leaf cp-recon-flags {
      type uint32;
      description
        "CP recon flags";
    }
    leaf cp-replay-reqs-in-progress {
      type uint32;
      description
        "CP replay reqs in progress";
    }
    leaf cp-replay-subs-in-progress {
      type uint32;
      description
        "CP replay subs in progress";
    }
    leaf disconnect-notification-count {
      type uint32;
      description
        "Number of subscriber disconnect notifications in
         queue";
    }
    leaf lcp-timeout-notification-count {
      type uint32;
      description
        "Number of LCP timeout notifications in queue";
    }
    leaf disconnect-notification-drop-count {
      type uint32;
      description
        "Number of subscriber disconnect notifications
         dropped";
    }
    leaf lcp-timeout-notification-drop-count {
      type uint32;
      description
        "Number of LCP timeout notifications dropped";
    }
    leaf notification-timer-expiry-count {
      type uint32;
      description
        "Number of times notification flow control timer
         expired";
    }
    leaf notification-timer-running {
      type boolean;
      description
        "Notification flow control timer running or not";
    }
    leaf stats-message-count {
      type uint32;
      description
        "Number of interim stats messages in queue";
    }
    leaf stats-connection-sts-flag {
      type boolean;
      description
        "Stats connection up status flag";
    }
    leaf l2tpfib-connection-sts-flag {
      type boolean;
      description
        "L2TP FIB connection up status flag";
    }
    leaf l2tp-netio-connection-sts-flag {
      type boolean;
      description
        "L2TP Netio connection up status flag";
    }
    leaf spiopppoe-connection-sts-flag {
      type boolean;
      description
        "SPIO PPPoE connection up status flag";
    }
    leaf spioppp-connection-sts-flag {
      type boolean;
      description
        "SPIO PPP connection up status flag";
    }
    leaf create-peak-val {
      type uint32;
      description
        "peak value for the create subscriber in
         transaction";
    }
    leaf delete-peak-val {
      type uint32;
      description
        "peak value for the delete subscriber in
         transaction";
    }
    leaf update-peak-val {
      type uint32;
      description
        "peak value for the update subscriber in
         transaction";
    }
    leaf total-in-progress {
      type uint32;
      description
        "Total Number of subscriber create/update/delete
         in progress";
    }
    leaf total-in-progress-peak {
      type uint32;
      description
        "Total transaction in progress";
    }
    leaf max-create-in-progress {
      type uint32;
      description
        "Maximum creates allowed in parallel";
    }
    leaf max-update-in-progress {
      type uint32;
      description
        "Maximum updates allowed in parallel";
    }
    leaf max-delete-in-progress {
      type uint32;
      description
        "Maximum deletes allowed in parallel";
    }
    leaf delete-batch-timer {
      type uint32;
      units "millisecond";
      description
        "Delete queue processing timer timeout in
         milliseconds";
    }
    leaf delete-batch-size {
      type uint32;
      description
        "Delete queue outstanding requests size";
    }
    leaf srg-stats-message-count {
      type uint32;
      description
        "Number of SRG stats messages in queue";
    }
    leaf outstanding-stats-message-count {
      type uint32;
      description
        "Number of stats messages for which CP response
         is pending";
    }
    leaf standby-in-flight-requests {
      type uint32;
      description
        "SRG standby SPA request cache in-flight requests
         count";
    }
    leaf standby-max-cache-requests {
      type uint32;
      description
        "Maximum number of in-flight requests allowed
         from SRG standby SPA request cache";
    }
    leaf standby-create-queue-size {
      type uint32;
      description
        "Total number of SPA create requests queued for
         SRG standby group";
    }
    leaf standby-update-queue-size {
      type uint32;
      description
        "Total number of SPA update requests queued for
         SRG standby group";
    }
    leaf srg-stats-max {
      type uint32;
      description
        "Maximum number of in-flight requests allowed for
         SRG stats retrieval";
    }
    leaf srg-stats-in-progress {
      type uint32;
      description
        "Current outstanding SRG stats requests count";
    }
    leaf peak-srg-stats-in-progress {
      type uint32;
      description
        "Peak stats requests count during SRG role change";
    }
    leaf interim-inflight-quota {
      type uint32;
      description
        "Interim Inflight Quota";
    }
    leaf interim-infligh-lwm {
      type uint32;
      description
        "Interim Inflight Low Water Mark";
    }
    leaf srg-stats-request-qsize {
      type uint32;
      description
        "Number of SRG Groups in stats request queue";
    }
    leaf srg-stats-retry-qsize {
      type uint32;
      description
        "Number of stats retry messages in SRG stats
         retry queue";
    }
    leaf lcp-outstanding-ka-expiry-cnt {
      type uint32;
      description
        "Number of outstanding LCP KA timeout
         notifications";
    }
  }

  grouping NAL-MAIN-EDM-COUNTER {
    description
      "NAL MAIN EDM COUNTER";
    leaf counter-name {
      type string {
        length "0..33";
      }
      description
        "Counter name";
    }
    leaf counter {
      type uint32;
      description
        "Counter value";
    }
  }

  grouping NAL-MAIN-EDM-VRF-AFI-INSTANCE {
    description
      "NAL MAIN EDM VRF AFI INSTANCE";
    leaf vrf-address-family {
      type uint8;
      description
        "VRF Table Address-Family";
    }
    leaf vrf-info-table-flag {
      type uint8;
      description
        "VRF Table Flags";
    }
    leaf vrf-table-sync-flag {
      type uint8;
      description
        "buffer complete sent to RIB";
    }
    leaf protocol-id {
      type uint16;
      description
        "Protocol Id";
    }
    leaf vrf-table-id {
      type uint32;
      description
        "VRF Table-Id";
    }
    leaf vrf-pending-routes {
      type uint32;
      description
        "VRF Table Pending-routes";
    }
    leaf ref-count {
      type uint64;
      description
        "No.of interfaces referencing this table";
    }
    leaf max-ref-count {
      type uint64;
      description
        "Max No. of interfaces allowed";
    }
  }

  grouping NAL-MAIN-EDM-VRFTBL-INFO {
    description
      "NAL VRF Table Info bag";
    leaf vrf-name-xr {
      type string {
        length "0..33";
      }
      description
        "Vrf Name";
    }
    list nal-vrf-afi-instance-info {
      description
        "NAL VRF AFI Instance table info";
      uses NAL-MAIN-EDM-VRF-AFI-INSTANCE;
    }
    list counter {
      max-elements "10";
      description
        "Packet statistics";
      uses NAL-MAIN-EDM-COUNTER;
    }
  }

  grouping NAL-SUBSCRIBER-DISCONNECT-HISTORY-DATA {
    description
      "Subscriber disconnect history bag";
    container fail-data {
      description
        "failed data";
      uses NAL-LAST-FAILED-DATA;
    }
    container session-data {
      description
        "subscriber session data info";
      uses NAL-SUBS-INFO;
    }
    container event-history {
      description
        "Subscriber event history";
      uses NAL-EVENT-HISTORY;
    }
    leaf disc-cause {
      type uint32;
      description
        "Disconnect code";
    }
  }

  grouping NAL-AIPC-SERVER-STATS-DATA {
    description
      "aipc server stats";
    leaf service-name {
      type string {
        length "0..256";
      }
      description
        "process Name";
    }
    leaf server-name {
      type string {
        length "0..256";
      }
      description
        "server Name";
    }
    leaf conn-present {
      type boolean;
      description
        "connection status";
    }
    leaf tx-attempt-count {
      type uint32;
      description
        "Tx attempt count";
    }
    leaf tx-count {
      type uint32;
      description
        "tx count";
    }
    leaf rx-count {
      type uint32;
      description
        "Rx count";
    }
    leaf notify-connect-count {
      type uint32;
      description
        "Notify connect count";
    }
    leaf notify-queue-high-count {
      type uint32;
      description
        "Notify Queue High count";
    }
    leaf notify-queue-low-count {
      type uint32;
      description
        "Notify Queue low count";
    }
    leaf notify-queue-full-count {
      type uint32;
      description
        "Notify Queue full count";
    }
    leaf notify-data-waiting-count {
      type uint32;
      description
        "Notify data waiting count";
    }
    leaf notify-error-count {
      type uint32;
      description
        "Notify error count";
    }
    leaf notify-close-count {
      type uint32;
      description
        "Notify close count";
    }
    leaf notify-sendstatus-count {
      type uint32;
      description
        "Notify send status count";
    }
    leaf notify-open-count {
      type uint32;
      description
        "Notify open count";
    }
    leaf pulse-data-waiting-count {
      type uint32;
      description
        "Pulse Data waiting count";
    }
    leaf queue-full {
      type boolean;
      description
        "Queue full";
    }
    leaf queue-full-drop {
      type uint32;
      description
        "Queue full drop";
    }
    leaf queue-ewouldblock-count {
      type uint32;
      description
        "queue would block count";
    }
    leaf outstanding-buffers {
      type uint32;
      description
        "Outstanding Buffers";
    }
    leaf cumulative-overflow-msgs {
      type uint32;
      description
        "cumulative overflow message";
    }
    leaf hwm-overflow-msgs {
      type uint32;
      description
        "Hwm overflow msg";
    }
    leaf get-mtu-failure {
      type uint32;
      description
        "Get Mtu Failure";
    }
    leaf get-buffer-failure {
      type uint32;
      description
        "get Buffer Failure";
    }
    leaf get-buffer-datap-failure {
      type uint32;
      description
        "get Buffer datap Failure";
    }
    leaf conn-failure {
      type uint32;
      description
        "Conn Failure";
    }
    leaf send-failure {
      type uint32;
      description
        "Send Failure";
    }
    leaf receive-failure {
      type uint32;
      description
        "receive Failure";
    }
    leaf release-buffer-failure {
      type uint32;
      description
        "Release Buffer failure";
    }
    leaf overflow-q-flush-count {
      type uint32;
      description
        "Overflow flush count";
    }
    leaf get-buffer-size-failure {
      type uint32;
      description
        "get Buffer size Failure";
    }
    leaf notify-queue-low-count-after-high {
      type uint32;
      description
        "notify queue low count after high";
    }
    leaf last-high-watermark-count-timestamp {
      type uint32;
      description
        "High WaterMark timestamp";
    }
    leaf last-low-watermark-count-timestamp {
      type uint32;
      description
        "Low WaterMark timestamp";
    }
  }

  grouping NAL-MAIN-EDM-OC-SUMMARY {
    description
      "Dynamic routes and OC entries summary";
    leaf v4-oc-entries {
      type uint32;
      description
        "Total V4 OC entries primary/secondary";
    }
    leaf v6-oc-entries {
      type uint32;
      description
        "Total V6 OC entries";
    }
    leaf v4-primary-entries {
      type uint32;
      description
        "Total primary addresses";
    }
    leaf v4-sec-entries {
      type uint32;
      description
        "Total secondary addresses";
    }
    leaf v4-rib-entries {
      type uint32;
      description
        "Total V4 RIB entries";
    }
    leaf v6-rib-entries {
      type uint32;
      description
        "Total V6 RIB entries";
    }
    leaf replayed-oc-entries {
      type uint32;
      description
        "Total entries replayed during last reconcile";
    }
  }

  grouping NAL-SUBSCRIBER-AFI-SUMMARY {
    description
      "Subscriber afi summary data";
    leaf none {
      type uint32;
      description
        "No afi";
    }
    leaf ipv4 {
      type uint32;
      description
        "IPv4 count";
    }
    leaf ipv6 {
      type uint32;
      description
        "IPv6 count";
    }
    leaf dual {
      type uint32;
      description
        "Dual count";
    }
    leaf lac {
      type uint32;
      description
        "LAC count";
    }
    leaf total {
      type uint32;
      description
        "Total";
    }
  }

  grouping NAL-SUBSCRIBER-STATE-SUMMARY {
    description
      "Subscriber state summary data";
    leaf initializing {
      type uint32;
      description
        "Initializing";
    }
    leaf connecting {
      type uint32;
      description
        "Connecting";
    }
    leaf connected {
      type uint32;
      description
        "Connected";
    }
    leaf activated {
      type uint32;
      description
        "Activated";
    }
    leaf idle {
      type uint32;
      description
        "Idle";
    }
    leaf disconnecting {
      type uint32;
      description
        "Disconnecting";
    }
    leaf total {
      type uint32;
      description
        "Total";
    }
  }

  grouping NAL-SUBSCRIBER-SUMMARY {
    description
      "Subscriber summary data";
    container ipoe-state-summary {
      description
        "IPoE State Summary";
      uses NAL-SUBSCRIBER-STATE-SUMMARY;
    }
    container pppoe-state-summary {
      description
        "PPPoE State Summary";
      uses NAL-SUBSCRIBER-STATE-SUMMARY;
    }
    container lac-state-summary {
      description
        "LAC State Summary";
      uses NAL-SUBSCRIBER-STATE-SUMMARY;
    }
    container ipoe-afi-summary {
      description
        "IPoE AFI Summary";
      uses NAL-SUBSCRIBER-AFI-SUMMARY;
    }
    container pppoe-afi-summary {
      description
        "PPPoE AFI Summary";
      uses NAL-SUBSCRIBER-AFI-SUMMARY;
    }
    container lac-afi-summary {
      description
        "LAC AFI Summary";
      uses NAL-SUBSCRIBER-AFI-SUMMARY;
    }
    container lns-state-summary {
      description
        "LNS State Summary";
      uses NAL-SUBSCRIBER-STATE-SUMMARY;
    }
    container lns-afi-summary {
      description
        "LNS AFI Summary";
      uses NAL-SUBSCRIBER-AFI-SUMMARY;
    }
  }

  grouping NAL-MAIN-EDM-CP-CONN-STS-INFO {
    description
      "NAL User & Control-plane connection status
       information";
    leaf nal-transport-user-plane-src-conn-flag {
      type boolean;
      description
        "True if NAL Transport user-plane source
         connection address is configured";
    }
    leaf nalcp-svr-connect-sts {
      type Nal-cp-connection-status;
      description
        "NAL control-plane connection-status value";
      xr:event-telemetry "Subscribe Telemetry Event";
    }
    leaf nalcp-svr-connect-sts-time {
      type uint32;
      description
        "NAL control-plane connection-status time stamp";
    }
    leaf nalcp-svr-connect-sts-prev {
      type Nal-cp-connection-status;
      description
        "NAL control-plane prev connection-status value";
    }
    leaf nalcp-svr-connect-sts-time-prev {
      type uint32;
      description
        "NAL control-plane prev connection-status time
         stamp";
    }
    leaf cp-assoc-status {
      type Nal-cp-assoc-status;
      description
        "Control plane association status";
    }
    leaf cp-assoc-status-time {
      type uint32;
      description
        "Control plane association status time stamp";
    }
    leaf nal-transport-user-plane-source-conn-addr-family {
      type uint8;
      description
        "NAL Transport user-plane source server
         connection address-family";
    }
    leaf nal-transport-up-source-ipv4-address {
      type inet:ipv4-address;
      description
        "NAL Transport user-plane server connection IPv4
         address";
    }
    leaf nal-transport-up-source-ipv6-address {
      type inet:ipv6-address;
      description
        "NAL Transport user-plane server connection IPv6
         address";
    }
    leaf nal-transport-up-src-loop-back-if-name {
      type string {
        length "0..80";
      }
      description
        "NAL Transport user-plane server loopback
         interface-name";
    }
    leaf nal-transport-up-source-gtpu-port {
      type uint32;
      description
        "NAL Transport user-plane server connection GTPU
         port-number";
    }
    leaf nal-transport-up-source-pfcp-port {
      type uint32;
      description
        "NAL Transport user-plane server connection PFCP
         port-number";
    }
    leaf nal-transport-up-source-vrf-name {
      type string {
        length "0..33";
      }
      description
        "NAL Transport user-plane server connection
         VRF-Name";
    }
    leaf nal-transport-control-plane-primary-srv-addr-family {
      type uint8;
      description
        "NAL transport control-plane primary-server
         connection address-family";
    }
    leaf nal-transport-cp-primary-ipv4-address {
      type inet:ipv4-address;
      description
        "NAL Transport C-plane primary-server connection
         IPv4 address";
    }
    leaf nal-transport-cp-primary-ipv6-address {
      type inet:ipv6-address;
      description
        "NAL Transport C-plane primary-server connection
         IPv6 address";
    }
    leaf nal-transport-cp-server-gtpu-port {
      type uint32;
      description
        "NAL Transport C-plane server's GTPU port-number";
    }
    leaf nal-transport-cp-server-pfcp-port {
      type uint32;
      description
        "NAL Transport C-plane server's PFCP port-number";
    }
    leaf retry-count {
      type uint16;
      description
        "CP association request retry count";
    }
    leaf tr459-enabled {
      type boolean;
      description
        "Flag indicating TR459 is enabled";
    }
    leaf gtpu-bind-rc {
      type string;
      description
        "Error code for GTPu socket bind";
    }
    leaf pfcp-bind-rc {
      type string;
      description
        "Error code for PFCP socket bind";
    }
  }

  grouping NAL-SIR-EVENT-INFO {
    description
      "SIR event notification received by NAL";
    leaf process-ready {
      type boolean;
      description
        "Current value of process ready";
    }
    leaf resync-pending-flags {
      type uint32;
      description
        "Current value of resync_pending flags";
    }
    leaf sir-event {
      type uint32;
      description
        "SIR event received";
    }
    leaf afi {
      type uint32;
      description
        "AFI type received in SIR event";
    }
  }

  grouping NAL-SIR-PROC-READY-INFO {
    description
      "NAL SIR PROC READY INFO";
    leaf process-ready {
      type boolean;
      description
        "Current value of process ready";
    }
    leaf resync-pending-flags {
      type uint32;
      description
        "Current value of resync_pending flags";
    }
    leaf sir-ready {
      type boolean;
      description
        "Current SIR status";
    }
    leaf sir-event {
      type uint32;
      description
        "SIR event notified";
    }
  }

  grouping NAL-SIR-EVENT-DATA {
    description
      "Union of data in SIR history";
    container proc-ready {
      when "../type = 'nal-sir-history-event-proc-ready'" {
        description
          "../Type = 'NAL_SIR_HISTORY_EVENT_PROC_READY'";
      }
      description
        "For event type NAL_SIR_HISTORY_EVENT_PROC_READY";
      uses NAL-SIR-PROC-READY-INFO;
    }
    container sir-event {
      when "../type = 'nal-sir-history-event-sir-state'" {
        description
          "../Type = 'NAL_SIR_HISTORY_EVENT_SIR_STATE'";
      }
      description
        "For event type NAL_SIR_HISTORY_EVENT_SIR_STATE";
      uses NAL-SIR-EVENT-INFO;
    }
    leaf type {
      type Nal-sir-history-event;
      description
        "Type";
    }
  }

  grouping NAL-SIR-HISTORY-NODE {
    description
      "SIR history node";
    container timestamp {
      description
        "Timestamp when the event occured";
      uses NAL-TIMESPEC;
    }
    container data {
      description
        "Data associated with each event type";
      uses NAL-SIR-EVENT-DATA;
    }
  }

  grouping NAL-MAIN-EDM-PROCESS-READINESS {
    description
      "Process readiness data";
    leaf resync-pending-flags {
      type uint32;
      description
        "Resync operations pending for NAL process";
    }
    leaf sir-ready {
      type boolean;
      description
        "Status of SIR readiness";
      xr:event-telemetry "Subscribe Telemetry Event";
    }
    leaf process-ready {
      type boolean;
      description
        "Process ready flag";
      xr:event-telemetry "Subscribe Telemetry Event";
    }
    leaf trans-pending {
      type boolean;
      description
        "Transactions pending";
    }
    list sir-history {
      description
        "SIR events history";
      uses NAL-SIR-HISTORY-NODE;
    }
  }

  grouping NAL-MAIN-EDM-SRG-GROUP-ACCESS-INTF {
    description
      "NAL MAIN EDM SRG GROUP ACCESS INTF";
    leaf interface-name {
      type string;
      description
        "Access interface name";
    }
  }

  grouping NAL-MAIN-EDM-SRG-GROUP-INFO {
    description
      "SRG group information";
    container access-tracking-object {
      description
        "SRG group access tracking object";
      uses NAL-MAIN-EDM-SRG-TRACK-OBJ;
    }
    container core-tracking-object {
      description
        "SRG group core tracking object";
      uses NAL-MAIN-EDM-SRG-TRACK-OBJ;
    }
    container group-update-timestamp {
      description
        "Group status update timestamp";
      uses NAL-TIMESPEC;
    }
    container srg-group-event-history {
      description
        "SRG Group events";
      uses NAL-EVENT-HISTORY;
    }
    container max-active-swo-stats-timespec {
      description
        "Max active switchover stats timespec";
      uses NAL-TIMESPEC;
    }
    container max-standby-swo-stats-timespec {
      description
        "Max standby switchover stats timespec";
      uses NAL-TIMESPEC;
    }
    leaf srg-group-name-xr {
      type string;
      description
        "SRG group name";
    }
    leaf virtual-mac-address {
      type yang:mac-address;
      description
        "Virtual Mac address";
    }
    leaf stats-state {
      type Nal-main-edm-srg-group-stats-state;
      description
        "Stats collection state";
    }
    leaf group-state {
      type Nal-main-edm-srg-group-state;
      description
        "SRG group state";
    }
    leaf srg-role {
      type Nal-main-edm-srg-role;
      description
        "SRG role";
    }
    leaf route-export-standby {
      type boolean;
      description
        "Route export on standby flag";
    }
    leaf fast-switchover-enable {
      type boolean;
      description
        "Fast switchover enable flag";
    }
    leaf srg-vrf-name {
      type string;
      description
        "SRG backup vrf name";
    }
    leaf admin-state {
      type Nal-main-edm-srg-group-admin-state;
      description
        "SRG group admin state";
    }
    leaf srg-id {
      type uint32;
      description
        "Subscriber redundancy group id";
    }
    leaf v4-table-id {
      type uint32;
      description
        "V4 table id for SRG VRF";
    }
    leaf v6-table-id {
      type uint32;
      description
        "V6 table id for SRG VRF";
    }
    leaf v4-proto-id {
      type uint32;
      description
        "V4 proto id for SRG VRF";
    }
    leaf v6-proto-id {
      type uint32;
      description
        "V6 proto id for SRG VRF";
    }
    leaf damping-timer-interval {
      type uint32;
      description
        "Damping timer interval";
    }
    leaf subscriber-count {
      type uint32;
      description
        "Subscriber count";
    }
    leaf im-total-errors {
      type uint32;
      description
        "Errored routes";
    }
    leaf rib-total-entries {
      type uint32;
      description
        "Total routes synced";
    }
    leaf rib-pending {
      type uint32;
      description
        "Pending routes";
    }
    leaf rib-total-errors {
      type uint32;
      description
        "Errored routes";
    }
    leaf im-terminate-counters {
      type uint32;
      description
        "IM terminate counters";
    }
    leaf rib-terminate-counters {
      type uint32;
      description
        "RIB terminate counters";
    }
    leaf stats-terminate-counters {
      type uint32;
      description
        "STATS terminate counters";
    }
    leaf ipv4-route-count {
      type uint32;
      description
        "IPV4 route count";
    }
    leaf ipv6-route-count {
      type uint32;
      description
        "IPV6 route count";
    }
    leaf flags {
      type uint32;
      description
        "SRG group flags";
    }
    leaf chkpt-flags {
      type uint32;
      description
        "Checkpoint flags";
    }
    leaf srg-fsm-state {
      type Nal-main-edm-srg-trans-state;
      description
        "SRG FSM transaction state";
    }
    leaf update-request-state {
      type Nal-main-edm-srg-group-upd-req-state;
      description
        "Role update request state";
    }
    leaf role-change-rc {
      type uint32;
      description
        "Status indicating if group role update can be
         handled";
    }
    leaf sub-disc-pending {
      type uint32;
      description
        "Subscriber disconnect response pending count
         from CP";
    }
    leaf route-tag {
      type uint32;
      description
        "Route tag configured for this group";
    }
    leaf subs-in-transaction {
      type uint32;
      description
        "Count of subscribers undergoing transactions";
    }
    leaf subs-in-af-down-queue {
      type uint32;
      description
        "Count of queued AF down transactions";
    }
    leaf subs-in-disconnect-queue {
      type uint32;
      description
        "Count of subscribers in disconnect queue";
    }
    leaf cp-recon-duration {
      type uint32;
      units "second";
      description
        "Control plane reconciliation duration in seconds";
    }
    leaf cp-recon-flags {
      type uint32;
      description
        "Control plane reconciliation flags";
    }
    leaf cp-replay-reqs-in-progress {
      type uint32;
      description
        "Control plane replay requests in progress";
    }
    leaf cp-replay-subs-in-progress {
      type uint32;
      description
        "Control plane replay subscribers in progress";
    }
    leaf active-grp-swo-stats-time {
      type uint32;
      description
        "Active group switchover stats time";
    }
    leaf standby-grp-swo-stats-time {
      type uint32;
      description
        "Standby group switchover stats time";
    }
    leaf max-active-grp-swo-stats-time {
      type uint32;
      description
        "Max active group switchover stats time";
    }
    leaf max-standby-grp-swo-stats-time {
      type uint32;
      description
        "Max standby group switchover stats time";
    }
    list access-interface {
      max-elements "10";
      description
        "SRG group access interface list";
      uses NAL-MAIN-EDM-SRG-GROUP-ACCESS-INTF;
    }
  }

  grouping NAL-MAIN-EDM-CHUNK-DATA {
    description
      "NAL MAIN EDM CHUNK DATA";
    leaf chunk-name {
      type string;
      description
        "Chunk Name";
    }
    leaf chunk-id {
      type uint32;
      description
        "Chunk Id";
    }
    leaf chunk-total-alloc {
      type uint32;
      description
        "Total number of chunk malloc done";
    }
    leaf chunk-total-free {
      type uint32;
      description
        "Total number of chunk free done";
    }
    leaf chunk-in-use {
      type uint32;
      description
        "total number of chunk blocks in use";
    }
    leaf block-size {
      type uint32;
      description
        "Per block size";
    }
  }

  grouping NAL-MAIN-EDM-CHUNK-STATS {
    description
      "NAL MAIN EDM CHUNK STATS";
    list chunk-stat {
      description
        "Chunk Memory statistics";
      uses NAL-MAIN-EDM-CHUNK-DATA;
    }
  }

  grouping NAL-SUBSCRIBER-SESSION-DATA {
    description
      "NAL subscriber detail data information";
    container sub-info {
      description
        "subscriber session data info";
      uses NAL-SUBS-INFO;
    }
  }

  grouping NAL-SUBSCRIBER-DISCONNECT-HISTORY-LAST-SUMMARY-DATA {
    description
      "Subscriber disconnect history last summary Bag";
    leaf sub-if-name {
      type string {
        length "0..80";
      }
      description
        "Interface Name";
    }
    leaf sub-disc-time {
      type uint32;
      description
        "Subscriber Disconnect Time ";
    }
    leaf disconnect-errorcode {
      type uint32;
      description
        "error code";
    }
  }

  grouping NAL-MAIN-EDM-EVENTS {
    description
      "NAL Main process init information";
    container event-history {
      description
        "Main process boot up events";
      uses NAL-EVENT-HISTORY;
    }
    container im-event-history {
      description
        "IM module events";
      uses NAL-EVENT-HISTORY;
    }
    container svm-event-history {
      description
        "SVM module events";
      uses NAL-EVENT-HISTORY;
    }
    container rib-event-history {
      description
        "RIB module events";
      uses NAL-EVENT-HISTORY;
    }
    container cp-event-history {
      description
        "CP module events";
      uses NAL-EVENT-HISTORY;
    }
    container config-event-history {
      description
        "Config module events";
      uses NAL-EVENT-HISTORY;
    }
  }

  grouping NAL-SUBSCRIBER-DISCONNECT-HISTORY-UNIQUE-DATA {
    description
      "Subscriber unique disconnect history Bag";
    leaf disconnect-unique-session-count {
      type uint32;
      description
        "Number of sessions disconnected with this error
         code";
    }
    leaf disconnect-errorcode {
      type uint32;
      description
        "error code";
    }
    leaf sub-if-name {
      type string {
        length "0..80";
      }
      description
        "Interface Name";
    }
    leaf sub-disc-time {
      type uint32;
      description
        "Subscriber Disconnect Time ";
    }
    leaf disc-reason {
      type string {
        length "0..64";
      }
      description
        "Disconnect reason";
    }
  }

  grouping NAL-SERVICE-PROFILE-DATA {
    description
      "NAL service profile information";
    leaf service-name {
      type string {
        length "0..65";
      }
      description
        "Name of the service";
    }
    leaf service-id {
      type uint32;
      description
        "Service id assigned by SUBDB";
    }
    leaf use-count {
      type uint32;
      description
        "Number of subscribers using this profile";
    }
    leaf state {
      type Svm-service-state;
      description
        "State of the service";
    }
    leaf fail-err {
      type uint32;
      description
        "Installation failure rc";
    }
    leaf stale-timer-remaining {
      type uint32;
      description
        "stale timer remaining";
    }
    leaf assoc-in-progress {
      type uint32;
      description
        "No of subscribers need to use this profile";
    }
    list wait-upi-dqueue {
      description
        "List of UPIDs waiting for this service";
      leaf entry {
        type uint32;
        description
          "List of UPIDs waiting for this service";
      }
    }
  }

  grouping IPSUB-BASE-INIT {
    description
      "ipsub base init data";
    leaf type {
      type uint8;
      description
        "Init data type";
    }
    leaf version {
      type uint8;
      description
        "Init data version";
    }
    leaf length {
      type uint16;
      description
        "Init data length";
    }
  }

  grouping IPSUB-INTF-INIT-TYPE {
    description
      "Subscriber intf init data";
    container base {
      description
        "base";
      uses IPSUB-BASE-INIT;
    }
    leaf subscriber-mac {
      type yang:mac-address;
      description
        "MAC address";
    }
    leaf vlan-tag-count {
      type uint16;
      description
        "Vlan tag count";
    }
    leaf vrf-table-id {
      type uint32;
      description
        "Vrf table id ";
    }
    leaf v6-vrf-table-id {
      type uint32;
      description
        "Ipv6 Vrf table id ";
    }
    leaf up-link-gre-key {
      type uint32;
      description
        "Up link gre key";
    }
    leaf down-link-gre-key {
      type uint32;
      description
        "Down link gre key";
    }
    leaf subscriber-gw-mac {
      type yang:mac-address;
      description
        "Gateway MAC address";
    }
    leaf sub-attr-bits {
      type uint8;
      description
        "Subscriber attr bits";
    }
    leaf sub-info-bits {
      type uint8;
      description
        "Subscriber info bits";
    }
    leaf subscriber-ipv4 {
      type uint32;
      description
        "Subscriber IPv4";
    }
    leaf nexthop-ipv4 {
      type uint32;
      description
        "next hop  IPv4 address";
    }
    leaf subscriber-ipv6 {
      type inet:ipv6-address;
      description
        "Subscriber Ipv6 address";
    }
    leaf subscriber-ipv6-prefix {
      type inet:ipv6-address;
      description
        "Subscriber Ipv6 address";
    }
    leaf nexthop-ipv6 {
      type inet:ipv6-address;
      description
        "Nexthop Ipv6 address";
    }
    leaf v6-len {
      type uint8;
      description
        "V6 len";
    }
    leaf v6-prefix-len {
      type uint8;
      description
        "V6 prefix len";
    }
    leaf template-ifh {
      type uint32;
      description
        "Template interface handle";
    }
    leaf ipv4-mtu {
      type uint16;
      description
        "Ipv4 MTU";
    }
    leaf ipv6-mtu {
      type uint16;
      description
        "Ipv6 MTU";
    }
    leaf odns-deviceid-higher {
      type uint32;
      description
        "ODNS device id highter";
    }
    leaf odns-deviceid-lower {
      type uint32;
      description
        "ODNS device id Lower";
    }
    list vlan-stack {
      max-elements "2";
      description
        "vlan stack type";
      uses DOT1Q-TAG-DATA-TYPE;
    }
  }

  grouping NAL-TRANS-CONTEXT-DATA {
    description
      "Nal transaction context";
    leaf state {
      type Nal-trans-state;
      description
        "Subscriber transactio state";
    }
    leaf client-type {
      type Nal-trans-client-data;
      description
        "Client type indicate who is triggert this
         transction";
    }
    leaf trans-id {
      type uint32;
      description
        "Transaction ID";
    }
    leaf disconnect-ack {
      type uint32;
      description
        "Disconnect Ack";
    }
    leaf module-err {
      type uint32;
      description
        "Error generated by sub module";
    }
    leaf module-interaction-mask {
      type uint64;
      description
        "Flag to indicate which sub-module interactions
         are in progress";
    }
    leaf rollback-module-mask {
      type uint64;
      description
        "Flag to indicate which sub-module rollback needs
         to be invoked";
    }
    leaf pending-cb-bitmask {
      type uint64;
      description
        "Flag indicating pending callbacks for this
         transaction";
    }
    leaf src-port-id {
      type uint16;
      description
        "Source port of txn_id";
    }
  }

  grouping NAL-TRANS-SUB-CONTEXT-DATA {
    description
      "Subscriber transaction context";
    container trans-context {
      description
        "trans context";
      uses NAL-TRANS-CONTEXT-DATA;
    }
  }

  grouping NAL-SRG-INFLIGHT-DATA {
    description
      "Srg inflight data";
    leaf flags {
      type uint32;
      description
        "SRG inflight flags";
    }
    leaf v4-pending-route-response {
      type uint8;
      description
        "SRG V4 pending route response";
    }
    leaf v6-pending-route-response {
      type uint8;
      description
        "SRG V6 pending route response";
    }
    leaf rib-errors {
      type uint8;
      description
        "SRG RIB errors";
    }
    leaf stats-errors {
      type uint8;
      description
        "SRG STATS errors";
    }
  }

  grouping NAL-IPSUB-INFLIGHT-DATA {
    description
      "Nal ipsub inflight data";
    leaf opearation {
      type Nal-intf-oper;
      description
        "Operation in progress";
    }
    leaf flags {
      type uint64;
      description
        "Flags to represent pending activities";
    }
    leaf fail-rc {
      type uint32;
      description
        "Backup of update error, internal rollback in
         progresss";
    }
  }

  grouping SVM-INFLIGHT-DATA {
    description
      "SVM inflight data";
    leaf service-name {
      type string {
        length "0..65";
      }
      description
        "Name of the service";
    }
    leaf service-id {
      type uint32;
      description
        "Service id assigned by SUBDB";
    }
    leaf operation {
      type Nal-spa-oper;
      description
        "Operation to be performed";
    }
    leaf service-flags {
      type uint32;
      description
        "Service flags";
    }
    leaf params-list {
      type yang:hex-string;
      description
        "Attribute list of service params";
    }
    leaf feature-id {
      type uint32;
      description
        "Feature ID";
    }
  }

  grouping NAL-SVM-INFLIGHT-DATA {
    description
      "Nal SVM inflight data";
    leaf opearation {
      type Svm-sub-oper;
      description
        "Operation in progress";
    }
    leaf state {
      type Svn-sub-state;
      description
        "State of the subscriber SVM data";
    }
    leaf fail-rc {
      type uint32;
      description
        "Fail rc";
    }
    leaf up-list {
      type yang:hex-string;
      description
        "User profile attribute list";
    }
    leaf remove-list {
      type yang:hex-string;
      description
        "User profile attribute remove list";
    }
    leaf service-index {
      type uint32;
      description
        "Service that is currently under process";
    }
    leaf subdb-pd-req-id {
      type uint32;
      description
        "SUBDB produce done req id";
    }
    leaf reconcile-state {
      type Svm-reconcile-state;
      description
        "Reconcilitation state";
    }
    list service {
      description
        "Service list array";
      uses SVM-INFLIGHT-DATA;
    }
  }

  grouping DOT1Q-TAG-DATA-TYPE {
    description
      "dot1q tag type";
    leaf etype {
      type uint16;
      description
        "etype";
    }
    leaf ucv {
      type uint16;
      description
        "ucv";
    }
  }

  grouping NAL-SUB-INTF-DATA {
    description
      "subscriber interface info";
    leaf vlan-tag-count {
      type uint16;
      description
        "Vlan tag count";
    }
    leaf sub-attr-bits {
      type uint8;
      description
        "Subscriber attr bits";
    }
    leaf flags {
      type uint64;
      description
        "flags bits";
    }
    leaf vrf-id {
      type uint32;
      description
        "vrf ID";
    }
    leaf v4-table-id {
      type uint32;
      description
        "V4 table id";
    }
    leaf v6-table-id {
      type uint32;
      description
        "V6 table id";
    }
    list vlan-stack {
      max-elements "2";
      description
        "vlan stack type";
      uses DOT1Q-TAG-DATA-TYPE;
    }
  }

  grouping NAL-LAST-FAILED-DATA {
    description
      "NAL subscriber last failed transaction data";
    leaf data {
      type string {
        length "0..65";
      }
      description
        "Failed data";
    }
    leaf msg-txn-id {
      type uint32;
      description
        "Message Txn ID";
    }
    leaf sess-txn-id {
      type uint32;
      description
        "Session Txn ID";
    }
    leaf feature-mask {
      type uint32;
      description
        "Feature Mask";
    }
    leaf svm-state {
      type uint32;
      description
        "SVM state";
    }
    leaf ip-sub-flags {
      type uint64;
      description
        "IPSUB flags";
    }
    leaf pending-callback {
      type uint64;
      description
        "Pending Callback";
    }
    leaf failure-reason {
      type uint32;
      description
        "Failure Reason";
    }
    leaf failure-timestamp {
      type uint32;
      description
        "Failure Timestamp";
    }
    leaf source-port-id {
      type uint16;
      description
        "Source port from which msg_txn_id was generated";
    }
  }

  grouping NAL-SUBSCRIBER-DEACTIVATED-SERVICE {
    description
      "NAL subscriber deactivated service information";
    leaf service-name {
      type string {
        length "0..65";
      }
      description
        "Name of the service";
    }
    leaf deactivation-time {
      type uint32;
      description
        "service deactivation Time";
    }
    leaf bytes-in {
      type uint32;
      units "byte";
      description
        "Bytes in";
    }
    leaf bytes-out {
      type uint32;
      units "byte";
      description
        "Bytes out";
    }
    leaf bytes-ingiga {
      type uint32;
      units "byte";
      description
        "In Bytes in Giga";
    }
    leaf bytes-out-giga {
      type uint32;
      units "byte";
      description
        "Bytes out in Giga";
    }
    leaf pkt-in {
      type uint32;
      description
        "Packets in";
    }
    leaf pkt-out {
      type uint32;
      description
        "Packets out";
    }
  }

  grouping NAL-SUBSCRIBER-SESSION-DATA-INTERNAL {
    description
      "Subscriber context data";
    container session-data {
      description
        "subscriber session data info";
      uses NAL-SUBS-INFO;
    }
    container sub-intf {
      description
        "sub intf";
      uses NAL-SUB-INTF-DATA;
    }
    container svm-inflight {
      description
        "svm inflight";
      uses NAL-SVM-INFLIGHT-DATA;
    }
    container ipsub-inflight {
      description
        "ipsub inflight";
      uses NAL-IPSUB-INFLIGHT-DATA;
    }
    container srg-inflight {
      description
        "srg inflight";
      uses NAL-SRG-INFLIGHT-DATA;
    }
    container trans-sub-context {
      description
        "trans sub context";
      uses NAL-TRANS-SUB-CONTEXT-DATA;
    }
    container last-init-data {
      description
        "last init data";
      uses IPSUB-INTF-INIT-TYPE;
    }
    leaf subscriber-flags {
      type uint32;
      description
        "Subscriber flags";
    }
    leaf ha-flags {
      type uint32;
      description
        "Subscriber flags";
    }
    leaf last-transaction-result {
      type uint32;
      description
        "Last Transaction Result";
    }
    leaf hold-stats-error {
      type uint32;
      description
        "hold stats status";
    }
    leaf clear-stats-error {
      type uint32;
      description
        "clear stats status";
    }
    leaf packets-in {
      type uint32;
      description
        "No of packets In";
    }
    leaf packets-out {
      type uint32;
      description
        "No of packets Out";
    }
    leaf ipv4-packets-in {
      type uint32;
      description
        "No of IPv4 packets In";
    }
    leaf ipv4-packets-out {
      type uint32;
      description
        "No of IPv4 packets Out";
    }
    leaf ipv4-bytes-in {
      type uint32;
      description
        "IPv4 Bytes in";
    }
    leaf ipv4-bytes-out {
      type uint32;
      description
        "IPv4 Bytes out";
    }
    leaf ipv4-bytes-in-giga {
      type uint32;
      description
        "IPv4 Bytes in Giga";
    }
    leaf ipv4-bytes-out-giga {
      type uint32;
      description
        "IPv4 Bytes out in Giga";
    }
    leaf ipv6-packets-in {
      type uint32;
      description
        "No of IPv6 packets In";
    }
    leaf ipv6-packets-out {
      type uint32;
      description
        "No of IPv6 packets Out";
    }
    leaf ipv6-bytes-in {
      type uint32;
      description
        "IPv6 Bytes in";
    }
    leaf ipv6-bytes-out {
      type uint32;
      description
        "IPv6 Bytes out";
    }
    leaf ipv6-bytes-in-giga {
      type uint32;
      description
        "IPv6 Bytes in Giga";
    }
    leaf ipv6-bytes-out-giga {
      type uint32;
      description
        "IPv6 Bytes out in Giga";
    }
    leaf transaction-id {
      type uint32;
      description
        "Subscriber transaction id";
    }
    leaf stale-feature-id-info {
      type uint32;
      description
        "subscriber stale feature id info";
    }
    leaf sus-dconnect-time {
      type uint32;
      description
        "Subscriber disconnect Time";
    }
    leaf obj-hdl {
      type uint64;
      description
        "objext handle";
    }
    leaf spi-oattched {
      type boolean;
      description
        "Has SPIO attached";
    }
    leaf old-loopback-name {
      type string {
        length "0..81";
      }
      description
        "Old Loopback Name";
    }
    leaf old-subscriber-ipv4gw {
      type uint32;
      description
        "Old Subscriber IPv4 Gateway";
    }
    list deactivated-service {
      description
        "last deactivated services";
      uses NAL-SUBSCRIBER-DEACTIVATED-SERVICE;
    }
    list last-fail {
      description
        "last failed transaction data";
      uses NAL-LAST-FAILED-DATA;
    }
  }

  grouping NAL-MAIN-EDM-UTILS-API-STATS {
    description
      "NAL MAIN EDM UTILS API STATS";
    container api-ts-fail {
      description
        "API failure timestamp";
      uses NAL-TIMESPEC;
    }
    leaf api-name {
      type string {
        length "0..65";
      }
      description
        "API name";
    }
    leaf api-success-count {
      type uint32;
      description
        "API success count";
    }
    leaf api-failure-count {
      type uint32;
      description
        "API failure count";
    }
    leaf api-max-time {
      type uint32;
      description
        "API last max success/failure time";
    }
    leaf upid {
      type uint32;
      description
        "User-plane ID of maximum timestamp";
    }
  }

  grouping NAL-MAIN-EDM-API-STATS {
    description
      "NAL api statistics";
    list api-stat {
      description
        "API statistics";
      uses NAL-MAIN-EDM-UTILS-API-STATS;
    }
  }

  grouping NAL-OPER-FADB-RECORD-DATA {
    description
      "NAL OPER FADB RECORD DATA";
    leaf feature-id {
      type uint32;
      description
        "Subscriber Feature-Id";
    }
    leaf upid {
      type uint32;
      description
        "User-plane ID";
    }
    leaf service-id {
      type uint32;
      description
        "Subscriber Service-Id";
    }
    leaf interim-fail-count {
      type uint32;
      description
        "Interim Fail Count";
    }
    leaf stale-timestamp {
      type uint32;
      description
        "Stale timestamp";
    }
    leaf hold-rc {
      type uint32;
      description
        "Hold RC";
    }
    leaf interim-error {
      type uint32;
      description
        "Interim Error";
    }
  }

  grouping NAL-MAIN-EDM-SRG-TRACK-OBJ {
    description
      "NAL MAIN EDM SRG TRACK OBJ";
    container last-update-timestamp {
      description
        "Last update timestamp";
      uses NAL-TIMESPEC;
    }
    leaf tracking-objectname {
      type string;
      description
        "Tracking object name";
    }
    leaf tracking-object-state {
      type Nal-main-edm-track-obj-state;
      description
        "Tracking object state";
    }
  }

  grouping NAL-MAIN-EDM-SRG-GROUP-SUMMARY {
    description
      "SRG group summary";
    container access-tracking-object {
      description
        "SRG group access tracking object";
      uses NAL-MAIN-EDM-SRG-TRACK-OBJ;
    }
    container core-tracking-object {
      description
        "SRG group core tracking object";
      uses NAL-MAIN-EDM-SRG-TRACK-OBJ;
    }
    leaf srg-group-name-xr {
      type string {
        length "0..65";
      }
      description
        "SRG group name";
    }
    leaf srg-role {
      type Nal-main-edm-srg-role;
      description
        "SRG role";
    }
    leaf subscriber-count {
      type uint32;
      description
        "Subscriber count";
    }
    leaf ipv4-route-count {
      type uint32;
      description
        "IPV4 route count";
    }
    leaf ipv6-route-count {
      type uint32;
      description
        "IPV6 route count";
    }
  }

  grouping NAL-TIMESPEC {
    description
      "Structure to replicate timespec";
    leaf tv-sec {
      type uint32;
      description
        "Time in sec";
    }
    leaf tv-nsec {
      type uint32;
      description
        "Time in nsec";
    }
  }

  grouping NAL-EVENT-HISTORY-ENTRY {
    description
      "Individual event history entry";
    container timestamp {
      description
        "Event timestamp";
      uses NAL-TIMESPEC;
    }
    leaf event-string {
      type string {
        length "0..64";
      }
      description
        "Event string";
    }
  }

  grouping NAL-EVENT-HISTORY {
    description
      "Event history bag";
    leaf class-name {
      type string {
        length "0..64";
      }
      description
        "Name of event history";
    }
    list event {
      description
        "Event history list";
      uses NAL-EVENT-HISTORY-ENTRY;
    }
  }

  grouping NAL-SUB-IPV6-FRAMED-ROUTE {
    description
      "NAL subscriber IPv6 framed route data";
    leaf next-hop {
      type inet:ipv6-address;
      description
        "Next Hop";
    }
    leaf tag {
      type uint32;
      description
        "Tag";
    }
    leaf metric {
      type uint32;
      description
        "Metric";
    }
    leaf next-hop-vrf {
      type string {
        length "0..33";
      }
      description
        "Next Hop Vrf Name";
    }
  }

  grouping NAL-SUB-IPV4-FRAMED-ROUTE {
    description
      "NAL subscriber IPv4 framed route data";
    leaf next-hop {
      type inet:ipv4-address;
      description
        "Next Hop";
    }
    leaf tag {
      type uint32;
      description
        "Tag";
    }
    leaf metric {
      type uint32;
      description
        "Metric";
    }
    leaf next-hop-vrf {
      type string {
        length "0..33";
      }
      description
        "Next Hop Vrf Name";
    }
  }

  grouping NAL-SUB-ACTIVATED-SERVICE {
    description
      "NAL subscriber activated service information";
    leaf service-name {
      type string {
        length "0..65";
      }
      description
        "Name of the service";
    }
    leaf activation-time {
      type uint32;
      description
        "service deactivation Time";
    }
    leaf flags {
      type uint32;
      description
        "flags";
    }
    leaf feature-id {
      type uint32;
      description
        "Feature ID";
    }
    leaf bytes-in {
      type uint32;
      units "byte";
      description
        "Bytes in";
    }
    leaf bytes-out {
      type uint32;
      units "byte";
      description
        "Bytes out";
    }
    leaf bytes-ingiga {
      type uint32;
      units "byte";
      description
        "In Bytes in Giga";
    }
    leaf bytes-out-giga {
      type uint32;
      units "byte";
      description
        "Bytes out in Giga";
    }
    leaf final-time {
      type uint32;
      description
        "service final stats Time";
    }
  }

  grouping NAL-SUBS-BRIEF {
    description
      "NAL subscriber  information brief";
    leaf cp-id {
      type uint32;
      description
        "Control-plane ID";
    }
    leaf ifhandle {
      type xr:Interface-name;
      description
        "Subscriber Interface name";
    }
    leaf sub-intf {
      type uint32;
      description
        "Subscriber Interface handle";
    }
    leaf subscriber-fsm-state {
      type Oper-nal-db-subscriber-state;
      description
        "Nal Subscriber state";
    }
    leaf mac-address {
      type yang:mac-address;
      description
        "MAC address";
    }
    leaf vrf-name {
      type string {
        length "0..33";
      }
      description
        "Vrf Name";
    }
    leaf subscriber-ipv4-address {
      type inet:ipv4-address;
      description
        "IPv4 Address of the subscriber";
    }
    leaf framed-ipv4-prefix-len {
      type yang:hex-string;
      description
        "IPv4 framed prefix len";
    }
    leaf ipv6-iana-address {
      type inet:ipv6-address;
      description
        "ipv6 iana address";
    }
    leaf ipv6-iapd-address {
      type inet:ipv6-address;
      description
        "ipv6  iapd address";
    }
    leaf ipv6-iapd-prefix {
      type uint8;
      description
        "ipv6  iapd prefix";
    }
    leaf framed-ipv6-prefix-len {
      type yang:hex-string;
      description
        "IPv6 framed prefix len";
    }
    list framed-ipv4-addr {
      max-elements "4";
      description
        "IPv4 framed addr";
      leaf entry {
        type inet:ipv4-address;
        description
          "IPv4 framed addr";
      }
    }
    list framed-ipv6-addr {
      max-elements "4";
      description
        "IPv6 framed addr";
      leaf entry {
        type In6-addr;
        description
          "IPv6 framed addr";
      }
    }
  }

  grouping NAL-SUBS-INFO {
    description
      "NAL subscriber  information";
    container session-brief {
      description
        "Session info brief data";
      uses NAL-SUBS-BRIEF;
    }
    leaf up-id {
      type uint32;
      description
        "User-plane ID";
    }
    leaf pppoe-session-id {
      type uint16;
      description
        "PPPoE sesison ID";
    }
    leaf retry-count {
      type uint32;
      description
        "Retry count";
    }
    leaf local-magic-number {
      type uint32;
      description
        "Local magic number";
    }
    leaf peer-magic-number {
      type uint32;
      description
        "Peer magic number";
    }
    leaf keep-alive-interval {
      type uint32;
      description
        "Keep alive interval";
    }
    leaf total-ka-req-sent {
      type uint32;
      description
        "Total KA Req Sent";
    }
    leaf total-ka-resp-recv {
      type uint32;
      description
        "Total KA Resp Recv";
    }
    leaf total-ka-req-recv {
      type uint32;
      description
        "Total KA Req Recv";
    }
    leaf total-ka-resp-sent {
      type uint32;
      description
        "Total KA Resp Sent";
    }
    leaf mtu {
      type uint32;
      description
        "Max transfer unit";
    }
    leaf is-encap-string-ready {
      type boolean;
      description
        "Flag whether encap String is ready or not";
    }
    leaf ka-echo-request-counter {
      type uint32;
      description
        "Keepalive  req sent but resp not received";
    }
    leaf lcp-identity {
      type uint8;
      description
        "Identification for KA echo req";
    }
    leaf pppflags {
      type uint32;
      description
        "PPP flags";
    }
    leaf subscriber-type {
      type Oper-nal-db-subscriber;
      description
        "Nal Subacriber type";
    }
    leaf parent-ifhandle {
      type xr:Interface-name;
      description
        "Parent interface";
    }
    leaf parent-interface {
      type string {
        length "0..80";
      }
      description
        "Parent interface";
    }
    leaf subscriber-interface {
      type string {
        length "0..80";
      }
      description
        "Subscriber interface";
    }
    leaf srg-role {
      type Nal-main-edm-srg-role;
      description
        "SRG role";
    }
    leaf srg-group-name {
      type string {
        length "0..65";
      }
      description
        "SRG group name";
    }
    leaf inner-vlan {
      type uint32;
      description
        "Inner Vlan";
    }
    leaf outer-vlan {
      type uint32;
      description
        "Outer Vlan";
    }
    leaf cpe-link-local-address {
      type inet:ipv6-address;
      description
        "CPE link local address";
    }
    leaf feature-id-info {
      type uint32;
      description
        "Subscriber feature id info";
    }
    leaf subscriber-flags {
      type uint32;
      description
        "Subscriber flags";
    }
    leaf interim-interval {
      type uint32;
      description
        "Interim Interval";
    }
    leaf last-interim-time-stamp {
      type uint32;
      description
        "Last Interim Time Stamp";
    }
    leaf interim-fail-count {
      type uint32;
      description
        "Interim Fail Count";
    }
    leaf interim-error {
      type uint32;
      description
        "Interim Error";
    }
    leaf bytes-in {
      type uint32;
      units "byte";
      description
        "Bytes in";
    }
    leaf bytes-out {
      type uint32;
      units "byte";
      description
        "Bytes out";
    }
    leaf bytes-ingiga {
      type uint32;
      units "byte";
      description
        "In Bytes in Giga";
    }
    leaf bytes-out-giga {
      type uint32;
      units "byte";
      description
        "Bytes out in Giga";
    }
    leaf subscriber-create-time {
      type uint32;
      description
        "Subscriber Create Time";
    }
    leaf subscriber-ipv4-up-time {
      type uint32;
      description
        "Subscriber IPv4 Up Time";
    }
    leaf subscriber-ipv6-up-time {
      type uint32;
      description
        "Subscriber IPv6 Up Time";
    }
    leaf subscriber-ipv4-down-time {
      type uint32;
      description
        "Subscriber IPv4 Down Time";
    }
    leaf subscriber-ipv6-down-time {
      type uint32;
      description
        "Subscriber IPv6 Down Time";
    }
    leaf subscriber-af-down-reason {
      type uint32;
      description
        "Subscriber AF Down Reason";
    }
    leaf afup-flags {
      type uint32;
      description
        "AF ipv4/ipv6 up falgs";
    }
    leaf ip-sub-flags {
      type uint64;
      description
        "IPSUB  flags";
    }
    leaf sub-disc-time {
      type uint32;
      description
        "Subscriber Disconnect Time ";
    }
    leaf ipv4-route-count {
      type uint8;
      description
        "IPv4 route count";
    }
    leaf ipv6-route-count {
      type uint8;
      description
        "IPv6 route count";
    }
    leaf local-session-id {
      type uint16;
      description
        "Local session id";
    }
    leaf local-tunnel-id {
      type uint16;
      description
        "Local tunnel id";
    }
    leaf remote-session-id {
      type uint16;
      description
        "Remote Session id";
    }
    leaf remote-tunnel-id {
      type uint16;
      description
        "Remote Tunnel id";
    }
    leaf tunnel-vrf-name {
      type string {
        length "0..33";
      }
      description
        "Tunnel Vrf Name";
    }
    leaf set-tos {
      type uint8;
      description
        "Set Tos";
    }
    leaf reflect-tos {
      type boolean;
      description
        "reflect tos";
    }
    leaf set-df {
      type boolean;
      description
        "Set DF";
    }
    leaf reflect-df {
      type boolean;
      description
        "reflect df";
    }
    leaf tcp-mss-adjust {
      type uint16;
      description
        "tcp mss adjust";
    }
    leaf dst-port {
      type uint16;
      description
        "dst port";
    }
    leaf local-endpt {
      type inet:ipv4-address;
      description
        "local endpt";
    }
    leaf remote-endpt {
      type inet:ipv4-address;
      description
        "Remote endpt";
    }
    leaf ipoe-afi-cap {
      type uint32;
      description
        "IPOE Subscriber AFI Capability";
    }
    leaf loopback-name {
      type string {
        length "0..81";
      }
      description
        "Loopback Name";
    }
    leaf subscriber-ipv4gw {
      type inet:ipv4-address;
      description
        "Subscriber IPv4 Gateway";
    }
    leaf stats-report-id {
      type uint16;
      description
        "subscriber stats report id";
    }
    list active-service {
      description
        "activated services";
      uses NAL-SUB-ACTIVATED-SERVICE;
    }
    list ipv4-framed-route {
      max-elements "4";
      description
        "ipv4 framed route";
      uses NAL-SUB-IPV4-FRAMED-ROUTE;
    }
    list ipv6-framed-route {
      max-elements "4";
      description
        "ipv6 framed route";
      uses NAL-SUB-IPV6-FRAMED-ROUTE;
    }
  }

  grouping NAL-SUBSCRIBER-DISCONNECT-HISTORY-UNIQUE-INTERNAL-DATA {
    description
      "Subscriber unique disconnect history Bag";
    container session-data {
      description
        "subscriber session data info";
      uses NAL-SUBS-INFO;
    }
    container event-history {
      description
        "Subscriber events history";
      uses NAL-EVENT-HISTORY;
    }
  }

  grouping NAL-SUBSCRIBER-DISCONNECT-HISTORY-UNIQUE-DETAIL-DATA {
    description
      "Subscriber unique disconnect history detail Bag";
    leaf disconnect-unique-session-count {
      type uint32;
      description
        "Number of sessions disconnected with this error
         code";
    }
    leaf disc-reason {
      type string {
        length "0..64";
      }
      description
        "Disconnect reason";
    }
    leaf disconnect-errorcode {
      type uint32;
      description
        "error code";
    }
    list unique-detail {
      max-elements "3";
      description
        "unique detail session info for last three
         disconnected sessions";
      uses NAL-SUBSCRIBER-DISCONNECT-HISTORY-UNIQUE-INTERNAL-DATA;
    }
  }
}
