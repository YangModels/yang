module Cisco-IOS-XR-optics-driver-xponder-cfg {
  namespace "http://cisco.com/ns/yang/Cisco-IOS-XR-optics-driver-xponder-cfg";
  prefix optics-driver-xponder-cfg;

  import cisco-semver {
    prefix semver;
  }
  import Cisco-IOS-XR-ifmgr-cfg {
    prefix a1;
  }
  import Cisco-IOS-XR-controller-optics-cfg {
    prefix a2;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR optics-driver-xponder package configuration.
     
     This YANG module augments the
       Cisco-IOS-XR-ifmgr-cfg,
       Cisco-IOS-XR-controller-optics-cfg
     modules with configuration data.
     
     Copyright (c) 2013-2021 by Cisco Systems, Inc.
     All rights reserved.";

  revision 2021-06-17 {
    description
      "Implemented common cli - xponder to apply different modes, wrapper for breakout/portmode cli";
    semver:module-version "1.2.0";
  }
  revision 2021-06-17 {
    description
      "Implemented common cli - xponder to apply different modes, wrapper for breakout/portmode cli IosSetYangSchemaRev Cisco-IOS-XR-optics-quad-cfg";
    semver:module-version "1.0.0";
  }
  revision 2019-04-05 {
    description
      "Establish semantic version baseline.";
  }
  revision 2015-11-09 {
    description
      "IOS XR 6.0 revision.";
  }

  typedef Xponder-type-list {
    type string {
      pattern "(400)|(4x100)|(3x100)|(2x100)|(1x100)";
    }
    description
      "400:400 optics xponder config, 4x100:4x100 optics
       xponder config, 3x100:3x100 optics xponder config
       , 2x100:2x100 optics xponder config, 1x100:1x100
       optics xponder config";
  }

  augment "/a1:interface-configurations/a1:interface-configuration" {
    description
      "This augment extends the configuration data of
       'Cisco-IOS-XR-ifmgr-cfg'";
    leaf xponder {
      type Xponder-type-list;
      description
        "Xponder config for optics";
    }
  }
}
