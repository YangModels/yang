submodule Cisco-IOS-XR-igp-topodb-oper-sub1 {
  belongs-to Cisco-IOS-XR-igp-topodb-oper {
    prefix Cisco-IOS-XR-igp-topodb-oper;
  }

  import ietf-inet-types {
    prefix inet;
  }
  import ietf-yang-types {
    prefix yang;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR igp-topodb package operational data.
     
     Copyright (c) 2013-2022 by Cisco Systems, Inc.
     All rights reserved.";

  revision 2022-02-02 {
    description
      "Modified for Flex algo firsthop gateway.";
    semver:module-version "4.0.0";
  }
  revision 2021-05-12 {
    description
      "Modified for Flex algo Inter-area support.";
    semver:module-version "3.0.0";
  }
  revision 2020-01-02 {
    description
      "Added topodb operational data support.";
    semver:module-version "1.1.0";
  }
  revision 2019-04-05 {
    description
      "Establish semantic version baseline.";
    semver:module-version "1.0.1";
  }
  revision 2015-11-09 {
    description
      "IOS XR 6.0 revision.";
  }

  typedef Otlib-repair-el {
    type enumeration {
      enum "mgmt-otlib-repair-el-invalid" {
        value 0;
        description
          "Unknown LFA";
      }
      enum "mgmt-otlib-repair-el-p-node" {
        value 1;
        description
          "Direct LFA";
      }
      enum "mgmt-otlib-repair-el-q-node" {
        value 2;
        description
          "TI LFA";
      }
    }
    description
      "Otlib repair el";
  }

  typedef Otlib-lfa {
    type enumeration {
      enum "mgmt-otlib-unknown-lfa" {
        value 0;
        description
          "Unknown LFA";
      }
      enum "mgmt-otlib-direct-lfa" {
        value 1;
        description
          "Direct LFA";
      }
      enum "mgmt-otlib-ti-lfa" {
        value 2;
        description
          "TI LFA";
      }
    }
    description
      "Otlib lfa";
  }

  grouping OTLIB-SH-AREA-ALGO-SUMMARY {
    description
      "OTLIB Area Algo Summary";
    leaf algo-number {
      type uint8;
      description
        "Algo Number";
    }
    leaf spf-trigger-flags {
      type uint8;
      description
        "SPF Trigger Flags";
    }
    leaf spf-schedule-flags {
      type uint8;
      description
        "SPF Schedule Flags";
    }
    leaf spf-count {
      type uint8;
      description
        "SPF Count";
    }
    leaf fad-adv-router-id {
      type inet:ipv4-address;
      description
        "FAD Adv Router ID";
    }
    leaf fad-area-id-string {
      type string {
        length "0..16";
      }
      description
        "FAD Adv Router's Area ID";
    }
    leaf metric-type {
      type uint8;
      description
        "Metric Type";
    }
    leaf algo-type {
      type uint8;
      description
        "Algo Type";
    }
    leaf is-uloop-active {
      type boolean;
      description
        "Whether microloop avoidance is active";
    }
    leaf is-fad-unsupported {
      type boolean;
      description
        "Whether selected FAD contains parameters not
         supported by this node";
    }
    leaf is-fapm-supported {
      type boolean;
      description
        "Whether FAPM/FAAM support is enabled";
    }
    leaf uloop-near-end-node {
      type uint32;
      description
        "Near end node in the active microloop
         calculation";
    }
    leaf uloop-far-end-node {
      type uint32;
      description
        "Far end node in the active microloop calculation";
    }
    leaf uloop-cost-in-out-node {
      type uint32;
      description
        "Node that had a cost in or cost out in the
         active microloop calculation";
    }
    leaf uloop-news {
      type uint8;
      description
        "Action that triggered the active microloop
         calculation";
    }
    leaf uloop-last-successful-near-end-node {
      type uint32;
      description
        "Near end node in the last successful microloop
         calculation";
    }
    leaf uloop-last-successful-far-end-node {
      type uint32;
      description
        "Far end node in the last successful microloop
         calculation";
    }
    leaf uloop-last-successful-cost-in-out-node {
      type uint32;
      description
        "Node that had a cost in or cost out in the last
         successful microloop calculation";
    }
    leaf uloop-last-successful-news {
      type uint8;
      description
        "Action that triggered the last successful
         microloop calculation";
    }
    leaf uloop-last-success-begin {
      type string {
        length "0..50";
      }
      description
        "Time at which last successful microloop
         calculation began";
    }
    leaf uloop-last-success-end {
      type string {
        length "0..50";
      }
      description
        "Time at which last successful microloop
         calculation was completed";
    }
    leaf-list exclude-affinity {
      type uint32;
      description
        "Exclude Affinity";
    }
    leaf-list include-any-affinity {
      type uint32;
      description
        "Include Any Affinity";
    }
    leaf-list include-all-affinity {
      type uint32;
      description
        "Include All Affinity";
    }
    leaf-list exclude-srlg {
      type uint32;
      description
        "Exclude SRLG";
    }
  }

  grouping OTLIB-SH-AREA-SUMMARY {
    description
      "OTLIB Area Summary";
    leaf area-id-string {
      type string {
        length "0..16";
      }
      description
        "Area ID";
    }
    leaf num-nodes {
      type uint16;
      description
        "No. of Nodes";
    }
    leaf ulooptime-remaining {
      type uint32;
      description
        "Time remaining for the active Microloop
         avoidance paths";
    }
    list algo {
      description
        "List of Algos";
      uses OTLIB-SH-AREA-ALGO-SUMMARY;
    }
  }

  grouping OTLIB-SH-INST-SUMMARY {
    description
      "OTLIB Instance Summary";
    leaf vrf-name {
      type string;
      description
        "VRF Name";
    }
    leaf router-id {
      type inet:ipv4-address;
      description
        "Router ID";
    }
    leaf num-areas {
      type uint16;
      description
        "No. of Areas";
    }
    leaf spf-trigger-flags {
      type uint8;
      description
        "SPF Trigger Flags";
    }
    leaf spf-schedule-flags {
      type uint8;
      description
        "SPF Schedule Flags";
    }
    leaf num-algos {
      type uint8;
      description
        "No. of Algos supported";
    }
    leaf algo-status {
      type yang:hex-string;
      description
        "Algo Status";
    }
    leaf max-paths {
      type uint16;
      description
        "Max Paths";
    }
    leaf num-routes {
      type uint32;
      description
        "No. of Routes";
    }
    leaf-list route-work-queue-size {
      type uint32;
      max-elements "4";
      description
        "Route Work Queue Sizes";
    }
    list srgb {
      description
        "SRGB List";
      uses OTLIB-SHOW-SR-RANGE;
    }
    list area {
      description
        "List of Areas";
      uses OTLIB-SH-AREA-SUMMARY;
    }
  }

  grouping OTLIB-SHOW-ROUTE-ULOOP-PATH {
    description
      "OTLIB Route Microloop Avoidance Path";
    leaf repair-list-size {
      type uint32;
      description
        "Repair List Size";
    }
    leaf tunnel-interface-name {
      type uint32;
      description
        "Microloop Avoidance Tunnel Interface";
    }
    list repair {
      max-elements "12";
      description
        "Microloop Avoidance Repair List";
      uses OTLIB-SH-REP-EL;
    }
  }

  grouping OTLIB-SH-REP-EL {
    description
      "OSPF Repair Element";
    leaf repair-element-id {
      type inet:ipv4-address;
      description
        "ID of the Repair Element";
    }
    leaf repair-label {
      type uint32;
      description
        "Label of Repair Element";
    }
    leaf repair-element-type {
      type Otlib-repair-el;
      description
        "Type of the Repair Element";
    }
  }

  grouping OTLIB-SHOW-ROUTE-BACKUP-PATH {
    description
      "OTLIB Route Backup Path";
    leaf interface-handle {
      type uint32;
      description
        "Interface Handle";
    }
    leaf next-hop-address {
      type inet:ipv4-address;
      description
        "NextHop IP Address";
    }
    leaf neighbor-id {
      type inet:ipv4-address;
      description
        "Neighbor ID";
    }
    leaf backup-route-source {
      type inet:ipv4-address;
      description
        "IP address of source of route";
    }
    leaf backup-metric {
      type uint64;
      description
        "Backup Metric";
    }
    leaf label {
      type uint32;
      description
        "Label";
    }
    leaf primary-path {
      type boolean;
      description
        "Whether this is also a Primary Path";
    }
    leaf interface-disjoint {
      type boolean;
      description
        "Wheher this is a Interface Disjoint path";
    }
    leaf line-card-disjoint {
      type boolean;
      description
        "Whether this is a Line Card Disjoint path";
    }
    leaf downstream {
      type boolean;
      description
        "Whether this is a downstream path";
    }
    leaf node-protect {
      type boolean;
      description
        "Whether this is a Node Protect path";
    }
    leaf srlg-disjoint {
      type boolean;
      description
        "Whether this is a SRLG Disjoint path";
    }
    leaf weighted-srlg {
      type boolean;
      description
        "Whether this is a Weighted SRLG path";
    }
    leaf lfa-type {
      type Otlib-lfa;
      description
        "LFA type";
    }
    leaf backup-repair-list-size {
      type uint32;
      description
        "Repair List Size";
    }
    leaf backup-tunnel-interface-name {
      type uint32;
      description
        "Backup Tunnel Interface";
    }
    list backup-repair {
      max-elements "12";
      description
        "Backup Repair List";
      uses OTLIB-SH-REP-EL;
    }
  }

  grouping OTLIB-SHOW-ROUTE-PATH {
    description
      "OTLIB Route Path";
    container backup-path {
      description
        "Backup path details";
      uses OTLIB-SHOW-ROUTE-BACKUP-PATH;
    }
    container uloop-path {
      description
        "Microloop Avoidance Path";
      uses OTLIB-SHOW-ROUTE-ULOOP-PATH;
    }
    leaf next-hop-address {
      type inet:ipv4-address;
      description
        "NextHop IP Address";
    }
    leaf interface-handle {
      type uint32;
      description
        "Interface Handle";
    }
    leaf neighbor-id {
      type inet:ipv4-address;
      description
        "Neighbor ID";
    }
    leaf info-src {
      type inet:ipv4-address;
      description
        "Source of Path";
    }
    leaf path-weight {
      type uint32;
      description
        "Path Weight";
    }
    leaf path-label {
      type uint32;
      description
        "Path Label";
    }
    leaf area-id {
      type uint32;
      description
        "Area ID";
    }
  }

  grouping OTLIB-SHOW-ROUTE-ALGO {
    description
      "OTLIB Route Algo";
    leaf algo-number {
      type uint8;
      description
        "Algo Number";
    }
    leaf route-metric {
      type uint64;
      description
        "Route Metric";
    }
    leaf forward-distance {
      type uint64;
      description
        "Forward Distance";
    }
    leaf route-update-time {
      type string {
        length "0..50";
      }
      description
        "Time at which this route was updated";
    }
    leaf route-algo-flags {
      type uint8;
      description
        "Route algo flags";
    }
    leaf route-type {
      type uint8;
      description
        "Route Type";
    }
    leaf route-sid {
      type uint32;
      description
        "Route SID";
    }
    leaf route-label {
      type uint32;
      description
        "Route label";
    }
    leaf path-count {
      type uint32;
      description
        "Route path count";
    }
    leaf ext-e-bit {
      type boolean;
      description
        "External E bit";
    }
    list path {
      description
        "Algo Path List";
      uses OTLIB-SHOW-ROUTE-PATH;
    }
    list route-contributor {
      description
        "Route prefix contributors";
      uses OTLIB-SHOW-PREFIX-CONTRIB;
    }
  }

  grouping OTLIB-SHOW-ROUTE {
    description
      "OTLIB Route";
    leaf route-prefix {
      type inet:ipv4-address;
      description
        "Route Prefix Address";
    }
    leaf route-prefix-length {
      type uint8;
      description
        "Route Prefix Length";
    }
    leaf route-priority {
      type uint8;
      description
        "Route priority";
    }
    leaf route-flags {
      type uint16;
      description
        "Route flags";
    }
    list algo {
      description
        "Route Algo list";
      uses OTLIB-SHOW-ROUTE-ALGO;
    }
  }

  grouping OTLIB-SHOW-ROUTE-INSTANCE {
    description
      "OTLIB Route Instance";
    leaf vrf-name {
      type string;
      description
        "VRF Name";
    }
    leaf router-id {
      type inet:ipv4-address;
      description
        "Router ID";
    }
    leaf num-routes {
      type uint32;
      description
        "No. of routes";
    }
    list route {
      description
        "List of Routes";
      uses OTLIB-SHOW-ROUTE;
    }
  }

  grouping OTLIB-SHOW-ASBR-CONTRIB-ALGO {
    description
      "OTLIB Flex algo specific ASBR contributor";
    leaf algo {
      type uint8;
      description
        "Algo number";
    }
    leaf igp-metric {
      type uint32;
      description
        "Base IGP metric of the asbr by the node";
    }
    leaf faam-metric {
      type uint32;
      description
        "FAAM metric of the asbr by the node";
    }
    leaf total-metric {
      type uint64;
      description
        "Total metric to reach the asbr";
    }
    leaf contrib-flags {
      type uint8;
      description
        "ASBR contributor flags";
    }
  }

  grouping OTLIB-SHOW-ASBR {
    description
      "OTLIB ASBR";
    leaf asbrid {
      type inet:ipv4-address;
      description
        "ASBR ID";
    }
    leaf asbr-metric {
      type uint32;
      description
        "ASBR metric";
    }
    list asbr-contributor {
      description
        "ASBR Contributors";
      uses OTLIB-SHOW-ASBR-CONTRIB-ALGO;
    }
  }

  grouping OTLIB-SHOW-ASBR-REACHABILITY-NODE {
    description
      "OTLIB ASBR Reachability Node";
    container node-id {
      description
        "Node ID";
      uses OTLIB-SHOW-NODE-ID;
    }
    leaf num-asb-rs {
      type uint32;
      description
        "Number of ASBRs";
    }
    list asbr {
      description
        "List of ASBRs advertised by the node";
      uses OTLIB-SHOW-ASBR;
    }
  }

  grouping OTLIB-SHOW-ASBR-REACHABILITY-AREA {
    description
      "OTLIB ASBR Reachability Area";
    leaf area-id-string {
      type string {
        length "0..16";
      }
      description
        "Area ID string";
    }
    list node {
      description
        "List of Nodes";
      uses OTLIB-SHOW-ASBR-REACHABILITY-NODE;
    }
  }

  grouping OTLIB-SHOW-ASBR-REACHABILITY-INSTANCE {
    description
      "OTLIB ASBR Reachability Instance";
    leaf router-id {
      type inet:ipv4-address;
      description
        "Router ID";
    }
    list area {
      description
        "List of Areas";
      uses OTLIB-SHOW-ASBR-REACHABILITY-AREA;
    }
  }

  grouping OTLIB-SHOW-NFTE-NODE-SRLG {
    description
      "OTLIB Nfte Srlg";
    leaf srlg-interface-topo-intf {
      type uint32;
      description
        "Srlg Interface Topo Interface";
    }
    leaf sit-pcspt-node-srlg-dist {
      type uint64;
      description
        "Srlg Pcspt Node Srlg Dist";
    }
    list nfte-path {
      description
        "Nfte Path List";
      uses OTLIB-SHOW-NFTE-PATH;
    }
  }

  grouping OTLIB-SHOW-NFTE-SRLG {
    description
      "OTLIB Nfte Srlg";
    leaf srlg-interface-topo-intf {
      type uint32;
      description
        "Srlg Interface Topo Interface";
    }
    leaf sit-pcspt-srlg-dist {
      type uint64;
      description
        "Srlg Pcspt Srlg Dist";
    }
    list nfte-path {
      description
        "Nfte Path List";
      uses OTLIB-SHOW-NFTE-PATH;
    }
  }

  grouping OTLIB-SHOW-NFTE-NODE {
    description
      "OTLIB Nfte Node";
    leaf nfte-pcspt-node-dist {
      type uint64;
      description
        "Nfte Post Convergence Node Distance";
    }
    list nfte-path {
      description
        "Nfte Path List";
      uses OTLIB-SHOW-NFTE-PATH;
    }
  }

  grouping OTLIB-SHOW-NFTE-PATH {
    description
      "OTLIB Nfte Path";
    leaf nfte-path-nexthop {
      type inet:ipv4-address;
      description
        "Nfte Path Nexthop";
    }
    leaf nfte-path-ifhandle {
      type uint32;
      description
        "Nfte Path Intf Handle";
    }
    leaf nfte-path-nbr-id {
      type inet:ipv4-address;
      description
        "Nfte Path Nbr Id";
    }
    leaf nfte-parent-node-id {
      type inet:ipv4-address;
      description
        "Nfte Parent Node Id";
    }
    leaf nfte-path-is-repair {
      type boolean;
      description
        "Nfte Path Node Id";
    }
    list repair-node {
      description
        "Repair Node List";
      uses OTLIB-SHOW-REPAIR-NODE;
    }
  }

  grouping OTLIB-SHOW-NFTE-LINK {
    description
      "OTLIB Nfte Link";
    leaf nfte-pcspt-dist {
      type uint64;
      description
        "Nfte Post Convergence Distance";
    }
    list nfte-path {
      description
        "Nfte Path List";
      uses OTLIB-SHOW-NFTE-PATH;
    }
  }

  grouping OTLIB-SHOW-NFTE {
    description
      "OTLIB Nfte";
    container nfte-link {
      description
        "Nfte Link Protection";
      uses OTLIB-SHOW-NFTE-LINK;
    }
    container nfte-node {
      description
        "Nfte Node Protection";
      uses OTLIB-SHOW-NFTE-NODE;
    }
    leaf nfte-node-id {
      type inet:ipv4-address;
      description
        "Nfte Node Id";
    }
    leaf nfte-dist {
      type uint64;
      description
        "Nfte Distance";
    }
    leaf nfte-rspt-dist {
      type uint64;
      description
        "Nfte Reverse SPT Distance";
    }
    leaf nfte-in-pspace {
      type boolean;
      description
        "Nfte In P Space";
    }
    leaf nfte-in-qspace {
      type boolean;
      description
        "Nfte In Q Space";
    }
    leaf nfte-in-ext-pspace {
      type boolean;
      description
        "Nfte In Ext P Space";
    }
    list nfte-srlg {
      description
        "Nfte Srlg Protection list";
      uses OTLIB-SHOW-NFTE-SRLG;
    }
    list nfte-node-srlg {
      description
        "Nfte Node Srlg Protection list";
      uses OTLIB-SHOW-NFTE-NODE-SRLG;
    }
  }

  grouping OTLIB-SHOW-IPFRR-NBR-ALGO {
    description
      "OTLIB Ipfrr Nbr Algo";
    leaf algo-number {
      type uint8;
      description
        "Algo Number";
    }
    leaf lfa-rev-num {
      type uint32;
      description
        "Lfa Revision Number";
    }
    list nfte {
      description
        "Node Flexalgo Topo Entries List";
      uses OTLIB-SHOW-NFTE;
    }
  }

  grouping OTLIB-SHOW-IPFRR-NBR {
    description
      "OTLIB Ipfrr Nbr";
    leaf neighbor-id {
      type inet:ipv4-address;
      description
        "Neighbor ID";
    }
    list ipfrr-nbr-algo {
      description
        "Ipfrr Nbr Algo List";
      uses OTLIB-SHOW-IPFRR-NBR-ALGO;
    }
  }

  grouping OTLIB-SHOW-IPFRR-AREA {
    description
      "OTLIB SHOW IPFRR AREA";
    leaf area-id-str {
      type string;
      description
        "Area Id Str";
    }
    list ipfrr-nbr {
      description
        "Ipfrr Nbr List";
      uses OTLIB-SHOW-IPFRR-NBR;
    }
  }

  grouping OTLIB-SHOW-IPFRR-INSTANCE {
    description
      "OTLIB SHOW IPFRR INSTANCE";
    leaf vrf-name {
      type string;
      description
        "VRF Name";
    }
    leaf router-id {
      type inet:ipv4-address;
      description
        "Router ID";
    }
    list ipfrr-area {
      description
        "Ipfrr Area List";
      uses OTLIB-SHOW-IPFRR-AREA;
    }
  }

  grouping OTLIB-SHOW-FHGW {
    description
      "OTLIB Firsthop Gateway";
    leaf interface-handle {
      type uint32;
      description
        "Interface Handle";
    }
    leaf next-hop-address {
      type inet:ipv4-address;
      description
        "NextHop IP Address";
    }
    leaf refcount {
      type uint32;
      description
        "Reference Count";
    }
  }

  grouping OTLIB-SHOW-FHGW-INSTANCE {
    description
      "OTLIB Firsthop Gateway Instance";
    leaf router-id {
      type inet:ipv4-address;
      description
        "Router ID";
    }
    list firsthop-gateway {
      description
        "List of firsthop gateways";
      uses OTLIB-SHOW-FHGW;
    }
  }

  grouping OTLIB-SHOW-FORW-ADDR {
    description
      "OTLIB Forwarding Address";
    leaf forw-addr {
      type inet:ipv4-address;
      description
        "Forw Addr";
    }
    leaf route-prefix {
      type inet:ipv4-address;
      description
        "Route Prefix";
    }
    leaf route-prefix-len {
      type uint8;
      description
        "Route Prefix Len";
    }
    leaf forw-addr-flags {
      type uint8;
      description
        "Forwarding Address flags";
    }
  }

  grouping OTLIB-SHOW-FORW-ADDR-INSTANCE {
    description
      "OTLIB Forwarding Address Instance";
    leaf router-id {
      type inet:ipv4-address;
      description
        "Router ID";
    }
    list forw-addr {
      description
        "List of forwarding addresses";
      uses OTLIB-SHOW-FORW-ADDR;
    }
  }

  grouping OTLIB-SHOW-REPAIR-NODE {
    description
      "OTLIB Repair Node";
    leaf re-label {
      type uint32;
      description
        "Repair element Label";
    }
    leaf re-address {
      type inet:ipv4-address;
      description
        "Repair Address";
    }
    leaf re-identifier {
      type inet:ipv4-address;
      description
        "Repair Identifier";
    }
    leaf re-is-node-sid {
      type boolean;
      description
        "Repair Is Node Sid";
    }
  }

  grouping OTLIB-SHOW-ULOOP-NODE-PATH {
    description
      "OTLIB Microloop Avoidance Node Path";
    leaf path-nexthop {
      type inet:ipv4-address;
      description
        "Path Nexthop";
    }
    leaf path-ifhandle {
      type uint32;
      description
        "Path Intf Handle";
    }
    leaf path-nbr-id {
      type uint32;
      description
        "Path Nbr Id";
    }
    leaf parent-node-id {
      type inet:ipv4-address;
      description
        "Parent Node Id";
    }
    leaf path-is-repair {
      type boolean;
      description
        "Path Node Id";
    }
    list repair-node {
      description
        "Reapir Node List";
      uses OTLIB-SHOW-REPAIR-NODE;
    }
  }

  grouping OTLIB-SHOW-ULOOP-NODE {
    description
      "OTLIB Microloop Avoidance Node";
    leaf node-id {
      type inet:ipv4-address;
      description
        "Node Id";
    }
    leaf rspt-dist {
      type uint64;
      description
        "Rspt Distance";
    }
    leaf in-pspace {
      type boolean;
      description
        "In P Space";
    }
    leaf in-qspace {
      type boolean;
      description
        "In Q Space";
    }
    leaf in-ext-pspace {
      type boolean;
      description
        "In Ext P Space";
    }
    list path {
      description
        "Path List";
      uses OTLIB-SHOW-ULOOP-NODE-PATH;
    }
  }

  grouping OTLIB-SHOW-ULOOP-ALGO {
    description
      "OTLIB Microloop Avoidance Algo";
    leaf algo-number {
      type uint8;
      description
        "Algo Number";
    }
    list node {
      description
        "Node List";
      uses OTLIB-SHOW-ULOOP-NODE;
    }
  }

  grouping OTLIB-SHOW-ULOOP-AREA {
    description
      "OTLIB Microloop Avoidance Area";
    leaf area-id-str {
      type string;
      description
        "Area Id Str";
    }
    list algo {
      description
        "Algo List";
      uses OTLIB-SHOW-ULOOP-ALGO;
    }
  }

  grouping OTLIB-SHOW-ULOOP-INSTANCE {
    description
      "OTLIB Microloop Avoidance Instance";
    leaf vrf-name {
      type string;
      description
        "VRF Name";
    }
    leaf router-id {
      type inet:ipv4-address;
      description
        "Router ID";
    }
    list area {
      description
        "Area List";
      uses OTLIB-SHOW-ULOOP-AREA;
    }
  }

  grouping OTLIB-SHOW-ASBR-CONTRIB {
    description
      "OTLIB ASBR contributor";
    leaf igp-metric {
      type uint32;
      description
        "Base IGP metric of the asbr by the node";
    }
    leaf faam-metric {
      type uint32;
      description
        "FAAM metric of the asbr by the node";
    }
    leaf total-metric {
      type uint64;
      description
        "Total metric to reach the asbr";
    }
    leaf contrib-flags {
      type uint8;
      description
        "ASBR contributor flags";
    }
    leaf adv-router-id {
      type inet:ipv4-address;
      description
        "Advertising Router ID";
    }
    leaf area-id {
      type uint32;
      description
        "Area ID of the contributor";
    }
  }

  grouping OTLIB-SHOW-TOPO-PATH {
    description
      "OTLIB Topo Path";
    leaf next-hop-address {
      type inet:ipv4-address;
      description
        "NextHop IP Address";
    }
    leaf interface-handle {
      type uint32;
      description
        "Interface Handle";
    }
    leaf neighbor-id {
      type inet:ipv4-address;
      description
        "Neighbor ID";
    }
    leaf path-weight {
      type uint32;
      description
        "Path Weight";
    }
    leaf area-id {
      type uint32;
      description
        "Area ID";
    }
  }

  grouping OTLIB-SHOW-NODE-ALGO {
    description
      "OTLIB Node Algo";
    leaf algo-number {
      type uint8;
      description
        "Algo Number";
    }
    leaf node-distance {
      type uint64;
      description
        "Node Distance";
    }
    leaf is-node-reachable {
      type boolean;
      description
        "Node reachable";
    }
    leaf is-direct-node {
      type boolean;
      description
        "Direct Node";
    }
    leaf is-node-dirty {
      type boolean;
      description
        "Node is dirty";
    }
    leaf is-abr-dirty {
      type boolean;
      description
        "ABR Node is dirty";
    }
    leaf is-asbr-dirty {
      type boolean;
      description
        "ASBR Node is dirty";
    }
    list path {
      description
        "Algo Path List";
      uses OTLIB-SHOW-TOPO-PATH;
    }
    list asbr-contributor {
      description
        "ASBR Contributors";
      uses OTLIB-SHOW-ASBR-CONTRIB;
    }
  }

  grouping OTLIB-SHOW-PATH-NODE {
    description
      "OTLIB Path Node";
    container node-id {
      description
        "Node ID";
      uses OTLIB-SHOW-NODE-ID;
    }
    leaf is-root-node {
      type boolean;
      description
        "Is root node";
    }
    leaf is-area-border-router {
      type boolean;
      description
        "Node is ABR";
    }
    leaf is-as-border-router {
      type boolean;
      description
        "Node is ASBR";
    }
    list algo {
      description
        "List of node Algos";
      uses OTLIB-SHOW-NODE-ALGO;
    }
  }

  grouping OTLIB-SHOW-PATH-AREA {
    description
      "OTLIB Path Area";
    leaf area-id-string {
      type string {
        length "0..16";
      }
      description
        "Area ID string. Valid only if it is not ASBR
         paths";
    }
    leaf is-asbr-paths {
      type boolean;
      description
        "Is the paths to ASBRs";
    }
    list node {
      description
        "List of Nodes";
      uses OTLIB-SHOW-PATH-NODE;
    }
  }

  grouping OTLIB-SHOW-PATH-INSTANCE {
    description
      "OTLIB Path Instance";
    leaf vrf-name {
      type string;
      description
        "VRF Name";
    }
    leaf router-id {
      type inet:ipv4-address;
      description
        "Router ID";
    }
    list area {
      description
        "List of Areas";
      uses OTLIB-SHOW-PATH-AREA;
    }
  }

  grouping OTLIB-SHOW-FAD-DEFN {
    description
      "OTLIB FAD Definition";
    leaf algo-number {
      type uint8;
      description
        "Algo Number";
    }
    leaf metric-type {
      type uint8;
      description
        "Metric Type";
    }
    leaf algo-type {
      type uint8;
      description
        "Algo Type";
    }
    leaf priority {
      type uint8;
      description
        "Algo Priority";
    }
    leaf fad-oper-flags {
      type uint16;
      description
        "FAD Operational Flags";
    }
    leaf fad-has-unsupported-params {
      type boolean;
      description
        "The FAD defintion contains TLVs or Flags that
         are not supported by this node";
    }
    leaf-list exclude-affinity {
      type uint32;
      description
        "Exclude Affinity";
    }
    leaf-list include-any-affinity {
      type uint32;
      description
        "Include Any Affinity";
    }
    leaf-list include-all-affinity {
      type uint32;
      description
        "Include All Affinity";
    }
    leaf-list exclude-srlg {
      type uint32;
      description
        "Exclude-any SRLG";
    }
  }

  grouping OTLIB-SHOW-SR-RANGE {
    description
      "OTLIB SR Range";
    leaf range-start {
      type uint32;
      description
        "Range Start";
    }
    leaf range-size {
      type uint32;
      description
        "Range Size";
    }
  }

  grouping OTLIB-SHOW-PREFIX-CONTRIB {
    description
      "OTLIB Prefix contributor";
    leaf algo {
      type uint8;
      description
        "Algo number";
    }
    leaf sid {
      type uint32;
      description
        "SID";
    }
    leaf igp-metric {
      type uint32;
      description
        "Base IGP metric of the prefix by the node";
    }
    leaf fapm-metric {
      type uint32;
      description
        "FAPM metric of the prefix by the node";
    }
    leaf total-metric {
      type uint64;
      description
        "Total metric to reach the prefix";
    }
    leaf contrib-flags {
      type uint8;
      description
        "Prefix contributor flags";
    }
    leaf sid-flags {
      type uint8;
      description
        "SID flags";
    }
    leaf route-type {
      type uint8;
      description
        "Route Type of this contributor";
    }
    leaf adv-router-id {
      type inet:ipv4-address;
      description
        "Advertising Router ID";
    }
    leaf area-id {
      type uint32;
      description
        "Area ID of the contributor";
    }
  }

  grouping OTLIB-SHOW-PREFIX {
    description
      "OTLIB Prefix";
    leaf prefix-address {
      type inet:ipv4-address;
      description
        "Prefix Address";
    }
    leaf prefix-length {
      type uint8;
      description
        "Prefix Length";
    }
    leaf prefix-metric {
      type uint32;
      description
        "Prefix metric";
    }
    leaf route-type {
      type uint32;
      description
        "Route Type";
    }
    leaf ext-e-bit {
      type boolean;
      description
        "External E Bit. Valid when route type is
         external";
    }
    leaf forwarding-address {
      type inet:ipv4-address;
      description
        "Forwarding Address applicable only for external
         prefixes";
    }
    leaf external-tag {
      type uint32;
      description
        "Tag applicable only for external prefixes";
    }
    leaf prefix-flags {
      type uint16;
      description
        "Prefix Flags";
    }
    list prefix-contributor {
      description
        "Prefix Contributors";
      uses OTLIB-SHOW-PREFIX-CONTRIB;
    }
  }

  grouping OTLIB-SHOW-ADJ-SID {
    description
      "OTLIB Adj Sid";
    leaf lan-nbr-id {
      type uint32;
      description
        "Neighbor ID in LAN";
    }
    leaf sid {
      type uint32;
      description
        "SID value advertised";
    }
    leaf type {
      type uint8;
      description
        "Type specifying if this is Normal Adj SID or LAN
         Adj SID";
    }
    leaf flags {
      type uint8;
      description
        "Adj SID Flags as per RFC";
    }
    leaf mtid {
      type uint8;
      description
        "Multi-Topology ID as per RFC";
    }
    leaf weight {
      type uint8;
      description
        "Weight used in load balancing";
    }
  }

  grouping OTLIB-SHOW-LINK-ASLA-ATTR {
    description
      "OTLIB ASLA Link Attrs";
    leaf srte-metric {
      type uint32;
      description
        "SR-TE Metric";
    }
    leaf min-delay {
      type uint32;
      description
        "Min Delay";
    }
    leaf-list ext-admin-group {
      type uint32;
      units "bit";
      description
        "Ext. Admin Group bits";
    }
    leaf-list srlg {
      type uint32;
      description
        "SRLG values";
    }
  }

  grouping OTLIB-SHOW-LINK-ATTR {
    description
      "OTLIB Link Attrs";
    container flex-algo-asla-attrs {
      description
        "Flex Algo ASLA Attributes";
      uses OTLIB-SHOW-LINK-ASLA-ATTR;
    }
    leaf lsid {
      type inet:ipv4-address;
      description
        "Ext Link LSA ID";
    }
    leaf local-interface-id {
      type uint32;
      description
        "Local Interface ID";
    }
    leaf remote-interface-id {
      type uint32;
      description
        "Remote Interface ID";
    }
    leaf remote-ipv4-address {
      type inet:ipv4-address;
      description
        "Remote IPv4 Address";
    }
    leaf max-bandwidth {
      type uint32;
      description
        "Max Bandwidth";
    }
    list adj-sid {
      description
        "Adjacency Sid";
      uses OTLIB-SHOW-ADJ-SID;
    }
  }

  grouping OTLIB-SHOW-LINK-ID {
    description
      "OTLIB Link ID";
    leaf link-id {
      type inet:ipv4-address;
      description
        "Link ID";
    }
    leaf link-data {
      type inet:ipv4-address;
      description
        "Link Data";
    }
    leaf link-type {
      type uint8;
      description
        "Link Type";
    }
  }

  grouping OTLIB-SHOW-LINK {
    description
      "OTLIB Link";
    container link-id {
      description
        "Link ID";
      uses OTLIB-SHOW-LINK-ID;
    }
    container remote-link-id {
      description
        "Remote Link ID";
      uses OTLIB-SHOW-LINK-ID;
    }
    container link-attrs {
      description
        "Link Attributes";
      uses OTLIB-SHOW-LINK-ATTR;
    }
    leaf link-metric {
      type uint16;
      description
        "Link Metric";
    }
    leaf link-subnet-mask {
      type inet:ipv4-address;
      description
        "Link Subnet Mask";
    }
    leaf link-oper-flags {
      type uint16;
      description
        "Link Operational flags";
    }
    leaf is-router-lsa-contrib {
      type boolean;
      description
        "Is Router LSA Contributing";
    }
    leaf is-network-lsa-contrib {
      type boolean;
      description
        "Is Network LSA Contributing";
    }
    leaf is-ext-link-lsa-contrib {
      type boolean;
      description
        "Is Ext Link LSA Contributing";
    }
  }

  grouping OTLIB-SHOW-NODE-ID {
    description
      "OTLIB Node ID";
    leaf adv-router-id {
      type inet:ipv4-address;
      description
        "Advertising Router ID";
    }
    leaf dr-identifier {
      type inet:ipv4-address;
      description
        "Node DR Identifier";
    }
  }

  grouping OTLIB-SHOW-NODE {
    description
      "OTLIB Node";
    container node-id {
      description
        "Node ID";
      uses OTLIB-SHOW-NODE-ID;
    }
    leaf num-links {
      type uint16;
      description
        "Number of Links";
    }
    leaf num-prefixes {
      type uint32;
      description
        "Number of prefixes";
    }
    leaf is-root-node {
      type boolean;
      description
        "Is root node";
    }
    leaf is-area-border-router {
      type boolean;
      description
        "Node is ABR";
    }
    leaf is-as-border-router {
      type boolean;
      description
        "Node is ASBR";
    }
    leaf node-oper-flags {
      type uint16;
      description
        "Node Operational flags";
    }
    leaf is-router-lsa-contrib {
      type boolean;
      description
        "Is Router LSA Contributing";
    }
    leaf is-network-lsa-contrib {
      type boolean;
      description
        "Is Network LSA Contributing";
    }
    leaf is-router-info-lsa-contrib {
      type boolean;
      description
        "Is Router Info LSA Contributing";
    }
    leaf-list node-algo {
      type uint8;
      description
        "Node algo support list";
    }
    list link {
      description
        "List of Links";
      uses OTLIB-SHOW-LINK;
    }
    list prefix {
      description
        "List of prefixes";
      uses OTLIB-SHOW-PREFIX;
    }
    list srgb {
      description
        "Node SRGB List";
      uses OTLIB-SHOW-SR-RANGE;
    }
    list fad {
      description
        "Flex Algo Definition List";
      uses OTLIB-SHOW-FAD-DEFN;
    }
  }

  grouping OTLIB-SHOW-AREA {
    description
      "OTLIB Area";
    leaf area-id-string {
      type string {
        length "0..16";
      }
      description
        "Area ID string. Valid only if not AS scoped";
    }
    leaf is-as-scoped {
      type boolean;
      description
        "Is the prefixes AS scoped";
    }
    leaf num-nodes {
      type uint16;
      description
        "No. of nodes under area";
    }
    list node {
      description
        "List of Nodes";
      uses OTLIB-SHOW-NODE;
    }
  }

  grouping OTLIB-SHOW-INSTANCE {
    description
      "OTLIB Instance";
    leaf vrf-name {
      type string;
      description
        "VRF Name";
    }
    leaf router-id {
      type inet:ipv4-address;
      description
        "Router ID";
    }
    list area {
      description
        "List of Areas";
      uses OTLIB-SHOW-AREA;
    }
  }
}
