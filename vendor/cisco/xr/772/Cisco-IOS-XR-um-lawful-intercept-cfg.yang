module Cisco-IOS-XR-um-lawful-intercept-cfg {
  namespace "http://cisco.com/ns/yang/Cisco-IOS-XR-um-lawful-intercept-cfg";
  prefix um-lawful-intercept-cfg;

  import Cisco-IOS-XR-um-aaa-cfg {
    prefix a1;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR lawful-intercept package configuration.
     
     This YANG module augments the
     modules with configuration data.
     
     Copyright (c) 2020 by Cisco Systems, Inc.
     All rights reserved.";

  revision 2020-08-10 {
    description
      "Initial release";
    semver:module-version "1.0.0";
  }

  feature li_cap_is_li_supported {
    description
      "li cap is li supported";
  }

  feature li_cap_is_overlap_tap_supported {
    description
      "li cap is overlap tap supported";
  }

  feature li_cap_is_2gig_policer_supported {
    description
      "li cap is 2gig policer supported";
  }

  augment "/a1:aaa" {
    container intercept {
      presence "Indicates a intercept node is configured.";
      description
        "Global LI-MA enable disable";
    }
  }
  container lawful-intercept {
    if-feature "li_cap_is_li_supported";
    description
      "Global LI enable disable";
    container disable {
      presence "Indicates a disable node is configured.";
      description
        "disable LI feature";
    }
    container overlap-tap {
      if-feature "li_cap_is_overlap_tap_supported";
      description
        "Over Lap Tap enable disable";
      container enable {
        presence "Indicates a enable node is configured.";
        description
          "disable LI OT feature";
      }
    }
    container interface-taps {
      if-feature "li_cap_is_2gig_policer_supported";
      description
        "2Gig policer enable";
      container two-gig {
        presence "Indicates a two-gig node is configured.";
        description
          "enable LI Interface Taps 2Gig policer";
      }
    }
  }
}
