module Cisco-IOS-XR-um-ncs5k-hw-module-cfg {
  namespace "http://cisco.com/ns/yang/Cisco-IOS-XR-um-ncs5k-hw-module-cfg";
  prefix um-ncs5k-hw-module-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ncs5k-hw-module package configuration.
     
     This YANG module augments the
     modules with configuration data.
     
     Copyright (c) 2020 by Cisco Systems, Inc.
     All rights reserved.";

  revision 2020-10-23 {
    description
      "Initial release";
    semver:module-version "1.0.0";
  }

  container hw-module {
    description
      "Configure h/w module";
    container loadbalancing {
      description
        "HW Loadbalancing configuration";
      leaf hash-seed {
        type uint32 {
          range "0..4294967295" {
            description
              "any number from 0 to (2^32 - 1)";
          }
        }
        description
          "Configure 32-bit seed for hashing";
      }
      container hash-sub-sel {
        description
          "Configure hash sub-sel for ECMP";
        container a0 {
          must
            "not(../b0 or ../a1
             or ../b1 or ../b1a1b0a0)";
          presence "Indicates a a0 node is configured.";
          description
            "ECMP Hash Sub Selection A0";
          leaf hash-offset {
            type uint32 {
              range "0..63" {
                description
                  "any decimal number from 0 to 127";
              }
            }
            description
              "Configure hash offset";
          }
        }
        container b0 {
          must
            "not(../a0 or ../a1
             or ../b1 or ../b1a1b0a0)";
          presence "Indicates a b0 node is configured.";
          description
            "ECMP Hash Sub Selection A1";
          leaf hash-offset {
            type uint32 {
              range "0..63" {
                description
                  "any decimal number from 0 to 127";
              }
            }
            description
              "Configure hash offset";
          }
        }
        container a1 {
          must
            "not(../a0 or ../b0
             or ../b1 or ../b1a1b0a0)";
          presence "Indicates a a1 node is configured.";
          description
            "ECMP Hash Sub Selection B0";
          leaf hash-offset {
            type uint32 {
              range "0..63" {
                description
                  "any decimal number from 0 to 127";
              }
            }
            description
              "Configure hash offset";
          }
        }
        container b1 {
          must
            "not(../a0 or ../b0
             or ../a1 or ../b1a1b0a0)";
          presence "Indicates a b1 node is configured.";
          description
            "ECMP Hash Sub Selection B1";
          leaf hash-offset {
            type uint32 {
              range "0..63" {
                description
                  "any decimal number from 0 to 127";
              }
            }
            description
              "Configure hash offset";
          }
        }
        container b1a1b0a0 {
          must
            "not(../a0 or ../b0
             or ../a1 or ../b1)";
          presence "Indicates a b1a1b0a0 node is configured.";
          description
            "ECMP Concatenate Hash B1A1B0A0";
          leaf hash-offset {
            type uint32 {
              range "0..63" {
                description
                  "any decimal number from 0 to 127";
              }
            }
            description
              "Configure hash offset";
          }
        }
      }
      container bgp-3107 {
        description
          "Enable ECMP for BGP 3107";
        container ecmp {
          description
            "ECMP Loadbalancing method";
          container enable {
            presence "Indicates a enable node is configured.";
            description
              "Enable ECMP for BGP LU";
          }
        }
      }
      container gtp {
        description
          "GTP optimized";
        container enable {
          presence "Indicates a enable node is configured.";
          description
            "Enable GTP TEID for hash calculation";
        }
      }
    }
    container urpf {
      description
        "Unicast reverse path forwarding";
      container enable {
        must "not(../disable)";
        presence "Indicates a enable node is configured.";
        description
          "Enable urpf";
      }
      container disable {
        must "not(../enable)";
        presence "Indicates a disable node is configured.";
        description
          "Disable urpf";
      }
    }
    container segment-routing {
      description
        "Platform specific segment-routing configuration";
      container reserve {
        description
          "Reservation for SR";
        container service-label {
          presence "Indicates a service-label node is configured.";
          description
            "Reserve service-label for SR";
        }
      }
    }
    container sp {
      presence "Indicates a sp node is configured.";
      description
        "Configure SP profile";
    }
    container dc {
      presence "Indicates a dc node is configured.";
      description
        "Configure DC profile";
    }
  }
}
