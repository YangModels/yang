module Cisco-IOS-XR-man-ems-oper {
  namespace "http://cisco.com/ns/yang/Cisco-IOS-XR-man-ems-oper";
  prefix man-ems-oper;

  import Cisco-IOS-XR-types {
    prefix xr;
  }
  import cisco-semver {
    prefix semver;
  }
  include Cisco-IOS-XR-man-ems-oper-sub1 {
    revision-date 2021-10-22;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR man-ems package operational data.
     
     This module contains definitions
     for the following management objects:
       grpc: grpc commands
     
     Copyright (c) 2013-2021 by Cisco Systems, Inc.
     All rights reserved.";

  revision 2021-10-22 {
    description
      "Added certificate bundle statistics";
    semver:module-version "1.3.0";
  }
  revision 2021-06-10 {
    description
      "Added gRPC tunnel.";
    semver:module-version "1.2.0";
  }
  revision 2021-03-22 {
    description
      "Added keep alive commands.";
    semver:module-version "1.1.0";
  }
  revision 2019-04-05 {
    description
      "Establish semantic version baseline.";
    semver:module-version "1.0.1";
  }
  revision 2019-02-22 {
    description
      "Fixed yang evaluator warnings.";
  }
  revision 2015-11-09 {
    description
      "IOS XR 6.0 revision.";
  }

  container grpc {
    config false;
    description
      "grpc commands";
    container state {
      description
        "Grpc State";
      uses GRPC-STATE;
    }
    container tunnel {
      description
        "Grpc tunnels";
      container destinations {
        description
          "Grpc tunnel destinations";
        list destination {
          description
            "Grpc tunnel sessions";
          leaf address {
            type xr:Cisco-ios-xr-string {
              length "1..128";
            }
            description
              "IPv4 address in dotted-quad notation, or IPv6
               address in full, mixed, shortened, and
               shortened-mixed notation.";
          }
          leaf port {
            type xr:Cisco-ios-xr-port-number;
            description
              "Destination port";
          }
          uses GRPC-TUNNEL-SESSIONS;
        }
      }
    }
    container status {
      description
        "Grpc Status";
      uses GRPC-STATUS-INFO-B;
    }
    container statistics {
      description
        "Grpc Statistics";
      uses GRPC-STATISTICS-INFO-B;
    }
  }
}
