module Cisco-IOS-XR-um-cont-breakout-cfg {
  namespace "http://cisco.com/ns/yang/Cisco-IOS-XR-um-cont-breakout-cfg";
  prefix um-cont-breakout-cfg;

  import Cisco-IOS-XR-types {
    prefix xr;
  }
  import Cisco-IOS-XR-um-interface-cfg {
    prefix a1;
  }
  import tailf-common {
    prefix tailf;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR cont-breakout package configuration.
     
     This YANG module augments the
     modules with configuration data.
     
     Copyright (c) 2020, 2022 by Cisco Systems, Inc.
     All rights reserved.";

  revision 2022-06-01 {
    description
      "Adjusted controller augmentation hierarchy";
    semver:module-version "1.0.0";
  }
  revision 2020-12-14 {
    description
      "Initial release";
    semver:module-version "1.0.0";
  }

  feature optics {
    description
      "optics";
  }

  grouping CONT-BODY {
    leaf breakout {
      when "../a1:controller-name[starts-with(text(),'Optics')]" {
        tailf:dependency "../a1:controller-name";
      }
      if-feature "optics";
      type xr:Cisco-ios-xr-string {
        length "1..800" {
          description
            "breakout mode: 4x10 | 4x25 | 2x50 | 8x50 | 4x100 | 3x100 | 2x100 | 1x100";
        }
      }
      description
        "Configure breakout mode";
    }
  }

  augment "/a1:controllers/a1:controller" {
    uses CONT-BODY;
  }
  augment "/a1:controllers/a1:controller-preconfigure" {
    uses CONT-BODY;
  }
}
