submodule Cisco-IOS-XR-ipsec-xr-oper-sub1 {
  belongs-to Cisco-IOS-XR-ipsec-xr-oper {
    prefix Cisco-IOS-XR-ipsec-xr-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR ipsec-xr package operational data.
     
     Copyright (c) 2013-2021 by Cisco Systems, Inc.
     All rights reserved.";

  revision 2021-09-24 {
    description
      "Initial yang support for ipsec oper.";
    semver:module-version "1.0.0";
  }
  revision 2019-04-05 {
    description
      "Establish semantic version baseline.";
  }
  revision 2015-11-09 {
    description
      "IOS XR 6.0 revision.";
  }

  grouping IPSEC-EDM-SA {
    description
      "IPSEC EDM SA";
    leaf spi {
      type uint32;
      description
        "sa spi";
    }
    leaf lifetime {
      type uint32;
      description
        "lifetime";
    }
    leaf rekey-time {
      type uint32;
      description
        "rekey time";
    }
    leaf prot {
      type string;
      description
        "sa protocol";
    }
    leaf encr {
      type string;
      description
        "encr algo";
    }
    leaf auth {
      type string;
      description
        "auth algo";
    }
  }

  grouping IPSEC-EDM-SA-PAIR {
    description
      "IPSEC EDM SA PAIR";
    container in-sa {
      description
        "Inbound sa";
      uses IPSEC-EDM-SA;
    }
    container out-sa {
      description
        "Outbound sa";
      uses IPSEC-EDM-SA;
    }
    leaf sa-id {
      type uint32;
      description
        "sa id";
    }
    leaf interface {
      type string;
      description
        "interface name";
    }
    leaf ifh {
      type uint32;
      description
        "interface handle";
    }
    leaf mode {
      type string;
      description
        "Ipsec mode";
    }
  }

  grouping IPSEC-EDM-INTERFACE-SAS {
    description
      "IPSEC EDM INTERFACE SAS";
    list sa {
      description
        "list of sa";
      uses IPSEC-EDM-SA-PAIR;
    }
  }
}
