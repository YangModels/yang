module Cisco-IOS-XR-um-cef-accounting-cfg {
  namespace "http://cisco.com/ns/yang/Cisco-IOS-XR-um-cef-accounting-cfg";
  prefix um-cef-accounting-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR cef-accounting package configuration.
     
     This YANG module augments the
     modules with configuration data.
     
     Copyright (c) 2021-2022 by Cisco Systems, Inc.
     All rights reserved.";

  revision 2022-06-21 {
    description
      "Added container hierarchical-load-balancing";
    semver:module-version "1.1.0";
  }
  revision 2021-02-10 {
    description
      "Initial release";
    semver:module-version "1.0.0";
  }

  container cef {
    description
      "CEF configuration";
    container adjacency {
      description
        "Adjacency configuration";
      container route {
        description
          "Adjacency route configuration";
        container override {
          description
            "Set override options for adjacency routes";
          container rib {
            presence "Indicates a rib node is configured.";
            description
              "Set options for adjacency routes overriding RIB routes";
          }
        }
      }
    }
    container pbts {
      description
        "PBTS configuration";
      container class {
        description
          "Forward class configuration";
        list forward-class {
          must
            "fallback-to/fallback-class-number or fallback-to/any or
             fallback-to/drop";
          key "forward-class-number";
          description
            "Forward Class number";
          leaf forward-class-number {
            type union {
              type enumeration {
                enum "any" {
                  value 8;
                  description
                    "Any forward class";
                }
              }
              type uint32 {
                range "0..7" {
                  description
                    "Forward Class number";
                }
              }
            }
            description
              "Forward Class number";
          }
          container fallback-to {
            description
              "Fallback to configuration";
            leaf-list fallback-class-number {
              type uint32 {
                range "0..7" {
                  description
                    "Fallback Class number";
                }
              }
              must "not(../any or ../drop)";
              max-elements "7";
              description
                "Fallback to configuration";
            }
            container any {
              must "not(../fallback-class-number or ../drop)";
              presence "Indicates a any node is configured.";
              description
                "Fallback to any class";
            }
            container drop {
              must "not(../any or ../fallback-class-number)";
              presence "Indicates a drop node is configured.";
              description
                "Fallback to drop";
            }
          }
        }
      }
    }
    container platform {
      description
        "Platform parameters";
      container lsm {
        description
          "Label-switched-multicast parameters";
        leaf frr-holdtime {
          type uint32 {
            range "3..180" {
              description
                "Time in seconds";
            }
          }
          description
            "Time to keep FRR slots programmed post FRR";
        }
      }
    }
    container retry {
      description
        "Retry parameters";
      leaf service-time {
        type uint32 {
          range "1..15000" {
            description
              "Time in msec";
          }
        }
        description
          "Retry service time (default 50 msec)";
      }
      leaf timeout {
        type uint32 {
          range "1..30000" {
            description
              "Time in msec";
          }
        }
        description
          "Retry timeout (default 15 msec)";
      }
      leaf syslog-timer {
        type uint32 {
          range "0..86400" {
            description
              "Time in seconds (default 120 seconds)";
          }
        }
        description
          "Syslog timer in seconds(default 120 seconds), 0 to disable";
      }
    }
    container encap-sharing {
      description
        "Disable MPLS encapsulation sharing";
      container disable {
        presence "Indicates a disable node is configured.";
        description
          "Use this in conjunction with BGP per-prefix label mode";
      }
    }
    container consistent-hashing {
      description
        "Load balancing consistent hashing";
      container auto-recovery {
        presence "Indicates a auto-recovery node is configured.";
        description
          "Automatically recover to previous hash state";
      }
    }
    container proactive-arp-nd {
      description
        "Proactive ARP/ND";
      container enable {
        presence "Indicates a enable node is configured.";
        description
          "Enable proactive ARP/ND feature";
      }
    }
    leaf ltrace-multiplier {
      type uint32 {
        range "1..16" {
          description
            "numeric value of the multiplier";
        }
      }
      description
        "ltrace multiplier";
    }
    container hierarchical-load-balancing {
      description
        "Hierarchical load balancing";
      container ecmp {
        presence "Indicates a ecmp node is configured.";
        description
          "ecmp hierarchical-load-balancing";
        leaf min-paths {
          type uint32 {
            range "1..128" {
              description
                "Number of paths. Warning: This configuration is disruptive";
            }
          }
          description
            "Minimum paths for qualifying HLB";
        }
      }
      container ucmp {
        presence "Indicates a ucmp node is configured.";
        description
          "ucmp hierarchical-load-balancing";
        leaf group-size {
          type uint32 {
            range "1..128" {
              description
                "Number of paths. Warning: This configuration is disruptive";
            }
          }
          description
            "UCMP group size for HLB";
        }
      }
    }
  }
  container accounting {
    presence "Indicates a accounting node is configured.";
    description
      "Enable accounting";
    container interfaces {
      presence "Indicates a interfaces node is configured.";
      description
        "Enable interfaces submode";
      container mpls {
        presence "Indicates a mpls node is configured.";
        description
          "Enable MPLS accounting";
        container ipv4 {
          description
            "Enable IPv4 accounting";
          container rsvp-te {
            presence "Indicates a rsvp-te node is configured.";
            description
              "Enable RSVP-TE accounting";
          }
        }
      }
      container segment-routing {
        description
          "Enable Segment-Routing (SR) accounting";
        container mpls {
          presence "Indicates a mpls node is configured.";
          description
            "Enable SR MPLS accounting";
          container ipv4 {
            presence "Indicates a ipv4 node is configured.";
            description
              "Enable IPv4 accounting";
          }
          container ipv6 {
            presence "Indicates a ipv6 node is configured.";
            description
              "Enable IPv6 accounting";
          }
        }
      }
    }
  }
}
