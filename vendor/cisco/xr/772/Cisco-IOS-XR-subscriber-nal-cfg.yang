module Cisco-IOS-XR-subscriber-nal-cfg {
  namespace "http://cisco.com/ns/yang/Cisco-IOS-XR-subscriber-nal-cfg";
  prefix subscriber-nal-cfg;

  import ietf-inet-types {
    prefix inet;
  }
  import ietf-yang-types {
    prefix yang;
  }
  import Cisco-IOS-XR-types {
    prefix xr;
  }
  import Cisco-IOS-XR-config-mda-cfg {
    prefix node;
  }
  import cisco-semver {
    prefix semver;
  }
  import Cisco-IOS-XR-ifmgr-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR subscriber-nal package configuration.
     
     This YANG module augments the
       Cisco-IOS-XR-ifmgr-cfg,
       Cisco-IOS-XR-config-mda-cfg
     modules with configuration data.
     
     Copyright (c) 2013-2022 by Cisco Systems, Inc.
     All rights reserved.";

  revision 2022-03-03 {
    description
      "Removed headless timer interval config CLI";
    semver:module-version "2.1.0";
  }
  revision 2021-09-28 {
    description
      "Augmented MDA common config schema
       2021-08-18
           Added support for tcp mss adjust config
       2021-07-13
           Added support for l2tp enable CLI
       2021-07-07
           Added support for pre-configuration.
       2021-05-05
           Added support for storing tr459 mode.
       2021-04-01
           NAL access interface config for LNS.";
    semver:module-version "2.0.0";
  }
  revision 2020-12-01 {
    description
      "NAL access interface config.";
    semver:module-version "1.0.0";
  }
  revision 2020-11-24 {
    description
      "Auto loopback primary address.";
  }
  revision 2019-04-05 {
    description
      "Establish semantic version baseline.";
  }
  revision 2015-11-09 {
    description
      "IOS XR 6.0 revision.";
  }

  grouping NODE-CFG {
    description
      "active/preconfigured nodes configuration";
    container subscriber-cnbng-nal-loc {
      presence "Indicates a subscriber-cnbng-nal-loc node is configured.";
      description
        "Table of SubscriberCnbngNalLoc";
      container nal-auto-lb-classes {
        description
          "Table of NALAutoLBClass";
        list nal-auto-lb-class {
          key "vrf-name";
          description
            "NAL Auto-Loopback configurations";
          container nal-auto-lb-int-classes {
            description
              "Table of NALAutoLBIntClass";
            list nal-auto-lb-int-class {
              key "nal-auto-lb-int-name";
              description
                "None";
              leaf nal-auto-lb-int-addr-class {
                type inet:ipv4-address-no-zone;
                description
                  "NAL auto-loopback Interface Primary-IP
                   address";
              }
              leaf nal-auto-lb-int-name {
                type xr:Interface-name;
                description
                  "NAL auto-loopback Interface";
              }
            }
          }
          leaf vrf-name {
            type xr:Cisco-ios-xr-string;
            description
              "Set constant string";
          }
        }
      }
      container subscriber-redundancy {
        presence "Indicates a subscriber-redundancy node is configured.";
        description
          "Subscriber redundancy configuration";
        container srg-groups {
          description
            "Table of SRGGroup";
          list srg-group {
            key "srg-group-name";
            description
              "SRG group configuration";
            container access-interfaces {
              presence "Indicates a access-interfaces node is configured.";
              description
                "Access interface list for this SRG Group";
              leaf enable {
                type empty;
                mandatory true;
                description
                  "Enable Access interface list for this SRG
                   Group. Deletion of this object also causes
                   deletion of all associated objects under
                   SRGGroupAccessIntfList.";
              }
              list access-interface {
                key "intf-name";
                description
                  "Access interface";
                leaf intf-name {
                  type xr:Interface-name;
                  description
                    "Interface name";
                }
                leaf intf-name-xr {
                  type xr:Interface-name;
                  mandatory true;
                  description
                    "Interface name";
                }
              }
            }
            leaf core-tracking-object {
              type xr:Cisco-ios-xr-string {
                length "1..32";
              }
              description
                "Core Tracking Object for this SRG Group";
            }
            leaf damping-timer {
              type uint32 {
                range "60..600";
              }
              units "second";
              description
                "Damping timer value for this SRG Group";
            }
            leaf metric-standby {
              type uint32 {
                range "1..1023";
              }
              description
                "Metric to be used when current role is
                 standby";
            }
            leaf route-tag {
              type uint32 {
                range "1..4294967295";
              }
              description
                "Route tag for subnets belonging to this
                 group";
            }
            leaf metric-active {
              type uint32 {
                range "1..1023";
              }
              description
                "Metric to be used when current role is
                 active";
            }
            leaf fast-switchover-disable {
              type uint32;
              description
                "Disable fast switchover for this SRG group";
            }
            leaf access-tracking-object {
              type xr:Cisco-ios-xr-string {
                length "1..32";
              }
              description
                "Access Tracking Object for this SRG Group";
            }
            leaf vmac-address {
              type yang:mac-address;
              description
                "Virtual MAC address for this SRG Group";
            }
            leaf srg-group-name {
              type xr:Cisco-ios-xr-string {
                length "1..64";
              }
              description
                "SRG Group ID";
            }
          }
        }
        leaf srg-damping-timer {
          type uint32 {
            range "60..600";
          }
          units "second";
          description
            "Timer value (in secs)";
        }
        leaf enable {
          type empty;
          mandatory true;
          description
            "Enable Subscriber redundancy configuration.
             Deletion of this object also causes deletion
             of all associated objects under
             SubscriberRedundancy.";
        }
        leaf nal-stats-request-rate {
          type uint32 {
            range "10..2000";
          }
          description
            "rate of stats request(Restricted to
             devlopment)";
        }
      }
      container nal-trans-cp-server-cfg {
        description
          "None";
        leaf nal-cp-primary-srv-cfg {
          type inet:ipv4-address-no-zone;
          description
            "IPv4 address of the CP's primary-server";
        }
      }
      container groups {
        description
          "Table of Group";
        list group {
          key "group-id";
          description
            "CnBNG NAL Group configuration";
          container interfaces {
            description
              "Table of Interface";
            list interface {
              key "interface-name interface-id";
              description
                "Interface for this Group";
              leaf interface-name {
                type xr:Interface-name;
                description
                  "Interface name";
              }
              leaf interface-id {
                type uint32 {
                  range "1..65535";
                }
                description
                  "ID for the interface to be mapped on to
                   slave";
              }
              leaf mac-address {
                type yang:mac-address;
                mandatory true;
                description
                  "MAC address";
              }
            }
          }
          leaf description {
            type string {
              length "1..256";
            }
            description
              "Description for this Group";
          }
          leaf tracking-object {
            type string;
            description
              "Core Tracking Object for this Group";
          }
          leaf group-id {
            type uint32 {
              range "1..4000";
            }
            description
              "Group ID";
          }
        }
      }
      container nal-trans-up-server-cfg {
        description
          "None";
        leaf prefix-string {
          type inet:ipv4-address-no-zone;
          description
            "IPv4 address for the UP-Server source
             connection";
        }
        leaf intf-name {
          type xr:Interface-name;
          description
            "Source Interface";
        }
        leaf gtp-port-num {
          type uint32 {
            range "15002..15051";
          }
          description
            "UP-server source GTP port-number";
        }
        leaf pcfp-port-num {
          type uint32 {
            range "15002..15051";
          }
          description
            "UP-server source PFCP port-number";
        }
        leaf vrf-name {
          type xr:Cisco-ios-xr-string {
            length "1..32";
          }
          description
            "UP server's VRF Name";
        }
      }
      leaf nal-host-name {
        type xr:Cisco-ios-xr-string {
          length "1..64";
        }
        description
          "NAL Host-name";
      }
      leaf nal-ipoe-fsol-flow-ctrl {
        type uint32 {
          range "50..400";
        }
        description
          "None";
      }
      leaf nal-max-sub-create-in-progress {
        type uint32 {
          range "200..800";
        }
        description
          "Create request range";
      }
      leaf nal-pppoe-fsol-flow-ctrl {
        type uint32 {
          range "50..400";
        }
        description
          "None";
      }
      leaf nal-route-summary-tag {
        type uint32 {
          range "1..4294967295";
        }
        description
          "Tag value";
      }
      leaf enable-tr459-mode {
        type uint32;
        description
          "Set constant integer";
      }
      leaf nal-max-delete-batch-timer {
        type uint32 {
          range "200..600";
        }
        description
          "Subscriber bulk disconnect timer timeout range";
      }
      leaf nal-enable-sec-addr-upd {
        type uint32;
        description
          "Enable secondary address update";
      }
      leaf description {
        type string {
          length "1..256";
        }
        description
          "Config User-description";
      }
      leaf nal-up-cp-stats-flow-ctrl {
        type uint32 {
          range "20..500";
        }
        description
          "limit";
      }
      leaf nall2tp-tcp-mss-config {
        type uint32 {
          range "1280..1460";
        }
        description
          "Tcp mss adjust range";
      }
      leaf nal-trace-level {
        type uint32;
        description
          "Set constant integer";
      }
      leaf nal-disconnect-history-file-logging {
        type uint32;
        description
          "Set constant integer";
      }
      leaf disable-secondary-address-notification {
        type uint32;
        description
          "Set constant integer";
      }
      leaf nal-max-delete-batch-size {
        type uint32 {
          range "600..1000";
        }
        description
          "Subscriber bulk disconnect range";
      }
      leaf nal-cp-assoc-retry-cnt {
        type uint32 {
          range "5..20";
        }
        description
          "Retry count";
      }
      leaf nall2tp-subscriber-config {
        type uint32;
        description
          "Set constant integer";
      }
      leaf spa-request-response-history-file-logging {
        type uint32;
        description
          "Set constant integer";
      }
      leaf nal-max-sub-delete-in-progress {
        type uint32 {
          range "2000..4000";
        }
        description
          "Delete request range";
      }
      leaf nal-max-sub-update-in-progress {
        type uint32 {
          range "600..1400";
        }
        description
          "Update request range";
      }
      leaf nal-up-cp-notif-flow-ctrl {
        type uint32 {
          range "20..400";
        }
        description
          "limit";
      }
      leaf enable {
        type empty;
        mandatory true;
        description
          "Enable Location Specification. Deletion of this
           object also causes deletion of all associated
           objects under SubscriberCnbngNalLoc.";
      }
    }
  }

  augment "/a1:interface-configurations/a1:interface-configuration" {
    description
      "This augment extends the configuration data of
       'Cisco-IOS-XR-ifmgr-cfg'";
    list cnbng-nal-ip-subscriber {
      key "ip-sub";
      description
        "None";
      leaf enable {
        type empty;
        description
          "Enable None. Deletion of this object also
           causes deletion of all associated objects under
           CnbngNalIpSubscriber.";
      }
      leaf ip-sub {
        type xr:Cisco-ios-xr-string;
        description
          "Set string";
      }
      list cnbng-nal-ipv4-sub-enable {
        key "ipv4 ipv4l2-conn";
        description
          "None";
        leaf enable {
          type empty;
          description
            "Enable None. Deletion of this object also
             causes deletion of all associated objects
             under CnbngNalIpv4SubEnable.";
        }
        leaf cnbng-nal-ipv4-sub-init-dhcp {
          type empty;
          description
            "Enable";
        }
        leaf ipv4 {
          type xr:Cisco-ios-xr-string;
          description
            "Set string";
        }
        leaf ipv4l2-conn {
          type xr:Cisco-ios-xr-string;
          description
            "Set string";
        }
      }
      list cnbng-nal-ipv6-sub-enable {
        key "ipv6 ipv6l2-conn";
        description
          "None";
        leaf cnbng-nal-ipv6-sub-init-dhcp {
          type empty;
          description
            "Enable";
        }
        leaf enable {
          type empty;
          description
            "Enable None. Deletion of this object also
             causes deletion of all associated objects
             under CnbngNalIpv6SubEnable.";
        }
        leaf ipv6 {
          type xr:Cisco-ios-xr-string;
          description
            "Set string";
        }
        leaf ipv6l2-conn {
          type xr:Cisco-ios-xr-string;
          description
            "Set string";
        }
      }
    }
  }
  augment "/a1:interface-configurations/a1:interface-configuration" {
    description
      "This augment extends the configuration data of
       'Cisco-IOS-XR-ifmgr-cfg'";
    container cnbng-nal-pppoe-subscriber {
      description
        "None";
      leaf pppoe {
        type uint32;
        description
          "Set constant integer";
      }
      leaf bba-group {
        type string;
        description
          "The bba-group to use";
      }
    }
  }
  augment "/a1:interface-configurations/a1:interface-configuration" {
    description
      "This augment extends the configuration data of
       'Cisco-IOS-XR-ifmgr-cfg'";
    leaf cnbng-nal-lns-subscriber {
      type empty;
      description
        "Enable";
    }
  }
  augment "/node:active-nodes/node:active-node" {
    description
      "This augment extends active nodes configuration";
    uses NODE-CFG;
  }
  augment "/node:preconfigured-nodes/node:preconfigured-node" {
    description
      "This augment extends preconfigured nodes
       configuration";
    uses NODE-CFG;
  }
}
