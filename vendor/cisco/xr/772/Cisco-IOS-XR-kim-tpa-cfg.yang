module Cisco-IOS-XR-kim-tpa-cfg {
  namespace "http://cisco.com/ns/yang/Cisco-IOS-XR-kim-tpa-cfg";
  prefix kim-tpa-cfg;

  import Cisco-IOS-XR-types {
    prefix xr;
  }
  import cisco-semver {
    prefix semver;
  }
  import ietf-inet-types {
    prefix inet;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR kim-tpa package configuration.
     
     This model is deprecated and will be replaced by
     Cisco-IOS-XR-linux-xlnc-cfg.yang which will provide the
     compatible functionalities.
     
     This module contains definitions
     for the following management objects:
       tpa: tpa configuration commands. This configuration is
         deprecated and will be removed in a future release.
     
     Copyright (c) 2013-2022 by Cisco Systems, Inc.
     All rights reserved.";

  revision 2022-05-20 {
    description
      "Added deprecation notice";
    semver:module-version "2.0.0";
  }
  revision 2019-12-17 {
    description
      "Option to disable stats synchronization added.";
    semver:module-version "1.1.0";
  }
  revision 2019-04-05 {
    description
      "Establish semantic version baseline.";
    semver:module-version "1.0.0";
  }
  revision 2018-07-27 {
    description
      "Added support for protection configuration";
  }
  revision 2017-09-07 {
    description
      "Fixed type translation error.";
  }
  revision 2015-11-09 {
    description
      "IOS XR 6.0 revision.";
  }

  typedef Ip-protocol {
    type enumeration {
      enum "tcp" {
        value 6;
        description
          "Transmission Control Protocol, RFC 793";
      }
      enum "udp" {
        value 17;
        description
          "User Datagram Protocol, RFC 768";
      }
    }
    description
      "Ip protocol";
  }

  grouping UPDATE-SOURCE {
    description
      "Common node of ipv4, ipv6";
    container update-source {
      status deprecated;
      description
        "Interface used for Source Address. This
         configuration is deprecated and will be removed
         in a future release.";
      leaf interface-name {
        type xr:Interface-name;
        must "not(../active-management)";
        description
          "Interface name for source address";
      }
      leaf active-management {
        type empty;
        must "not(../interface-name)";
        description
          "Use the management port on the Active RP";
      }
    }
  }

  grouping PROTECTION {
    description
      "Common node of ipv4, ipv6";
    container allow-entries {
      description
        "Traffic protection configuration";
      list allow-entry {
        key "protocol local-port";
        description
          "Allow traffic matching a filter";
        leaf protocol {
          type Ip-protocol;
          description
            "L4 protocol";
        }
        leaf local-port {
          type xr:Cisco-ios-xr-port-number;
          description
            "Local port";
        }
      }
      list allow-entry-local-address {
        key "protocol local-port local-address";
        description
          "Allow traffic matching a filter";
        leaf protocol {
          type Ip-protocol;
          description
            "L4 protocol";
        }
        leaf local-port {
          type xr:Cisco-ios-xr-port-number;
          description
            "Local port";
        }
        leaf local-address {
          type inet:ip-prefix;
          description
            "local prefix/length";
        }
      }
      list allow-entry-remote-address {
        key "protocol local-port remote-address";
        description
          "Allow traffic matching a filter";
        leaf protocol {
          type Ip-protocol;
          description
            "L4 protocol";
        }
        leaf local-port {
          type xr:Cisco-ios-xr-port-number;
          description
            "Local port";
        }
        leaf remote-address {
          type inet:ip-prefix;
          description
            "remote prefix/length";
        }
      }
      list allow-entry-local-address-remote-address {
        key "protocol local-port local-address remote-address";
        description
          "Allow traffic matching a filter";
        leaf protocol {
          type Ip-protocol;
          description
            "L4 protocol";
        }
        leaf local-port {
          type xr:Cisco-ios-xr-port-number;
          description
            "Local port";
        }
        leaf local-address {
          type inet:ip-prefix;
          description
            "local prefix/length";
        }
        leaf remote-address {
          type inet:ip-prefix;
          description
            "remote prefix/length";
        }
      }
      list allow-entry-interface-name {
        key "protocol local-port interface-name";
        description
          "Allow traffic matching a filter";
        leaf protocol {
          type Ip-protocol;
          description
            "L4 protocol";
        }
        leaf local-port {
          type xr:Cisco-ios-xr-port-number;
          description
            "Local port";
        }
        leaf interface-name {
          type xr:Interface-name;
          description
            "Interface name";
        }
      }
      list allow-entry-local-address-interface-name {
        key "protocol local-port local-address interface-name";
        description
          "Allow traffic matching a filter";
        leaf protocol {
          type Ip-protocol;
          description
            "L4 protocol";
        }
        leaf local-port {
          type xr:Cisco-ios-xr-port-number;
          description
            "Local port";
        }
        leaf local-address {
          type inet:ip-prefix;
          description
            "local prefix/length";
        }
        leaf interface-name {
          type xr:Interface-name;
          description
            "Interface name";
        }
      }
      list allow-entry-remote-address-interface-name {
        key "protocol local-port remote-address interface-name";
        description
          "Allow traffic matching a filter";
        leaf protocol {
          type Ip-protocol;
          description
            "L4 protocol";
        }
        leaf local-port {
          type xr:Cisco-ios-xr-port-number;
          description
            "Local port";
        }
        leaf remote-address {
          type inet:ip-prefix;
          description
            "remote prefix/length";
        }
        leaf interface-name {
          type xr:Interface-name;
          description
            "Interface name";
        }
      }
      list allow-entry-local-address-remote-address-interface-name {
        key "protocol local-port local-address remote-address interface-name";
        description
          "Allow traffic matching a filter";
        leaf protocol {
          type Ip-protocol;
          description
            "L4 protocol";
        }
        leaf local-port {
          type xr:Cisco-ios-xr-port-number;
          description
            "Local port";
        }
        leaf local-address {
          type inet:ip-prefix;
          description
            "local prefix/length";
        }
        leaf remote-address {
          type inet:ip-prefix;
          description
            "remote prefix/length";
        }
        leaf interface-name {
          type xr:Interface-name;
          description
            "Interface name";
        }
      }
    }
  }

  grouping DEFAULT-ROUTE {
    description
      "Common node of ipv4, ipv6";
    leaf default-route {
      type string;
      status deprecated;
      description
        "Default interface used for routing. This
         configuration is deprecated and will be removed
         in a future release.";
    }
  }

  grouping EGRESS-UPDATE-SOURCE {
    description
      "Common node of ipv4, ipv6";
    container interface-names {
      status deprecated;
      description
        "Interface used for source address for egress
         interface. This configuration is deprecated and
         will be removed in a future release.";
      list interface-name {
        key "interface-name";
        status deprecated;
        description
          "Egress interface name";
        leaf egress-interface-source {
          type xr:Interface-name;
          status deprecated;
          description
            "Interface name for source address";
        }
        leaf interface-name {
          type xr:Cisco-ios-xr-string;
          description
            "Interface";
        }
      }
    }
  }

  container tpa {
    status deprecated;
    description
      "This model is deprecated and will be replaced by
       Cisco-IOS-XR-linux-xlnc-cfg.yang which will
       provide the compatible functionalities.  tpa
       configuration commands. This configuration is
       deprecated and will be removed in a future
       release.";
    container vrf-names {
      status deprecated;
      description
        "VRF container. This configuration is deprecated
         and will be removed in a future release.";
      list vrf-name {
        key "vrf-name";
        status deprecated;
        description
          "VRF name";
        container east-west-names {
          status deprecated;
          description
            "EastWest container. This configuration is
             deprecated and will be removed in a future
             release.";
          list east-west-name {
            key "east-west-name";
            status deprecated;
            description
              "East West interface";
            leaf east-west-name {
              type xr:Cisco-ios-xr-string;
              description
                "Interface";
            }
            leaf vrf {
              type string;
              description
                "VRF name";
            }
            leaf interface {
              type string;
              description
                "Interface";
            }
          }
        }
        container address-family {
          status deprecated;
          description
            "Address family. This configuration is
             deprecated and will be removed in a future
             release.";
          container ipv6 {
            status deprecated;
            description
              "IPv6 configuration";
            uses DEFAULT-ROUTE;
            uses EGRESS-UPDATE-SOURCE;
            uses PROTECTION;
            uses UPDATE-SOURCE;
          }
          container ipv4 {
            status deprecated;
            description
              "IPv4 configuration";
            uses DEFAULT-ROUTE;
            uses EGRESS-UPDATE-SOURCE;
            uses PROTECTION;
            uses UPDATE-SOURCE;
          }
        }
        leaf disable {
          type empty;
          status deprecated;
          description
            "Disable routes and interfaces. This
             configuration is deprecated and will be
             removed in a future release.";
        }
        leaf vrf-name {
          type xr:Cisco-ios-xr-string {
            length "1..32";
          }
          description
            "VRF name";
        }
      }
    }
    container logging {
      status deprecated;
      description
        "Third party app logging. This configuration is
         deprecated and will be removed in a future
         release.";
      container kim {
        status deprecated;
        description
          "KIM logging";
        leaf rotation-max {
          type uint32;
          status deprecated;
          description
            "How many log rotation files to keep";
        }
        leaf file-size-max-kb {
          type uint32;
          units "kilobyte";
          status deprecated;
          description
            "Size in Kilobytes of the log file";
        }
      }
    }
    container statistics {
      status deprecated;
      description
        "Statistics. This configuration is deprecated and
         will be removed in a future release.";
      leaf disable {
        type empty;
        status deprecated;
        description
          "set this item to disable stats collection. This
           configuration is deprecated and will be removed
           in a future release.";
      }
      leaf max-intf-events {
        type uint32;
        status deprecated;
        description
          "How many interface events to record";
      }
      leaf max-lpts-events {
        type uint32;
        status deprecated;
        description
          "How many LPTS events to record";
      }
      leaf statistics-update-frequency {
        type uint32;
        units "second";
        status deprecated;
        description
          "Statistics update frequency into Linux";
      }
    }
  }
}
