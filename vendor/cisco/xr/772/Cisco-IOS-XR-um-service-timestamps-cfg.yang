module Cisco-IOS-XR-um-service-timestamps-cfg {
  namespace "http://cisco.com/ns/yang/Cisco-IOS-XR-um-service-timestamps-cfg";
  prefix um-service-timestamps-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR service-timestamps package configuration.
     
     This YANG module augments the
     modules with configuration data.
     
     Copyright (c) 2020 by Cisco Systems, Inc.
     All rights reserved.";

  revision 2020-10-06 {
    description
      "Initial release";
    semver:module-version "1.0.0";
  }

  container service {
    description
      "Modify use of network based services";
    container timestamps {
      description
        "Timestamp debug/log messages";
      container debug {
        description
          "Timestamp debug messages";
        container datetime {
          description
            "Timestamp with date and time";
          container localtime-only {
            must "not(../localtime or ../msec or ../show-timezone or ../year)";
            presence "Indicates a localtime-only node is configured.";
            description
              "Timestamp with date and time";
          }
          container localtime {
            presence "Indicates a localtime node is configured.";
            description
              "Use local time zone for timestamps";
          }
          container msec {
            presence "Indicates a msec node is configured.";
            description
              "Include milliseconds in timestamp";
          }
          container show-timezone {
            presence "Indicates a show-timezone node is configured.";
            description
              "Add time zone information to timestamp";
          }
          container year {
            presence "Indicates a year node is configured.";
            description
              "Add year to timestamp";
          }
        }
        container uptime {
          presence "Indicates a uptime node is configured.";
          description
            "Timestamp with systime uptime";
        }
        container disable {
          presence "Indicates a disable node is configured.";
          description
            "Disable timestamp debug messages";
        }
      }
      container log {
        description
          "Timestamp log messages";
        container datetime {
          description
            "Timestamp with date and time";
          container localtime-only {
            presence "Indicates a localtime-only node is configured.";
            description
              "Timestamp with date and time";
          }
          container localtime {
            presence "Indicates a localtime node is configured.";
            description
              "Use local time zone for timestamps";
          }
          container msec {
            presence "Indicates a msec node is configured.";
            description
              "Include milliseconds in timestamp";
          }
          container show-timezone {
            presence "Indicates a show-timezone node is configured.";
            description
              "Add time zone information to timestamp";
          }
          container year {
            presence "Indicates a year node is configured.";
            description
              "Add Year to timestamp";
          }
        }
        container uptime {
          presence "Indicates a uptime node is configured.";
          description
            "Timestamp with systime uptime";
        }
        container disable {
          presence "Indicates a disable node is configured.";
          description
            "Disable timestamp log messages";
        }
      }
    }
  }
}
