module Cisco-IOS-XR-um-subscriber-pta-cfg {
  namespace "http://cisco.com/ns/yang/Cisco-IOS-XR-um-subscriber-pta-cfg";
  prefix um-subscriber-pta-cfg;

  import Cisco-IOS-XR-um-subscriber-cfg {
    prefix a1;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR subscriber-pta package configuration.
     
     This YANG module augments the
     modules with configuration data.
     
     Copyright (c) 2021 by Cisco Systems, Inc.
     All rights reserved.";

  revision 2021-02-19 {
    description
      "Initial release";
    semver:module-version "1.0.0";
  }

  augment "/a1:subscriber" {
    container pta {
      description
        "pta subscriber configuration";
      container tcp {
        description
          "tcp";
        leaf mss-adjust {
          type uint32 {
            range "1280..1536" {
              description
                "TCP MSS Adjust maximum segment size";
            }
          }
          description
            "Set the TCP segment size to be adjusted";
        }
      }
    }
  }
}
