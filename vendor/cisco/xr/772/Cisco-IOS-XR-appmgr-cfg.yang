module Cisco-IOS-XR-appmgr-cfg {
  namespace "http://cisco.com/ns/yang/Cisco-IOS-XR-appmgr-cfg";
  prefix appmgr-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR appmgr package configuration.
     
     This module contains definitions
     for the following management objects:
       appmgr: Appmgr configuration data
     
     Copyright (c) 2013-2022 by Cisco Systems, Inc.
     All rights reserved.";

  revision 2022-03-01 {
    description
      "Adding username configuration for process scripts";
    semver:module-version "2.0.0";
  }
  revision 2021-04-04 {
    description
      "Support for secure vault tuple.";
    semver:module-version "1.1.0";
  }
  revision 2021-02-15 {
    description
      "Support for process scripts.";
  }
  revision 2019-04-05 {
    description
      "Establish semantic version baseline.";
  }
  revision 2015-11-09 {
    description
      "IOS XR 6.0 revision.";
  }

  typedef App-restart-policy {
    type enumeration {
      enum "never" {
        value 1;
        description
          "Do not automatically restart the app.";
      }
      enum "on-failure" {
        value 2;
        description
          "Restart the app if it exits due to an error.";
      }
      enum "always" {
        value 3;
        description
          "Always restart the app if it stops. (the
           default)";
      }
      enum "unless-stopped" {
        value 4;
        description
          "Similar to always, except that when the app is
           stopped (manually or otherwise), it is not
           restarted.";
      }
      enum "unless-errored" {
        value 5;
        description
          "Similar to always, except that when the app is
           in error state, it is not restarted.";
      }
    }
    description
      "App restart policy";
  }

  typedef App {
    type enumeration {
      enum "docker" {
        value 1;
        description
          "Docker application";
      }
    }
    description
      "App";
  }

  container appmgr {
    description
      "Appmgr configuration data";
    container process-scripts {
      description
        "Table of process scripts";
      list process-script {
        key "name";
        description
          "Process script configuration";
        container restart-policy {
          description
            "Application restart policy";
          leaf restart {
            type App-restart-policy;
            description
              "Appliction restart policy";
          }
          leaf max-retries {
            when "../restart = 'on-failure'" {
              description
                "../Restart = on-failure";
            }
            type uint32 {
              range "1..10";
            }
            description
              "Maximum retries to attempt";
          }
        }
        leaf arguments {
          type string {
            length "1..1024";
          }
          description
            "Process script argument string";
        }
        leaf username {
          type string {
            length "2..253";
          }
          description
            "Username to execute process script under";
        }
        leaf executable {
          type string {
            length "1..255";
            pattern "[a-zA-Z0-9][a-zA-Z0-9_.-]+";
          }
          description
            "Process script executable name";
        }
        leaf name {
          type string {
            length "1..255";
            pattern "^[a-zA-Z0-9][a-zA-Z0-9_.-]+$";
          }
          description
            "Application identifier";
        }
      }
    }
    container applications {
      description
        "Table of applications";
      list application {
        key "name";
        description
          "Application configuration";
        container activate {
          description
            "Application activation";
          leaf type {
            type App;
            description
              "Appliction type - type of application to be
               deployed";
          }
          leaf source {
            type string {
              length "1..255";
              pattern "^[a-zA-Z0-9][a-zA-Z0-9_:.-]+$";
            }
            description
              "Appliction source - name of source";
          }
          leaf command {
            type string {
              length "1..1024";
            }
            description
              "Command to be run inside the container -
               Docker Only ";
          }
          leaf run-options {
            type string {
              length "1..1024";
            }
            description
              "Docker run options as a string - Docker Only";
          }
          leaf svault-options {
            type string {
              length "1..255";
              pattern "^[a-zA-Z_][a-zA-Z_0-9:.-]*";
            }
            description
              "Secure Vault Profile as a string - Docker
               Only";
          }
        }
        leaf name {
          type string {
            length "1..255";
            pattern "^[a-zA-Z0-9][a-zA-Z0-9_.-]+$";
          }
          description
            "Application identifier";
        }
      }
    }
  }
}
