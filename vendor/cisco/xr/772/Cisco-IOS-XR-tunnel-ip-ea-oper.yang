module Cisco-IOS-XR-tunnel-ip-ea-oper {
  namespace "http://cisco.com/ns/yang/Cisco-IOS-XR-tunnel-ip-ea-oper";
  prefix tunnel-ip-ea-oper;

  import ietf-inet-types {
    prefix inet;
  }
  import Cisco-IOS-XR-types {
    prefix xr;
  }
  import cisco-semver {
    prefix semver;
  }
  import Cisco-IOS-XR-tunnel-gre-datatypes {
    prefix dt1;
  }
  include Cisco-IOS-XR-tunnel-ip-ea-oper-sub1 {
    revision-date 2022-02-26;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR tunnel-ip-ea package operational data.
     
     This module contains definitions
     for the following management objects:
       tunnel-ip-ea: Tunnel IP EA parameters
     
     Copyright (c) 2013-2022 by Cisco Systems, Inc.
     All rights reserved.";

  revision 2022-02-26 {
    description
      "Added a new bag for source direct";
    semver:module-version "2.0.0";
  }
  revision 2019-04-05 {
    description
      "Establish semantic version baseline.";
    semver:module-version "1.0.1";
  }
  revision 2015-11-09 {
    description
      "IOS XR 6.0 revision.";
  }

  container tunnel-ip-ea {
    config false;
    description
      "Tunnel IP EA parameters";
    container nodes {
      description
        "Node table for node-specific operational data";
      list node {
        key "node-name";
        description
          "Node-specific data for a particular node";
        container summary {
          description
            "EA summary information";
          uses TUNL-IP-EA-SUM;
        }
        container endpoints {
          description
            "GRE EA DB endpoints DB";
          list endpoint {
            description
              "GRE EA DB endpoints DB";
            leaf tunnel-id {
              type dt1:Tunl-id-range;
              description
                "Tunnel ID";
            }
            leaf transport-ip-address {
              type inet:ip-address-no-zone;
              description
                "Transport IP Address";
            }
            leaf overlay-ip-address {
              type inet:ip-address-no-zone;
              description
                "Overlay IP Address";
            }
            uses TUNL-P2MP-EA-EDM-TED-DB-ARRAY;
          }
        }
        container shared-memory-summary {
          description
            "EA shared memory information";
          uses TUNL-GRE-EA-SHM-EDM;
        }
        container qual-table {
          description
            "EA QT parameters";
          container tunnel-ids {
            description
              "Tunnel ID list";
            list tunnel-id {
              key "tid";
              description
                "Tunnel interface id value";
              leaf tid {
                type dt1:Tunl-id-range;
                description
                  "Tunnel ID";
              }
              uses TUNL-IP-EA-EDM;
            }
          }
          container qual-table-params {
            description
              "Qualification Table Parameter list";
            list qual-table-param {
              description
                "Qualification Table parameters";
              leaf source-address {
                type inet:ip-address-no-zone;
                description
                  "Source IP address";
              }
              leaf destination-address {
                type inet:ip-address-no-zone;
                description
                  "Destination IP address";
              }
              leaf rsi-table-id {
                type uint32 {
                  range "0..4294967295";
                }
                description
                  "RSI Table ID";
              }
              leaf tunnel-key {
                type uint32 {
                  range "0..4294967295";
                }
                description
                  "TunnelKey";
              }
              leaf tunnel-mode {
                type dt1:Tunl-mode-enum;
                description
                  "Tunnel Mode";
              }
              uses TUNL-IP-EA-EDM;
            }
          }
        }
        container source-direct {
          description
            "EA source direct address information";
          uses TUNL-GRE-EA-SRC-DIRECT-ARRAY;
        }
        container database {
          description
            "EA database parameters";
          container interface-names {
            description
              "Interface Names List";
            list interface-name {
              key "ifname";
              description
                "Interface Name";
              leaf ifname {
                type xr:Interface-name;
                description
                  "Tunnel Interface Name";
              }
              uses TUNL-IP-EA-EDM;
            }
          }
          container tunnel-ids {
            description
              "Tunnel ID list";
            list tunnel-id {
              key "tid";
              description
                "Tunnel ID";
              leaf tid {
                type dt1:Tunl-id-range;
                description
                  "Tunnel ID";
              }
              uses TUNL-IP-EA-EDM;
            }
          }
        }
        leaf node-name {
          type xr:Node-id;
          description
            "Node";
        }
      }
    }
  }
}
