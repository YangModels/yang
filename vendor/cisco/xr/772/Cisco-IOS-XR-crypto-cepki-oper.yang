module Cisco-IOS-XR-crypto-cepki-oper {
  namespace "http://cisco.com/ns/yang/Cisco-IOS-XR-crypto-cepki-oper";
  prefix crypto-cepki-oper;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR crypto-cepki package operational data.
     
     This module contains definitions
     for the following management objects:
       crypto-certificate-authority: Public Key Infrastructure
         Related Information
     
     Copyright (c) 2013-2022 by Cisco Systems, Inc.
     All rights reserved.";

  revision 2022-04-06 {
    description
      "Added serial number and fingerprint for ca.";
    semver:module-version "1.1.0";
  }
  revision 2019-04-05 {
    description
      "Establish semantic version baseline.";
    semver:module-version "1.0.0";
  }
  revision 2015-11-09 {
    description
      "IOS XR 6.0 revision.";
  }

  grouping CERTIFICATE-EXPIRES-ON {
    description
      "Common node of certificate-authority-certificate,
       router-certificate, router-signature-certificate,
       router-encryption-certificate";
    leaf certificate-expires-on {
      type uint64;
      units "second";
      description
        "Valid before date of the Certificate, in seconds
         since 00:00:00 UTC, January 1, 1970";
    }
  }

  grouping SERIAL-NUM {
    description
      "Common node of certificate-authority-certificate,
       router-certificate, router-signature-certificate,
       router-encryption-certificate";
    leaf serial-num {
      type string;
      description
        "Serial number of the Certificate";
    }
  }

  grouping ISSUER {
    description
      "Common node of certificate-authority-certificate,
       router-certificate, router-signature-certificate,
       router-encryption-certificate";
    leaf issuer {
      type string;
      description
        "Issuer Name of the Certificate";
    }
  }

  grouping FINGER-PRINT {
    description
      "Common node of certificate-authority-certificate,
       router-certificate, router-signature-certificate,
       router-encryption-certificate";
    leaf finger-print {
      type string;
      description
        "SHA1 Fingerprint of the Certificate";
    }
  }

  grouping CRL-DISTRIBUTION-POINT-TABLE {
    description
      "Common node of certificate-authority-certificate,
       router-certificate, router-signature-certificate,
       router-encryption-certificate";
    container crl-distribution-points {
      description
        "Router Certificates CRLDistributionPoint Table";
      list crl-distribution-point {
        key "index";
        description
          "Certificate CRLDistributionPoint Instance";
        leaf index {
          type uint32;
          description
            "CDP Entry Index";
        }
        leaf cdp-content {
          type string;
          mandatory true;
          description
            "CRLDistributionPoint Content";
        }
      }
    }
  }

  grouping CERTIFICATE-VALID-FROM {
    description
      "Common node of certificate-authority-certificate,
       router-certificate, router-signature-certificate,
       router-encryption-certificate";
    leaf certificate-valid-from {
      type uint64;
      units "second";
      description
        "Valid from date of the Certificate, in seconds
         since 00:00:00 UTC, January 1, 1970";
    }
  }

  grouping SUBJECT {
    description
      "Common node of certificate-authority-certificate,
       router-certificate, router-signature-certificate,
       router-encryption-certificate";
    leaf subject {
      type string;
      description
        "Subject Name of the Certificate";
    }
  }

  container crypto-certificate-authority {
    config false;
    description
      "Public Key Infrastructure Related Information";
    container trustpoints {
      description
        "CA Trustpoint Table Information";
      list trustpoint {
        key "name";
        description
          "Certificate Information for a particular
           Trustpoint";
        container router-certificate {
          description
            "Router Certificate Attributes";
          uses SUBJECT;
          uses CERTIFICATE-VALID-FROM;
          uses CRL-DISTRIBUTION-POINT-TABLE;
          uses CERTIFICATE-EXPIRES-ON;
          uses SERIAL-NUM;
          uses FINGER-PRINT;
          uses ISSUER;
        }
        container router-encryption-certificate {
          description
            "Router Encryption Certificate Attributes";
          uses SUBJECT;
          uses CERTIFICATE-VALID-FROM;
          uses CRL-DISTRIBUTION-POINT-TABLE;
          uses CERTIFICATE-EXPIRES-ON;
          uses SERIAL-NUM;
          uses FINGER-PRINT;
          uses ISSUER;
        }
        container router-signature-certificate {
          description
            "Router Signature Certificate Attributes";
          uses SUBJECT;
          uses CERTIFICATE-VALID-FROM;
          uses CRL-DISTRIBUTION-POINT-TABLE;
          uses CERTIFICATE-EXPIRES-ON;
          uses SERIAL-NUM;
          uses FINGER-PRINT;
          uses ISSUER;
        }
        container certificate-authority-certificate {
          description
            "Certificate Authority Certificate Attributes";
          uses SUBJECT;
          uses CERTIFICATE-VALID-FROM;
          uses CRL-DISTRIBUTION-POINT-TABLE;
          uses CERTIFICATE-EXPIRES-ON;
          uses SERIAL-NUM;
          uses FINGER-PRINT;
          uses ISSUER;
        }
        leaf name {
          type xr:Cisco-ios-xr-string;
          description
            "The Trustpoint to query";
        }
      }
    }
  }
}
