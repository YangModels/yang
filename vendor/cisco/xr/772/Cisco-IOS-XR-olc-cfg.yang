module Cisco-IOS-XR-olc-cfg {
  namespace "http://cisco.com/ns/yang/Cisco-IOS-XR-olc-cfg";
  prefix olc-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR olc package configuration.
     
     This module contains definitions
     for the following management objects:
       olc: Optical Application Configurations
     
     Copyright (c) 2013-2022 by Cisco Systems, Inc.
     All rights reserved.";

  revision 2022-05-31 {
    description
      "Automatic link config CLI addition.";
    semver:module-version "1.0.0";
  }
  revision 2022-02-28 {
    description
      "Enhancement to fiber_type configuration by adding new fiber type.";
  }
  revision 2022-01-19 {
    description
      "Enhancement to Span length config tx direction CLI addition.";
  }
  revision 2022-01-17 {
    description
      "Enhancement to Link tuner config CLI addition.";
  }
  revision 2021-12-07 {
    description
      "Link tuner config CLI addition.";
  }
  revision 2021-01-19 {
    description
      "APC config CLI addition.";
  }
  revision 2020-11-04 {
    description
      "Initial Revision.";
  }
  revision 2019-04-05 {
    description
      "Establish semantic version baseline.";
  }
  revision 2015-11-09 {
    description
      "IOS XR 6.0 revision.";
  }

  typedef Cfg-state {
    type enumeration {
      enum "none" {
        value 0;
        description
          "NONE";
      }
      enum "disable" {
        value 1;
        description
          "DISABLE";
      }
      enum "enable" {
        value 2;
        description
          "ENABLE";
      }
    }
    description
      "Cfg state";
  }

  typedef Fiber {
    type enumeration {
      enum "smf" {
        value 1;
        description
          "SMF";
      }
      enum "smf-28e" {
        value 2;
        description
          "SMF 28E";
      }
      enum "tw-rs" {
        value 3;
        description
          "TW RS";
      }
      enum "tw-reach" {
        value 4;
        description
          "TW Reach";
      }
      enum "e-leaf" {
        value 5;
        description
          "E LEAF";
      }
      enum "free-light" {
        value 6;
        description
          "FREE LIGHT";
      }
      enum "metro-core" {
        value 7;
        description
          "METRO CORE";
      }
      enum "tera-light" {
        value 8;
        description
          "TERA LIGHT";
      }
      enum "tw-minus" {
        value 9;
        description
          "TW minus";
      }
      enum "tw-plus" {
        value 10;
        description
          "TW plus";
      }
      enum "ull-smf28" {
        value 11;
        description
          "ULL SMF28";
      }
    }
    description
      "Fiber";
  }

  grouping APC-LOCAL-DIR-DISABLE {
    description
      "Common node of apc-local-dir-tx, apc-local-dir-rx";
    leaf apc-local-dir-disable {
      type empty;
      description
        "Configuration to disable local APC regulation.
         APC is enabled on by default.";
    }
  }

  container olc {
    description
      "Optical Application Configurations";
    container controller-rsips {
      description
        "Global scope configurations";
      list controller-rsip {
        key "controller";
        description
          "Controller specific configurations";
        container apc {
          description
            "APC configuration";
          container psds {
            description
              "Power spectral density configuration";
            list psd {
              key "psd-index";
              description
                "PSD Configuration";
              leaf psd-index {
                type uint32 {
                  range "1..33";
                }
                description
                  "PSD Index";
              }
              leaf psd-value {
                type int32 {
                  range "-300..230";
                }
                mandatory true;
                description
                  "Value in increments of 0.1 dBm per 12.5 GHz
                   , between -30.0 to 23.0.";
              }
            }
          }
          leaf drop-psd {
            type int32 {
              range "-300..230";
            }
            description
              "Configuration for drop psd in increments of 0
               .1 dBm per 12.5 GHz, between -30.0 to 23.0.";
          }
          leaf apc-pause {
            type empty;
            description
              "Pause APC on the domain";
          }
          leaf apc-cfg-state {
            type Cfg-state;
            default "none";
            description
              "Change config state of APC.";
          }
          leaf psd-min {
            type int32 {
              range "-400..230";
            }
            description
              "Configuration for minimum psd in increments
               of 0.1 dBm per 12.5 GHz, between -40.0 to 23
               .0.";
          }
        }
        container apc-local {
          description
            "APC agent per direction disable configuration";
          container apc-local-dir-tx {
            description
              "Disable APC agent in TX direction";
            uses APC-LOCAL-DIR-DISABLE;
          }
          container apc-local-dir-rx {
            description
              "Disable APC agent in RX direction";
            uses APC-LOCAL-DIR-DISABLE;
          }
        }
        container raman {
          description
            "Raman configuration";
          leaf raman-tune-target-gain {
            type uint32 {
              range "0..300";
            }
            description
              "Gain Value in increments of 0.1 dB, between 0
               .0 and 30.0 dB";
          }
          leaf raman-tune-cfg-state {
            type Cfg-state;
            default "none";
            description
              "Change config state of Automatic Raman Tuning";
          }
        }
        container link-tuner {
          description
            "Link tuner configuration";
          leaf spectrum-density {
            type uint32 {
              range "1..100";
            }
            default "81";
            description
              "Spectrum density configuration for the given
               controller";
          }
          leaf link-tuner-cfg-state {
            type Cfg-state;
            default "none";
            description
              "Change config state of Link Tuner";
          }
        }
        container span-loss {
          description
            "Span loss configuration";
          leaf max-threshold {
            type uint32 {
              range "0..420";
            }
            description
              "Maximum threshold configuration for the given
               controller";
          }
          leaf min-threshold {
            type uint32 {
              range "0..420";
            }
            description
              "Minimum threshold configuration for the given
               controller";
          }
        }
        container gain-estimator {
          description
            "Gain estimator configuration";
          leaf gain-estimator-cfg-state {
            type Cfg-state;
            default "none";
            description
              "Change config state of Gain Estimator";
          }
        }
        leaf rx-connector-loss {
          type string {
            length "1..6";
          }
          description
            "Rx connector loss in dB";
        }
        leaf tx-connector-loss {
          type string {
            length "1..6";
          }
          description
            "Tx connector loss in dB";
        }
        leaf fiber-type {
          type Fiber;
          default "smf";
          description
            "Fiber Type for given controller";
        }
        leaf span-length {
          type uint32 {
            range "1..2000";
          }
          description
            "Span length in 0.1 km";
        }
        leaf controller {
          type xr:Interface-name;
          description
            "Controller RSIP";
        }
      }
    }
    container global-config {
      description
        "Global scope configurations";
      leaf auto-link-bringup {
        type empty;
        description
          "Enable Automatic link bringup.";
      }
    }
  }
}
