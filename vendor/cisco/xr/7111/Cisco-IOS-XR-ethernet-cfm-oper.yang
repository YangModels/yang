module Cisco-IOS-XR-ethernet-cfm-oper {
  namespace "http://cisco.com/ns/yang/Cisco-IOS-XR-ethernet-cfm-oper";
  prefix ethernet-cfm-oper;

  import ietf-yang-types {
    prefix yang;
  }
  import Cisco-IOS-XR-types {
    prefix xr;
  }
  import cisco-semver {
    prefix semver;
  }
  import Cisco-IOS-XR-ethernet-cfm-datatypes {
    prefix dt1;
  }
  import Cisco-IOS-XR-infra-sla-oper {
    prefix a1;
  }
  include Cisco-IOS-XR-ethernet-cfm-oper-sub4 {
    revision-date 2023-02-01;
  }
  include Cisco-IOS-XR-ethernet-cfm-oper-sub3 {
    revision-date 2023-02-01;
  }
  include Cisco-IOS-XR-ethernet-cfm-oper-sub2 {
    revision-date 2023-02-01;
  }
  include Cisco-IOS-XR-ethernet-cfm-oper-sub1 {
    revision-date 2023-02-01;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ethernet-cfm package operational data.
     
     This module contains definitions
     for the following management objects:
       cfm: CFM operational data
     
     This YANG module augments the
       Cisco-IOS-XR-infra-sla-oper
     module with state data.
     
     Copyright (c) 2013-2023 by Cisco Systems, Inc.
     All rights reserved.";

  revision 2023-02-01 {
    description
      "Add malformed CCM flag
       2022-01-19
         Add CCM and AIS encapsulation conflict errors.
       2022-01-18
         Added CSF packet counters.
       2021-10-22
         Added counters for missing MEP offload intervals.
       2021-09-02
         Added support for LTM statistics.";
    semver:module-version "2.0.0";
  }
  revision 2020-10-07 {
    description
      "Added the Link Loss Forwarding feature.";
    semver:module-version "1.3.0";
  }
  revision 2020-07-07 {
    description
      "Added SLA summary information.";
    semver:module-version "1.2.0";
  }
  revision 2019-10-02 {
    description
      "Bandwidth notification addition";
    semver:module-version "1.1.0";
  }
  revision 2019-04-05 {
    description
      "Establish semantic version baseline.";
    semver:module-version "1.0.0";
  }
  revision 2018-12-20 {
    description
      "Bandwidth notification class and type name update.";
  }
  revision 2017-10-06 {
    description
      "Traceroute transaction ID changed from int to uint.";
  }
  revision 2015-11-09 {
    description
      "IOS XR 6.0 revision.";
  }

  typedef Cfm-ais-dir {
    type enumeration {
      enum "up" {
        value 0;
        description
          "Packets sent inward";
      }
      enum "down" {
        value 1;
        description
          "Packets sent outward";
      }
    }
    description
      "Cfm ais dir";
  }

  augment "/a1:sla-nodes" {
    description
      "This augment extends the operational data of
       'Cisco-IOS-XR-infra-sla-oper'";
    list node {
      key "node";
      description
        "Node-specific data for a particular node";
      container protocols {
        description
          "Table of all SLA protocols";
        container ethernet {
          description
            "The Ethernet SLA protocol";
          container summary {
            description
              "SLA summary configured data";
            uses SLA-OPER-SUMMARY;
          }
          container on-demand-summary {
            description
              "SLA summary on-demand data";
            uses SLA-OPER-SUMMARY;
          }
        }
      }
      leaf node {
        type xr:Node-id;
        description
          "Node";
      }
    }
  }
  augment "/a1:sla/a1:protocols" {
    description
      "This augment extends the operational data of
       'Cisco-IOS-XR-infra-sla-oper'";
    container ethernet {
      description
        "The Ethernet SLA protocol";
      container statistics-on-demand-currents {
        description
          "Table of current statistics for SLA on-demand
           operations";
        list statistics-on-demand-current {
          description
            "Current statistics data for an SLA on-demand
             operation";
          leaf operation-id {
            type uint32 {
              range "1..4294967295";
            }
            description
              "Operation ID";
          }
          leaf domain-name {
            type string;
            description
              "Domain name";
          }
          leaf interface-name {
            type xr:Interface-name;
            description
              "Interface name";
          }
          leaf mep-id {
            type dt1:Cfm-mep-id;
            description
              "MEP ID in the range 1 to 8191. Either MEP ID
               or MAC address must be specified.";
          }
          leaf mac-address {
            type yang:mac-address;
            description
              "Unicast MAC Address in xxxx.xxxx.xxxx format.
               Either MEP ID or MAC address must be
               specified.";
          }
          uses SLA-OPER-OPERATION-STATISTICS;
        }
      }
      container operations {
        description
          "Table of SLA operations";
        list operation {
          description
            "SLA operation to get operation data for";
          leaf profile-name {
            type xr:Cisco-ios-xr-string;
            description
              "Profile Name";
          }
          leaf domain-name {
            type string;
            description
              "Domain name";
          }
          leaf interface-name {
            type xr:Interface-name;
            description
              "Interface name";
          }
          leaf mep-id {
            type dt1:Cfm-mep-id;
            description
              "MEP ID in the range 1 to 8191. Either MEP ID
               or MAC address must be specified.";
          }
          leaf mac-address {
            type yang:mac-address;
            description
              "Unicast MAC Address in xxxx.xxxx.xxxx format.
               Either MEP ID or MAC address must be
               specified.";
          }
          uses SLA-OPER-OPERATION;
        }
      }
      container statistics-historicals {
        description
          "Table of historical statistics for SLA
           operations";
        list statistics-historical {
          description
            "Historical statistics data for an SLA
             configured operation";
          leaf profile-name {
            type xr:Cisco-ios-xr-string;
            description
              "Profile Name";
          }
          leaf domain-name {
            type string;
            description
              "Domain name";
          }
          leaf interface-name {
            type xr:Interface-name;
            description
              "Interface name";
          }
          leaf mep-id {
            type dt1:Cfm-mep-id;
            description
              "MEP ID in the range 1 to 8191. Either MEP ID
               or MAC address must be specified.";
          }
          leaf mac-address {
            type yang:mac-address;
            description
              "Unicast MAC Address in xxxx.xxxx.xxxx format.
               Either MEP ID or MAC address must be
               specified.";
          }
          uses SLA-OPER-OPERATION-STATISTICS;
        }
      }
      container statistics-on-demand-historicals {
        description
          "Table of historical statistics for SLA
           on-demand operations";
        list statistics-on-demand-historical {
          description
            "Historical statistics data for an SLA
             on-demand  operation";
          leaf operation-id {
            type uint32 {
              range "1..4294967295";
            }
            description
              "Operation ID";
          }
          leaf domain-name {
            type string;
            description
              "Domain name";
          }
          leaf interface-name {
            type xr:Interface-name;
            description
              "Interface name";
          }
          leaf mep-id {
            type dt1:Cfm-mep-id;
            description
              "MEP ID in the range 1 to 8191. Either MEP ID
               or MAC address must be specified.";
          }
          leaf mac-address {
            type yang:mac-address;
            description
              "Unicast MAC Address in xxxx.xxxx.xxxx format.
               Either MEP ID or MAC address must be
               specified.";
          }
          uses SLA-OPER-OPERATION-STATISTICS;
        }
      }
      container config-errors {
        description
          "Table of SLA configuration errors on configured
           operations";
        list config-error {
          description
            "SLA operation to get configuration errors data
             for";
          leaf profile-name {
            type xr:Cisco-ios-xr-string;
            description
              "Profile Name";
          }
          leaf domain-name {
            type string;
            description
              "Domain name";
          }
          leaf interface-name {
            type xr:Interface-name;
            description
              "Interface name";
          }
          leaf mep-id {
            type dt1:Cfm-mep-id;
            description
              "MEP ID in the range 1 to 8191";
          }
          leaf mac-address {
            type yang:mac-address;
            description
              "Unicast MAC Address in xxxx.xxxx.xxxx format";
          }
          uses SLA-OPER-CONFIG-ERRORS;
        }
      }
      container on-demand-operations {
        description
          "Table of SLA on-demand operations";
        list on-demand-operation {
          description
            "SLA on-demand operation to get operation data
             for";
          leaf operation-id {
            type uint32 {
              range "1..4294967295";
            }
            description
              "Operation ID";
          }
          leaf domain-name {
            type string;
            description
              "Domain name";
          }
          leaf interface-name {
            type xr:Interface-name;
            description
              "Interface name";
          }
          leaf mep-id {
            type dt1:Cfm-mep-id;
            description
              "MEP ID in the range 1 to 8191. Either MEP ID
               or MAC address must be specified.";
          }
          leaf mac-address {
            type yang:mac-address;
            description
              "Unicast MAC Address in xxxx.xxxx.xxxx format.
               Either MEP ID or MAC address must be
               specified.";
          }
          uses SLA-OPER-OPERATION;
        }
      }
      container statistics-currents {
        description
          "Table of current statistics for SLA operations";
        list statistics-current {
          description
            "Current statistics data for an SLA configured
             operation";
          leaf profile-name {
            type xr:Cisco-ios-xr-string;
            description
              "Profile Name";
          }
          leaf domain-name {
            type string;
            description
              "Domain name";
          }
          leaf interface-name {
            type xr:Interface-name;
            description
              "Interface name";
          }
          leaf mep-id {
            type dt1:Cfm-mep-id;
            description
              "MEP ID in the range 1 to 8191. Either MEP ID
               or MAC address must be specified.";
          }
          leaf mac-address {
            type yang:mac-address;
            description
              "Unicast MAC Address in xxxx.xxxx.xxxx format.
               Either MEP ID or MAC address must be
               specified.";
          }
          uses SLA-OPER-OPERATION-STATISTICS;
        }
      }
    }
  }
  container cfm {
    config false;
    description
      "CFM operational data";
    container nodes {
      description
        "Node table for node-specific operational data";
      list node {
        key "node";
        description
          "Node-specific data for a particular node";
        container interface-aises {
          description
            "Interface AIS table";
          list interface-ais {
            key "interface direction";
            description
              "AIS statistics for a particular interface";
            leaf interface {
              type xr:Interface-name;
              description
                "Interface";
            }
            leaf direction {
              type Cfm-ais-dir;
              description
                "AIS Direction";
            }
            uses CFM-PM-EFP-AIS-BAG;
          }
        }
        container bandwidth-notifications {
          description
            "Bandwidth Notifications Table";
          list bandwidth-notification {
            key "interface md-level mep-direction port-id mac-address";
            description
              "Bandwidth Notification";
            leaf interface {
              type xr:Interface-name;
              description
                "Interface";
            }
            leaf md-level {
              type uint32;
              description
                "MDLevel";
            }
            leaf mep-direction {
              type dt1:Cfm-mep-dir;
              description
                "MepDirection";
            }
            leaf port-id {
              type uint32;
              description
                "PortID";
            }
            leaf mac-address {
              type yang:mac-address;
              description
                "MAC Address";
            }
            uses CFM-PM-BNM-LINK-BAG;
          }
        }
        container interface-statistics {
          description
            "Interface Statistics table";
          list interface-statistic {
            key "interface";
            description
              "Counters for a particular interface";
            leaf interface {
              type xr:Interface-name;
              description
                "Interface";
            }
            uses CFM-PM-EFP-STATS-BAG;
          }
        }
        container interface-llfs {
          description
            "Interface LLF table";
          list interface-llf {
            key "interface";
            description
              "LLF statistics for a particular interface";
            leaf interface {
              type xr:Interface-name;
              description
                "Interface";
            }
            uses CFM-PM-EFP-LLF-BAG;
          }
        }
        container malformed-packets-table {
          description
            "Malformed Packets Table";
          container malformed-packets-interfaces {
            description
              "Table of interfaces which have received
               malformed packets";
            list malformed-packets-interface {
              key "interface";
              description
                "Malformed packets received on a specific
                 interface";
              leaf interface {
                type xr:Interface-name;
                description
                  "Interface";
              }
              uses CFM-PM-MALF-PKT-IFH-BAG;
            }
          }
          container malformed-packets-unknown-interface {
            description
              "Malformed packets received on unknown
               interfaces";
            uses CFM-PM-MALF-PKT-IFH-BAG;
          }
        }
        container summary {
          description
            "Summary CFM information on MEPs, traceroute,
             and more";
          uses CFM-MA-SUMMARY;
        }
        container ccm-learning-databases {
          description
            "CCMLearningDatabase table";
          list ccm-learning-database {
            key "domain service mac-address";
            description
              "CCM Learning Database entry";
            leaf domain {
              type string {
                length "1..127";
              }
              description
                "Maintenance Domain";
            }
            leaf service {
              type string {
                length "1..127";
              }
              description
                "Service (Maintenance Association)";
            }
            leaf mac-address {
              type yang:mac-address;
              description
                "MAC Address";
            }
            uses CFM-PM-CLDB-BAG;
          }
        }
        leaf node {
          type xr:Node-id;
          description
            "Node";
        }
      }
    }
    container global {
      description
        "Global operational data";
      container incomplete-traceroutes {
        description
          "Incomplete Traceroute table";
        list incomplete-traceroute {
          key "domain service mep-id interface transaction-id";
          description
            "Information about a traceroute operation that
             has not yet timed out";
          leaf domain {
            type string {
              length "1..127";
            }
            description
              "Maintenance Domain";
          }
          leaf service {
            type string {
              length "1..127";
            }
            description
              "Service (Maintenance Association)";
          }
          leaf mep-id {
            type dt1:Cfm-mep-id;
            description
              "MEP ID";
          }
          leaf interface {
            type xr:Interface-name;
            description
              "Interface";
          }
          leaf transaction-id {
            type uint32;
            description
              "Transaction ID";
          }
          uses CFM-PM-MEP-INCOMPLETE-TR-BAG;
        }
      }
      container maintenance-points {
        description
          "Maintenance Points table";
        list maintenance-point {
          key "domain service interface";
          description
            "Information about a particular Maintenance
             Point";
          leaf domain {
            type string {
              length "1..127";
            }
            description
              "Maintenance Domain";
          }
          leaf service {
            type string {
              length "1..127";
            }
            description
              "Service (Maintenance Association)";
          }
          leaf interface {
            type xr:Interface-name;
            description
              "Interface";
          }
          uses CFM-MA-MP-BRIEF;
        }
      }
      container global-configuration-errors {
        description
          "CFM Global Manager Configuration Error
           Information";
        list global-configuration-error {
          key "domain service";
          description
            "Information about a particular configuration
             error";
          leaf domain {
            type string {
              length "1..127";
            }
            description
              "Maintenance Domain";
          }
          leaf service {
            type string {
              length "1..127";
            }
            description
              "Service (Maintenance Association)";
          }
          uses CGM-CFG-ERRORS;
        }
      }
      container mep-configuration-errors {
        description
          "MEP configuration errors table";
        list mep-configuration-error {
          key "domain service interface";
          description
            "Information about a particular configuration
             error";
          leaf domain {
            type string {
              length "1..127";
            }
            description
              "Maintenance Domain";
          }
          leaf service {
            type string {
              length "1..127";
            }
            description
              "Service (Maintenance Association)";
          }
          leaf interface {
            type xr:Interface-name;
            description
              "Interface";
          }
          uses CFM-MA-MEP-ERRORS;
        }
      }
      container traceroute-caches {
        description
          "Traceroute Cache table";
        list traceroute-cache {
          key "domain service mep-id interface transaction-id";
          description
            "Information about a particular traceroute
             operation";
          leaf domain {
            type string {
              length "1..127";
            }
            description
              "Maintenance Domain";
          }
          leaf service {
            type string {
              length "1..127";
            }
            description
              "Service (Maintenance Association)";
          }
          leaf mep-id {
            type dt1:Cfm-mep-id;
            description
              "MEP ID";
          }
          leaf interface {
            type xr:Interface-name;
            description
              "Interface";
          }
          leaf transaction-id {
            type uint32;
            description
              "Transaction ID";
          }
          uses CFM-PM-MEP-TR-CACHE-BAG;
        }
      }
      container local-meps {
        description
          "Local MEPs table";
        list local-mep {
          key "domain service mep-id interface";
          description
            "Information about a particular local MEP";
          leaf domain {
            type string {
              length "1..127";
            }
            description
              "Maintenance Domain";
          }
          leaf service {
            type string {
              length "1..127";
            }
            description
              "Service (Maintenance Association)";
          }
          leaf mep-id {
            type dt1:Cfm-mep-id;
            description
              "MEP ID";
          }
          leaf interface {
            type xr:Interface-name;
            description
              "Interface";
          }
          uses CFM-PM-MEP-STATS-BAG;
        }
      }
      container peer-me-pv2s {
        description
          "Peer MEPs table Version 2";
        list peer-me-pv2 {
          key "domain service local-mep-id interface peer-mep-id peer-mac-address";
          description
            "Information about a peer MEP for a particular
             local MEP";
          leaf domain {
            type string {
              length "1..127";
            }
            description
              "Maintenance Domain";
          }
          leaf service {
            type string {
              length "1..127";
            }
            description
              "Service (Maintenance Association)";
          }
          leaf local-mep-id {
            type dt1:Cfm-mep-id;
            description
              "MEP ID of Local MEP";
          }
          leaf interface {
            type xr:Interface-name;
            description
              "Interface";
          }
          leaf peer-mep-id {
            type dt1:Cfm-mep-id;
            description
              "MEP ID of Peer MEP";
          }
          leaf peer-mac-address {
            type yang:mac-address;
            description
              "Peer MAC address";
          }
          uses CFM-PM-REMOTE-MEPS-V2-BAG;
        }
      }
    }
  }
}
