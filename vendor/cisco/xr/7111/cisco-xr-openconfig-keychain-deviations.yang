//*************  DO-NOT EDIT  **************
//*********** Auto-generated file ********** 

 module cisco-xr-openconfig-keychain-deviations {

  prefix  "oc-keychaindevs";

  namespace "http://cisco.com/ns/yang/cisco-xr-openconfig-keychain-deviations";

  import openconfig-keychain { prefix oc-keychain; }

  organization "Cisco Systems, Inc.";

  contact
    "Cisco Systems, Inc.
     Customer Service

     Postal: 170 West Tasman Drive
     San Jose, CA 95134

     Tel: +1 800 553-NETS

     E-mail: cs-yang@cisco.com";

  description
    "This module contains a set of deviations for 

     openconfig-keychain.yang@2022-03-05 

     on Cisco IOS-XR devices.

     Copyright (c) 2017 by Cisco Systems, Inc.
     All rights reserved.";

  revision "2023-02-17" {
    description
      "Initial revision applicable to IOS-XR 6.4.1";
  }


  deviation /oc-keychain:keychains/oc-keychain:keychain {
    deviate not-supported;
  }


}
//total deviations:1
