module Cisco-IOS-XR-dot1x-oper {
  namespace "http://cisco.com/ns/yang/Cisco-IOS-XR-dot1x-oper";
  prefix dot1x-oper;

  import Cisco-IOS-XR-types {
    prefix xr;
  }
  import cisco-semver {
    prefix semver;
  }
  include Cisco-IOS-XR-dot1x-oper-sub1 {
    revision-date 2023-05-04;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR dot1x package operational data.
     
     This module contains definitions
     for the following management objects:
       dot1x: Dot1x operational data
     
     Copyright (c) 2013-2023 by Cisco Systems, Inc.
     All rights reserved.";

  revision 2023-05-04 {
    description
      "Addition of Remote AAA Authentication configuration into auth info";
    semver:module-version "2.3.0";
  }
  revision 2021-03-31 {
    description
      "EAP TTLS/EAP Attestation";
    semver:module-version "2.2.0";
  }
  revision 2020-04-23 {
    description
      "Dot1x Port Status";
    semver:module-version "2.1.0";
  }
  revision 2019-08-23 {
    description
      "Host Mode";
    semver:module-version "2.0.0";
  }
  revision 2019-04-05 {
    description
      "Establish semantic version baseline.";
    semver:module-version "1.0.0";
  }
  revision 2015-11-09 {
    description
      "IOS XR 6.0 revision.";
  }

  container dot1x {
    config false;
    description
      "Dot1x operational data";
    container statistics {
      description
        "Dot1x operational data";
      container interface-statistics {
        description
          "Interfaces with Dot1x";
        list interface-statistic {
          key "name";
          description
            "Dot1x Data for that Interface";
          leaf name {
            type xr:Interface-name;
            description
              "Interface Name";
          }
          uses DOT1X-IF-STATISTICS;
        }
      }
    }
    container nodes {
      description
        "Node-specific Dot1x operational data";
      list node {
        key "node-name";
        description
          "Dot1x operational data for a particular node";
        container interface-summaries {
          description
            "Dot1x Summary";
          list interface-summary {
            key "name";
            description
              "Dot1x Summary for that Interface";
            leaf name {
              type xr:Interface-name;
              description
                "Interface Name";
            }
            uses DOT1X-INTERFACE;
          }
        }
        container dot1x-defaults {
          description
            "Dot1x Default Values";
          uses DOT1X-DEFAULT;
        }
        container statistics {
          description
            "Dot1x Default Values";
          uses DOT1X-STATISTICS;
        }
        leaf node-name {
          type xr:Node-id;
          description
            "The node name";
        }
      }
    }
    container session {
      description
        "Dot1x operational data";
      container interface-sessions {
        description
          "Interfaces with Dot1x";
        list interface-session {
          key "name";
          description
            "Dot1x Data for that Interface";
          leaf name {
            type xr:Interface-name;
            description
              "Interface Name";
          }
          uses DOT1X-INTERFACE-DETAIL;
        }
      }
    }
  }
}
