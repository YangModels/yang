module Cisco-IOS-XR-segment-routing-srv6-cfg {
  namespace "http://cisco.com/ns/yang/Cisco-IOS-XR-segment-routing-srv6-cfg";
  prefix segment-routing-srv6-cfg;

  import ietf-inet-types {
    prefix inet;
  }
  import Cisco-IOS-XR-types {
    prefix xr;
  }
  import cisco-semver {
    prefix semver;
  }
  import Cisco-IOS-XR-segment-routing-srv6-datatypes {
    prefix dt1;
  }
  import Cisco-IOS-XR-segment-routing-ms-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR segment-routing-srv6 package configuration.
     
     This YANG module augments the
       Cisco-IOS-XR-segment-routing-ms-cfg
     module with configuration data.
     
     Copyright (c) 2013-2023 by Cisco Systems, Inc.
     All rights reserved.";

  revision 2023-04-20 {
    description
      "Added DT46/uDT46 and forwarding configs
       2023-02-08
         Added generic static allocation context
       2023-01-20
         backed out SRv6 accounting per prefix config
       2022-11-30
         Added support for SRv6 accounting per prefix config
       2022-08-03
         Deprecated merge overlay underlay sids config
       2022-05-19
         Added support for uSID LIB ranges config
       2022-03-23
         Added support for static adjacency SID configuration
       2021-11-23
         Added support for locator delayed delete configuration
       2021-09-17
         Extend config knob propagate traffic-class and hoplimit for SRv6 encap to support being explicitly disabled";
    semver:module-version "1.3.0";
  }
  revision 2020-08-25 {
    description
      "Added MicroSegmentGlobalParams container and MergeOverlayUnderlaySIDS leaf";
    semver:module-version "1.2.0";
  }
  revision 2019-11-21 {
    description
      "Support for anycast locator flag
       2019-10-08
         Support config knob to set traffic-class for SRv6 encap
       2019-04-22
         Flex-Algo support
       2019-04-22
         Flex-Algo specific changes";
    semver:module-version "1.1.0";
  }
  revision 2019-04-05 {
    description
      "Establish semantic version baseline.";
    semver:module-version "1.0.1";
  }
  revision 2015-11-09 {
    description
      "IOS XR 6.0 revision.";
  }

  augment "/a1:sr" {
    description
      "This augment extends the configuration data of
       'Cisco-IOS-XR-segment-routing-ms-cfg'";
    container srv6 {
      description
        "Segment Routing with IPv6 dataplane";
      container static {
        description
          "Configure SRv6 static routing parameters";
        container endpoints {
          description
            "Configure SRv6 static endpoints";
          list endpoint {
            key "prefix";
            description
              "Configure an SRv6 static SID endpoint";
            container forwarding {
              description
                "Configure Static Endpoint forwarding
                 parameters";
              leaf forwarding-enable {
                type empty;
                description
                  "Create a rewrite for this static SID";
              }
            }
            container allocation-context {
              description
                "Generic SRv6 Static SID allocation context,
                 see specific contexts for field hints";
              leaf interface-name {
                type xr:Interface-name;
                description
                  "Name of the interface";
              }
              leaf algo-id {
                type dt1:Srv6-algo-value;
                description
                  "Algorithm ID";
              }
              leaf protected {
                type boolean;
                description
                  "Protected";
              }
              leaf differentiator {
                type dt1:Srv6-differentiator;
                description
                  "Differentiator";
              }
              leaf vrf-name {
                type string;
                description
                  "Name of the vrf";
              }
            }
            container allocation-context-vrf {
              description
                "Configure DT46/uDT46 SRv6 Static SID
                 allocation context";
              leaf interface-name {
                type xr:Interface-name;
                description
                  "Unused for this ctx type";
              }
              leaf algo-id {
                type dt1:Srv6-algo-value;
                description
                  "Unused for this ctx type";
              }
              leaf protected {
                type boolean;
                description
                  "Unused for this ctx type";
              }
              leaf differentiator {
                type dt1:Srv6-differentiator;
                description
                  "Differentiator";
              }
              leaf vrf-name {
                type string;
                description
                  "Name of the vrf";
              }
            }
            container allocation-context-adjacency {
              description
                "Configure uA/End.X SRv6 Static SID
                 allocation context";
              leaf interface-name {
                type xr:Interface-name;
                description
                  "Name of the interface";
              }
              leaf algo-id {
                type dt1:Srv6-algo-value;
                description
                  "Algorithm ID";
              }
              leaf protected {
                type boolean;
                description
                  "Protected";
              }
              leaf differentiator {
                type dt1:Srv6-differentiator;
                description
                  "Differentiator";
              }
              leaf vrf-name {
                type string;
                description
                  "Unused for this ctx type";
              }
            }
            leaf behavior {
              type dt1:Srv6-static-sid-behavior;
              description
                "Configure SRv6 Static SID allocation context";
            }
            leaf prefix {
              type inet:ip-address-no-zone;
              description
                "IPv6 prefix";
            }
          }
        }
      }
      container logging {
        description
          "Enable logging";
        leaf locator-status {
          type empty;
          description
            "Enable logging for locator status changes";
        }
      }
      container formats {
        description
          "Configure SRv6 format parameters";
        container formats {
          description
            "Configure table of SRv6 formats";
          list format {
            key "name";
            description
              "Configure a SRv6 format";
            container usid {
              description
                "Specify uSID specific parameters";
              container local-id-block-ranges {
                description
                  "Specify uSID LIB ranges (start,
                   explicit-start)";
                leaf lib-start {
                  type dt1:Srv6u-sid-lib-start-range;
                  default "57344";
                  description
                    "Start of LIB";
                }
                leaf explict-lib-start {
                  type dt1:Srv6u-sid-elib-start-range;
                  default "65024";
                  description
                    "Start of Explicit LIB";
                }
              }
              leaf wide-local-id-block-explicit-range {
                type dt1:Srv6u-sid-ewlib-start-range;
                default "65527";
                description
                  "Specify uSID WLIB explicit range";
              }
            }
            leaf format-enable {
              type empty;
              description
                "Enable a SRv6 format";
            }
            leaf name {
              type xr:Cisco-ios-xr-string;
              description
                "Format name";
            }
          }
        }
      }
      container micro-segment-global-params {
        description
          "Configure micro-segment related parameters";
        leaf merge-overlay-underlay-sids {
          type empty;
          status deprecated;
          description
            "DEPRECATED - DO NOT USE";
        }
      }
      container locators {
        description
          "Configure SRv6 locators parameters";
        container locators {
          description
            "Configure SRv6 table of locators";
          list locator {
            key "name";
            description
              "Configure a SRv6 locator";
            container micro-segment {
              description
                "Configure micro-segments (uSID) related
                 parameters";
              leaf behavior {
                type dt1:Srv6u-behavior;
                description
                  "Specify Locator's behavior";
              }
            }
            container prefix {
              description
                "Specify locator prefix value";
              leaf prefix {
                type inet:ip-address-no-zone;
                description
                  "IPv6 Prefix";
              }
              leaf prefix-length {
                type dt1:Srv6-locator-len;
                description
                  "Prefix length";
              }
            }
            leaf delayed-delete {
              type empty;
              description
                "Specify locator to maintain SID forwarding
                 until holdtime for stale/freed SID has
                 passed";
            }
            leaf locator-enable {
              type empty;
              description
                "Enable a SRv6 locator";
            }
            leaf anycast {
              type empty;
              description
                "Specify locator to be anycast type";
            }
            leaf algorithm {
              type dt1:Srv6-algo-value;
              description
                "Specify locator algorithm";
            }
            leaf name {
              type dt1:Srv6-locator-name;
              description
                "Locator name";
            }
          }
        }
      }
      container encapsulation {
        description
          "Configure encapsulation related parameters";
        container traffic-class {
          description
            "Configure IPv6 header traffic-class";
          leaf option {
            type dt1:Srv6-encapsulation-tc-option;
            description
              "Config option";
          }
          leaf value {
            when "../option = 'value'" {
              description
                "../Option = Value";
            }
            type dt1:Srv6-encapsulation-tc-value;
            default "0";
            description
              "Field Value";
          }
        }
        container hop-limit {
          description
            "Configure IPv6 Hop-Limit options";
          leaf option {
            type dt1:Srv6-encapsulation-hop-limit-option;
            description
              "Hop-Limit config option";
          }
          leaf value {
            when "../option = 'count'" {
              description
                "../Option = Count";
            }
            type dt1:Srv6-encapsulation-hop-limit-value;
            default "0";
            description
              "Count for Hop-limit";
          }
        }
        leaf source-address {
          type inet:ip-address-no-zone;
          description
            "Configure a source address";
        }
      }
      leaf enable {
        type empty;
        description
          "Enable SRv6";
      }
      leaf sid-holdtime {
        type dt1:Srv6sid-holdtime;
        description
          "Configure SID holdtime for a stale/freed SID";
      }
    }
  }
}
