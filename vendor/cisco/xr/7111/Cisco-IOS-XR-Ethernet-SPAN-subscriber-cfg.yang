module Cisco-IOS-XR-Ethernet-SPAN-subscriber-cfg {
  namespace "http://cisco.com/ns/yang/Cisco-IOS-XR-Ethernet-SPAN-subscriber-cfg";
  prefix ethernet-span-subscriber-cfg;

  import cisco-semver {
    prefix semver;
  }
  import Cisco-IOS-XR-Ethernet-SPAN-datatypes {
    prefix dt1;
  }
  import Cisco-IOS-XR-subscriber-infra-tmplmgr-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR Ethernet-SPAN-subscriber package configuration.
     
     This YANG module augments the
       Cisco-IOS-XR-subscriber-infra-tmplmgr-cfg
     module with configuration data.
     
     Copyright (c) 2013-2022 by Cisco Systems, Inc.
     All rights reserved.";

  revision 2022-07-13 {
    description
      "Added support for ACL merge groups
       2021-10-06
         Added support for global mirror intervals";
    semver:module-version "2.0.0";
  }
  revision 2021-07-19 {
    description
      "Added extended range of values to mirror interval sampling";
    semver:module-version "1.1.0";
  }
  revision 2020-12-03 {
    description
      "Added support for multiple attachments per class on an interface";
    semver:module-version "1.0.0";
  }
  revision 2020-01-30 {
    description
      "Added support for L3 IPv4 and IPv6 ACLs on a L2 ethernet SPAN session";
  }
  revision 2019-04-05 {
    description
      "Establish semantic version baseline.";
  }
  revision 2015-11-09 {
    description
      "IOS XR 6.0 revision.";
  }

  typedef Span-traffic-direction {
    type enumeration {
      enum "rx-only" {
        value 1;
        description
          "Replicate only received (ingress) traffic";
      }
      enum "tx-only" {
        value 2;
        description
          "Replicate only transmitted (egress) traffic";
      }
    }
    description
      "Span traffic direction";
  }

  grouping SPAN-ATTACHMENT-TABLE {
    description
      "Common node of interface-configuration,
       l2-transport";
    container span-attachments {
      description
        "Monitor Session container for this source
         interface";
      list span-attachment {
        key "session-name";
        description
          "Configuration for a particular Monitor Session";
        container mplsacl {
          description
            "Enable MPLS ACL matching for traffic mirroring";
          leaf acl-enable {
            type empty;
            mandatory true;
            description
              "Enable ACL";
          }
          leaf acl-name {
            type dt1:Span-acl-name;
            description
              "ACL Name";
          }
          leaf merge-group {
            type uint32;
            description
              "merge group";
          }
          leaf priority {
            type uint32;
            description
              "priority";
          }
        }
        container ipv4acl {
          description
            "Enable IPv4 ACL matching for traffic mirroring";
          leaf acl-enable {
            type empty;
            mandatory true;
            description
              "Enable ACL";
          }
          leaf acl-name {
            type dt1:Span-acl-name;
            description
              "ACL Name";
          }
          leaf merge-group {
            type uint32;
            description
              "merge group";
          }
          leaf priority {
            type uint32;
            description
              "priority";
          }
        }
        container ipv6acl {
          description
            "Enable IPv6 ACL matching for traffic mirroring";
          leaf acl-enable {
            type empty;
            mandatory true;
            description
              "Enable ACL";
          }
          leaf acl-name {
            type dt1:Span-acl-name;
            description
              "ACL Name";
          }
          leaf merge-group {
            type uint32;
            description
              "merge group";
          }
          leaf priority {
            type uint32;
            description
              "priority";
          }
        }
        leaf drops {
          type boolean;
          description
            "Specify whether or not to mirror dropped
             packets";
        }
        leaf session-name {
          type dt1:Span-session-name;
          description
            "Session Name";
        }
        uses MIRROR-FIRST;
        uses MIRROR-INTERVAL;
        uses ATTACHMENT-CONFIG;
        uses ACL;
      }
    }
  }

  grouping ETHERNET-SPAN-DYN-TMPL-CFG-SPAN-ATTACHMENT-TABLE {
    description
      "Common node of interface-configuration,
       l2-transportCommon node of ip-subscriber, ppp,
       subscriber-service";
    container span-attachments {
      description
        "Monitor Session container for this source
         interface";
      list span-attachment {
        key "session-name";
        description
          "Configuration for a particular Monitor Session";
        leaf session-name {
          type dt1:Span-session-name;
          description
            "Session Name";
        }
        uses MIRROR-FIRST;
        uses MIRROR-INTERVAL;
        uses ATTACHMENT-CONFIG;
        uses ACL;
      }
    }
  }

  grouping MIRROR-INTERVAL {
    description
      "Common node of span-attachment, span-attachment";
    leaf mirror-interval {
      type dt1:Span-mirror-interval;
      description
        "Specify the mirror interval";
    }
  }

  grouping MIRROR-FIRST {
    description
      "Common node of span-attachment, span-attachment";
    leaf mirror-first {
      type uint32 {
        range "1..10000";
      }
      units "byte";
      description
        "Mirror a specified number of bytes from start of
         packet";
    }
  }

  grouping ACL {
    description
      "Common node of span-attachment, span-attachment";
    container acl {
      presence "Indicates a acl node is configured.";
      description
        "Enable ACL matching for traffic mirroring";
      leaf acl-enable {
        type empty;
        mandatory true;
        description
          "Enable ACL";
      }
      leaf acl-name {
        type dt1:Span-acl-name;
        description
          "ACL Name";
      }
      leaf merge-group {
        type uint32;
        description
          "merge group";
      }
      leaf priority {
        type uint32;
        description
          "priority";
      }
    }
  }

  grouping ATTACHMENT-CONFIG {
    description
      "Common node of span-attachment, span-attachment";
    container attachment-config {
      presence "Indicates a attachment-config node is configured.";
      description
        "Attach the interface to a Monitor Session";
      leaf session-class {
        type dt1:Span-session-class;
        mandatory true;
        description
          "Traffic class for the session";
      }
      leaf direction {
        type Span-traffic-direction;
        description
          "Specify the direction of traffic to replicate
           (optional)";
      }
      leaf port-level-enable {
        type empty;
        description
          "Enable port level traffic mirroring";
      }
    }
  }

  augment "/a1:dynamic-template/a1:subscriber-services/a1:subscriber-service" {
    description
      "This augment extends the configuration data of
       'Cisco-IOS-XR-subscriber-infra-tmplmgr-cfg'";
    uses ETHERNET-SPAN-DYN-TMPL-CFG-SPAN-ATTACHMENT-TABLE;
  }
  augment "/a1:dynamic-template/a1:ppps/a1:ppp" {
    description
      "This augment extends the configuration data of
       'Cisco-IOS-XR-subscriber-infra-tmplmgr-cfg'";
    uses ETHERNET-SPAN-DYN-TMPL-CFG-SPAN-ATTACHMENT-TABLE;
  }
  augment "/a1:dynamic-template/a1:ip-subscribers/a1:ip-subscriber" {
    description
      "This augment extends the configuration data of
       'Cisco-IOS-XR-subscriber-infra-tmplmgr-cfg'";
    uses ETHERNET-SPAN-DYN-TMPL-CFG-SPAN-ATTACHMENT-TABLE;
  }
}
