module Cisco-IOS-XR-asr9k-np-oper {
  namespace "http://cisco.com/ns/yang/Cisco-IOS-XR-asr9k-np-oper";
  prefix asr9k-np-oper;

  import Cisco-IOS-XR-types {
    prefix xr;
  }
  import cisco-semver {
    prefix semver;
  }
  include Cisco-IOS-XR-asr9k-np-oper-sub1 {
    revision-date 2023-03-14;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR asr9k-np package operational data.
     
     This module contains definitions
     for the following management objects:
       hardware-module-np: Hardware NP Counters
     
     Copyright (c) 2013-2023 by Cisco Systems, Inc.
     All rights reserved.";

  revision 2023-03-14 {
    description
      "add support for NP soft-errors
       2023-03-10
         add support for NP Punt-path-counters
       2023-03-03
         add support for NP fabric-counters
       2023-02-13
         add support for NP interlaken interface status
       2023-01-23
         add support for NP interrupts
       2023-01-09
         add support for NP summary
       2021-12-18
         add support for NP resources";
    semver:module-version "1.2.0";
  }
  revision 2021-05-26 {
    description
      "add support for NP ucode counter query by index";
    semver:module-version "1.1.0";
  }
  revision 2021-04-23 {
    description
      "add/update sh controllers np portmap for xml support";
    semver:module-version "1.0.0";
  }
  revision 2020-12-21 {
    description
      "add/update sh controllers np valid-port-groups";
  }
  revision 2019-10-29 {
    description
      "Add more specific descriptions to address Good description issue";
  }
  revision 2019-04-05 {
    description
      "Establish semantic version baseline.";
  }
  revision 2015-11-09 {
    description
      "IOS XR 6.0 revision.";
  }

  typedef Np {
    type string {
      pattern "(np0)|(np1)|(np2)|(np3)|(np4)|(np5)|(np6)|(np7)|(np8)";
    }
    description
      "np0:NP0, np1:NP1, np2:NP2, np3:NP3, np4:NP4, np5
       :NP5, np6:NP6, np7:NP7, np8:NP8";
  }

  container hardware-module-np {
    config false;
    description
      "Hardware NP Counters";
    container nodes {
      description
        "Table of nodes";
      list node {
        key "node-name";
        description
          "Number";
        container nps {
          description
            "List of all NP";
          list np {
            key "np-name";
            description
              "np0 to np7";
            container mac-cfg-mode {
              description
                "Information of valid mac config mode";
              uses PRM-MAC-CFGMODE;
            }
            container np-soft-errors {
              description
                "Information of NP Soft Errors";
              uses PRM-NP-SOFT-ERR;
            }
            container np-uidb {
              description
                "Hardware np uidb";
              uses PRM-NP-UIDB;
            }
            container np-port-map {
              description
                "Information of NP port map";
              uses PRM-NP-PORTMAP;
            }
            container np-ports {
              description
                "Information of NP ports";
              uses PRM-NP-PORTS;
            }
            container tcam-region-summary {
              description
                "Information of the TCAM region";
              uses TCAM-INFO-SHOW-SUM-REGION;
            }
            container chn-load {
              description
                "prm channel load info";
              uses PRM-NP-CHN-LOAD;
            }
            container np-summary {
              description
                "Information of NP summary";
              uses PRM-NP-SUMMARY;
            }
            container np-fabric-counters {
              description
                "Information of NP fabric counters";
              uses PRM-NP-FAB-CNT;
            }
            container np-interrupts {
              description
                "Information of NP interrupts";
              uses PRM-NP-INTERRUPTS;
            }
            container load-utilization {
              description
                "Hardware np load or utilization";
              uses PRM-NP-LOAD;
            }
            container tcam-summary {
              description
                "prm tcam summary info";
              uses TCAM-INFO-SHOW-SUM;
            }
            container np-interlaken {
              description
                "Information of NP fabric-to-bridge
                 (interlaken) Interfaces";
              uses PRM-NP-ILKN-STS;
            }
            container l2rm-hw-resource {
              description
                "L2rm Hardware Resources";
              uses PRM-NP-L2RM-HW-RSC;
            }
            container profile {
              description
                "Hardware Profile";
              uses PRM-NP-PROFILE;
            }
            container counters {
              description
                "prm counters info";
              uses PRM-NP-COUNTERS;
            }
            container indexed-counters {
              description
                "PRM NP counters info by index";
              list indexed-counter {
                key "counter-index";
                description
                  "List of NP ucode Counters";
                container ucode-counter {
                  description
                    "PRM indexed counter info";
                  uses PRM-NP-INDEXED-COUNTER;
                }
                leaf counter-index {
                  type uint32;
                  description
                    "Indexed Counter Key";
                }
              }
            }
            container resources {
              description
                "sub-leafs for resources displays";
              container tcam {
                description
                  "TCAM section of resources display";
                container one-sixty-ing {
                  description
                    "TCAM Region";
                  container compr-acl {
                    description
                      "TCAM feature utilization";
                    uses PRM-RESOURCES-TCAM-FEATURE;
                  }
                  container compr-ipv6-acl-src-ip {
                    description
                      "TCAM feature utilization";
                    uses PRM-RESOURCES-TCAM-FEATURE;
                  }
                  container qos-fmt-0 {
                    description
                      "TCAM feature utilization";
                    uses PRM-RESOURCES-TCAM-FEATURE;
                  }
                  container qos-fmt-15 {
                    description
                      "TCAM feature utilization";
                    uses PRM-RESOURCES-TCAM-FEATURE;
                  }
                  container compr-acl-dst-port {
                    description
                      "TCAM feature utilization";
                    uses PRM-RESOURCES-TCAM-FEATURE;
                  }
                  container pbr-fmt-4 {
                    description
                      "TCAM feature utilization";
                    uses PRM-RESOURCES-TCAM-FEATURE;
                  }
                  container pbr-l2 {
                    description
                      "TCAM feature utilization";
                    uses PRM-RESOURCES-TCAM-FEATURE;
                  }
                  container ipv6-li {
                    description
                      "TCAM feature utilization";
                    uses PRM-RESOURCES-TCAM-FEATURE;
                  }
                  container qos {
                    description
                      "TCAM feature utilization";
                    uses PRM-RESOURCES-TCAM-FEATURE;
                  }
                  container qos-fmt-1 {
                    description
                      "TCAM feature utilization";
                    uses PRM-RESOURCES-TCAM-FEATURE;
                  }
                  container ipv4-meta-acl {
                    description
                      "TCAM feature utilization";
                    uses PRM-RESOURCES-TCAM-FEATURE;
                  }
                  container pbr-mpls {
                    description
                      "TCAM feature utilization";
                    uses PRM-RESOURCES-TCAM-FEATURE;
                  }
                  container pbr-ipv6 {
                    description
                      "TCAM feature utilization";
                    uses PRM-RESOURCES-TCAM-FEATURE;
                  }
                  container compr-ipv6-acl-dst-ip {
                    description
                      "TCAM feature utilization";
                    uses PRM-RESOURCES-TCAM-FEATURE;
                  }
                  container pbr-fmt-0 {
                    description
                      "TCAM feature utilization";
                    uses PRM-RESOURCES-TCAM-FEATURE;
                  }
                  container edpl {
                    description
                      "TCAM feature utilization";
                    uses PRM-RESOURCES-TCAM-FEATURE;
                  }
                  container qos-fmt-2 {
                    description
                      "TCAM feature utilization";
                    uses PRM-RESOURCES-TCAM-FEATURE;
                  }
                  container compr-ipv4-acl-src-ip {
                    description
                      "TCAM feature utilization";
                    uses PRM-RESOURCES-TCAM-FEATURE;
                  }
                  container l2-acl {
                    description
                      "TCAM feature utilization";
                    uses PRM-RESOURCES-TCAM-FEATURE;
                  }
                  container ipv4-acl {
                    description
                      "TCAM feature utilization";
                    uses PRM-RESOURCES-TCAM-FEATURE;
                  }
                  container qos-fmt-3 {
                    description
                      "TCAM feature utilization";
                    uses PRM-RESOURCES-TCAM-FEATURE;
                  }
                  container ipv6-acl {
                    description
                      "TCAM feature utilization";
                    uses PRM-RESOURCES-TCAM-FEATURE;
                  }
                  container pbr {
                    description
                      "TCAM feature utilization";
                    uses PRM-RESOURCES-TCAM-FEATURE;
                  }
                  container compr-ipv4-acl-dst-ip {
                    description
                      "TCAM feature utilization";
                    uses PRM-RESOURCES-TCAM-FEATURE;
                  }
                  container compr-acl-src-port {
                    description
                      "TCAM feature utilization";
                    uses PRM-RESOURCES-TCAM-FEATURE;
                  }
                  container qos-fmt-4 {
                    description
                      "TCAM feature utilization";
                    uses PRM-RESOURCES-TCAM-FEATURE;
                  }
                  container ipv6-meta-acl {
                    description
                      "TCAM feature utilization";
                    uses PRM-RESOURCES-TCAM-FEATURE;
                  }
                  container ipv4-li {
                    description
                      "TCAM feature utilization";
                    uses PRM-RESOURCES-TCAM-FEATURE;
                  }
                  container pbr-ipv4 {
                    description
                      "TCAM feature utilization";
                    uses PRM-RESOURCES-TCAM-FEATURE;
                  }
                }
                container one-sixty-egr {
                  description
                    "TCAM Region";
                  container compr-acl {
                    description
                      "TCAM feature utilization";
                    uses PRM-RESOURCES-TCAM-FEATURE;
                  }
                  container compr-ipv6-acl-src-ip {
                    description
                      "TCAM feature utilization";
                    uses PRM-RESOURCES-TCAM-FEATURE;
                  }
                  container qos-fmt-0 {
                    description
                      "TCAM feature utilization";
                    uses PRM-RESOURCES-TCAM-FEATURE;
                  }
                  container qos-fmt-15 {
                    description
                      "TCAM feature utilization";
                    uses PRM-RESOURCES-TCAM-FEATURE;
                  }
                  container compr-acl-dst-port {
                    description
                      "TCAM feature utilization";
                    uses PRM-RESOURCES-TCAM-FEATURE;
                  }
                  container pbr-fmt-4 {
                    description
                      "TCAM feature utilization";
                    uses PRM-RESOURCES-TCAM-FEATURE;
                  }
                  container pbr-l2 {
                    description
                      "TCAM feature utilization";
                    uses PRM-RESOURCES-TCAM-FEATURE;
                  }
                  container ipv6-li {
                    description
                      "TCAM feature utilization";
                    uses PRM-RESOURCES-TCAM-FEATURE;
                  }
                  container qos {
                    description
                      "TCAM feature utilization";
                    uses PRM-RESOURCES-TCAM-FEATURE;
                  }
                  container qos-fmt-1 {
                    description
                      "TCAM feature utilization";
                    uses PRM-RESOURCES-TCAM-FEATURE;
                  }
                  container ipv4-meta-acl {
                    description
                      "TCAM feature utilization";
                    uses PRM-RESOURCES-TCAM-FEATURE;
                  }
                  container pbr-mpls {
                    description
                      "TCAM feature utilization";
                    uses PRM-RESOURCES-TCAM-FEATURE;
                  }
                  container pbr-ipv6 {
                    description
                      "TCAM feature utilization";
                    uses PRM-RESOURCES-TCAM-FEATURE;
                  }
                  container compr-ipv6-acl-dst-ip {
                    description
                      "TCAM feature utilization";
                    uses PRM-RESOURCES-TCAM-FEATURE;
                  }
                  container pbr-fmt-0 {
                    description
                      "TCAM feature utilization";
                    uses PRM-RESOURCES-TCAM-FEATURE;
                  }
                  container edpl {
                    description
                      "TCAM feature utilization";
                    uses PRM-RESOURCES-TCAM-FEATURE;
                  }
                  container qos-fmt-2 {
                    description
                      "TCAM feature utilization";
                    uses PRM-RESOURCES-TCAM-FEATURE;
                  }
                  container compr-ipv4-acl-src-ip {
                    description
                      "TCAM feature utilization";
                    uses PRM-RESOURCES-TCAM-FEATURE;
                  }
                  container l2-acl {
                    description
                      "TCAM feature utilization";
                    uses PRM-RESOURCES-TCAM-FEATURE;
                  }
                  container ipv4-acl {
                    description
                      "TCAM feature utilization";
                    uses PRM-RESOURCES-TCAM-FEATURE;
                  }
                  container qos-fmt-3 {
                    description
                      "TCAM feature utilization";
                    uses PRM-RESOURCES-TCAM-FEATURE;
                  }
                  container ipv6-acl {
                    description
                      "TCAM feature utilization";
                    uses PRM-RESOURCES-TCAM-FEATURE;
                  }
                  container pbr {
                    description
                      "TCAM feature utilization";
                    uses PRM-RESOURCES-TCAM-FEATURE;
                  }
                  container compr-ipv4-acl-dst-ip {
                    description
                      "TCAM feature utilization";
                    uses PRM-RESOURCES-TCAM-FEATURE;
                  }
                  container compr-acl-src-port {
                    description
                      "TCAM feature utilization";
                    uses PRM-RESOURCES-TCAM-FEATURE;
                  }
                  container qos-fmt-4 {
                    description
                      "TCAM feature utilization";
                    uses PRM-RESOURCES-TCAM-FEATURE;
                  }
                  container ipv6-meta-acl {
                    description
                      "TCAM feature utilization";
                    uses PRM-RESOURCES-TCAM-FEATURE;
                  }
                  container ipv4-li {
                    description
                      "TCAM feature utilization";
                    uses PRM-RESOURCES-TCAM-FEATURE;
                  }
                  container pbr-ipv4 {
                    description
                      "TCAM feature utilization";
                    uses PRM-RESOURCES-TCAM-FEATURE;
                  }
                }
                container six-forty-ing {
                  description
                    "TCAM Region";
                  container compr-acl {
                    description
                      "TCAM feature utilization";
                    uses PRM-RESOURCES-TCAM-FEATURE;
                  }
                  container compr-ipv6-acl-src-ip {
                    description
                      "TCAM feature utilization";
                    uses PRM-RESOURCES-TCAM-FEATURE;
                  }
                  container qos-fmt-0 {
                    description
                      "TCAM feature utilization";
                    uses PRM-RESOURCES-TCAM-FEATURE;
                  }
                  container qos-fmt-15 {
                    description
                      "TCAM feature utilization";
                    uses PRM-RESOURCES-TCAM-FEATURE;
                  }
                  container compr-acl-dst-port {
                    description
                      "TCAM feature utilization";
                    uses PRM-RESOURCES-TCAM-FEATURE;
                  }
                  container pbr-fmt-4 {
                    description
                      "TCAM feature utilization";
                    uses PRM-RESOURCES-TCAM-FEATURE;
                  }
                  container pbr-l2 {
                    description
                      "TCAM feature utilization";
                    uses PRM-RESOURCES-TCAM-FEATURE;
                  }
                  container ipv6-li {
                    description
                      "TCAM feature utilization";
                    uses PRM-RESOURCES-TCAM-FEATURE;
                  }
                  container qos {
                    description
                      "TCAM feature utilization";
                    uses PRM-RESOURCES-TCAM-FEATURE;
                  }
                  container qos-fmt-1 {
                    description
                      "TCAM feature utilization";
                    uses PRM-RESOURCES-TCAM-FEATURE;
                  }
                  container ipv4-meta-acl {
                    description
                      "TCAM feature utilization";
                    uses PRM-RESOURCES-TCAM-FEATURE;
                  }
                  container pbr-mpls {
                    description
                      "TCAM feature utilization";
                    uses PRM-RESOURCES-TCAM-FEATURE;
                  }
                  container pbr-ipv6 {
                    description
                      "TCAM feature utilization";
                    uses PRM-RESOURCES-TCAM-FEATURE;
                  }
                  container compr-ipv6-acl-dst-ip {
                    description
                      "TCAM feature utilization";
                    uses PRM-RESOURCES-TCAM-FEATURE;
                  }
                  container pbr-fmt-0 {
                    description
                      "TCAM feature utilization";
                    uses PRM-RESOURCES-TCAM-FEATURE;
                  }
                  container edpl {
                    description
                      "TCAM feature utilization";
                    uses PRM-RESOURCES-TCAM-FEATURE;
                  }
                  container qos-fmt-2 {
                    description
                      "TCAM feature utilization";
                    uses PRM-RESOURCES-TCAM-FEATURE;
                  }
                  container compr-ipv4-acl-src-ip {
                    description
                      "TCAM feature utilization";
                    uses PRM-RESOURCES-TCAM-FEATURE;
                  }
                  container l2-acl {
                    description
                      "TCAM feature utilization";
                    uses PRM-RESOURCES-TCAM-FEATURE;
                  }
                  container ipv4-acl {
                    description
                      "TCAM feature utilization";
                    uses PRM-RESOURCES-TCAM-FEATURE;
                  }
                  container qos-fmt-3 {
                    description
                      "TCAM feature utilization";
                    uses PRM-RESOURCES-TCAM-FEATURE;
                  }
                  container ipv6-acl {
                    description
                      "TCAM feature utilization";
                    uses PRM-RESOURCES-TCAM-FEATURE;
                  }
                  container pbr {
                    description
                      "TCAM feature utilization";
                    uses PRM-RESOURCES-TCAM-FEATURE;
                  }
                  container compr-ipv4-acl-dst-ip {
                    description
                      "TCAM feature utilization";
                    uses PRM-RESOURCES-TCAM-FEATURE;
                  }
                  container compr-acl-src-port {
                    description
                      "TCAM feature utilization";
                    uses PRM-RESOURCES-TCAM-FEATURE;
                  }
                  container qos-fmt-4 {
                    description
                      "TCAM feature utilization";
                    uses PRM-RESOURCES-TCAM-FEATURE;
                  }
                  container ipv6-meta-acl {
                    description
                      "TCAM feature utilization";
                    uses PRM-RESOURCES-TCAM-FEATURE;
                  }
                  container ipv4-li {
                    description
                      "TCAM feature utilization";
                    uses PRM-RESOURCES-TCAM-FEATURE;
                  }
                  container pbr-ipv4 {
                    description
                      "TCAM feature utilization";
                    uses PRM-RESOURCES-TCAM-FEATURE;
                  }
                }
                container six-forty-egr {
                  description
                    "TCAM Region";
                  container compr-acl {
                    description
                      "TCAM feature utilization";
                    uses PRM-RESOURCES-TCAM-FEATURE;
                  }
                  container compr-ipv6-acl-src-ip {
                    description
                      "TCAM feature utilization";
                    uses PRM-RESOURCES-TCAM-FEATURE;
                  }
                  container qos-fmt-0 {
                    description
                      "TCAM feature utilization";
                    uses PRM-RESOURCES-TCAM-FEATURE;
                  }
                  container qos-fmt-15 {
                    description
                      "TCAM feature utilization";
                    uses PRM-RESOURCES-TCAM-FEATURE;
                  }
                  container compr-acl-dst-port {
                    description
                      "TCAM feature utilization";
                    uses PRM-RESOURCES-TCAM-FEATURE;
                  }
                  container pbr-fmt-4 {
                    description
                      "TCAM feature utilization";
                    uses PRM-RESOURCES-TCAM-FEATURE;
                  }
                  container pbr-l2 {
                    description
                      "TCAM feature utilization";
                    uses PRM-RESOURCES-TCAM-FEATURE;
                  }
                  container ipv6-li {
                    description
                      "TCAM feature utilization";
                    uses PRM-RESOURCES-TCAM-FEATURE;
                  }
                  container qos {
                    description
                      "TCAM feature utilization";
                    uses PRM-RESOURCES-TCAM-FEATURE;
                  }
                  container qos-fmt-1 {
                    description
                      "TCAM feature utilization";
                    uses PRM-RESOURCES-TCAM-FEATURE;
                  }
                  container ipv4-meta-acl {
                    description
                      "TCAM feature utilization";
                    uses PRM-RESOURCES-TCAM-FEATURE;
                  }
                  container pbr-mpls {
                    description
                      "TCAM feature utilization";
                    uses PRM-RESOURCES-TCAM-FEATURE;
                  }
                  container pbr-ipv6 {
                    description
                      "TCAM feature utilization";
                    uses PRM-RESOURCES-TCAM-FEATURE;
                  }
                  container compr-ipv6-acl-dst-ip {
                    description
                      "TCAM feature utilization";
                    uses PRM-RESOURCES-TCAM-FEATURE;
                  }
                  container pbr-fmt-0 {
                    description
                      "TCAM feature utilization";
                    uses PRM-RESOURCES-TCAM-FEATURE;
                  }
                  container edpl {
                    description
                      "TCAM feature utilization";
                    uses PRM-RESOURCES-TCAM-FEATURE;
                  }
                  container qos-fmt-2 {
                    description
                      "TCAM feature utilization";
                    uses PRM-RESOURCES-TCAM-FEATURE;
                  }
                  container compr-ipv4-acl-src-ip {
                    description
                      "TCAM feature utilization";
                    uses PRM-RESOURCES-TCAM-FEATURE;
                  }
                  container l2-acl {
                    description
                      "TCAM feature utilization";
                    uses PRM-RESOURCES-TCAM-FEATURE;
                  }
                  container ipv4-acl {
                    description
                      "TCAM feature utilization";
                    uses PRM-RESOURCES-TCAM-FEATURE;
                  }
                  container qos-fmt-3 {
                    description
                      "TCAM feature utilization";
                    uses PRM-RESOURCES-TCAM-FEATURE;
                  }
                  container ipv6-acl {
                    description
                      "TCAM feature utilization";
                    uses PRM-RESOURCES-TCAM-FEATURE;
                  }
                  container pbr {
                    description
                      "TCAM feature utilization";
                    uses PRM-RESOURCES-TCAM-FEATURE;
                  }
                  container compr-ipv4-acl-dst-ip {
                    description
                      "TCAM feature utilization";
                    uses PRM-RESOURCES-TCAM-FEATURE;
                  }
                  container compr-acl-src-port {
                    description
                      "TCAM feature utilization";
                    uses PRM-RESOURCES-TCAM-FEATURE;
                  }
                  container qos-fmt-4 {
                    description
                      "TCAM feature utilization";
                    uses PRM-RESOURCES-TCAM-FEATURE;
                  }
                  container ipv6-meta-acl {
                    description
                      "TCAM feature utilization";
                    uses PRM-RESOURCES-TCAM-FEATURE;
                  }
                  container ipv4-li {
                    description
                      "TCAM feature utilization";
                    uses PRM-RESOURCES-TCAM-FEATURE;
                  }
                  container pbr-ipv4 {
                    description
                      "TCAM feature utilization";
                    uses PRM-RESOURCES-TCAM-FEATURE;
                  }
                }
              }
            }
            container fast-drop {
              description
                "prm fast drop counters info";
              uses PRM-NP-FAST-DROP;
            }
            container efd {
              description
                "EFD COS to Priority Mapping";
              uses PRM-EFD;
            }
            container np-punt-path-counters {
              description
                "Information of NP Punt path counters";
              uses PRM-NP-PUNT-CNT;
            }
            leaf np-name {
              type Np;
              description
                "NP name";
            }
          }
        }
        leaf node-name {
          type xr:Node-id;
          description
            "node number";
        }
      }
    }
  }
}
