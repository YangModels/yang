module Cisco-IOS-XR-system-reboot-act {
  namespace "http://cisco.com/ns/yang/Cisco-IOS-XR-system-reboot-act";
  prefix system-reboot-act;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR system reboot operations corresponding
     to the gNOI system.proto definitions.
     
     Copyright (c) 2019-2020, 2022 by Cisco Systems, Inc.
     All rights reserved.";

  revision 2022-03-07 {
    description
      "Added cancel reboot request rpc";
    semver:module-version "1.1.0";
  }
  revision 2020-07-15 {
    description
      "IOS XR 7.0.12 revision.";
    semver:module-version "1.0.0";
  }

  typedef location-name {
    type string {
      length "1..64";
    }
    description
      "Fully qualified location specification, e.g. 0/RP0/CPU0";
  }

  typedef reboot-method {
    type enumeration {
      enum "unknown" {
        description
          "Invalid default method";
      }
      enum "cold" {
        description
          "Shutdown and restart OS and all hardware";
      }
      enum "powerdown" {
        description
          "Halt and power down, if possible";
      }
      enum "halt" {
        description
          "Halt, if possible";
      }
      enum "warm" {
        description
          "Reload configuration but not underlying hardware";
      }
      enum "nsf" {
        description
          "Non-stop-forwarding reboot, if possible";
      }
      enum "reset" {
        description
          "Reboot to factory defaults";
      }
      enum "powerup" {
        description
          "Apply power, no-op if power is already on";
      }
    }
    description
      "Reboot action type";
  }

  typedef boot-media {
    type enumeration {
      enum "network" {
        description
          "Load image from network directory";
      }
      enum "usb" {
        description
          "Load image from USB directory";
      }
    }
    description
      "Boot media Type";
  }

  rpc reboot-request {
    description
      "Boot, reboot, or shutdown the specified entity";
    input {
      leaf method {
        type reboot-method;
        mandatory true;
        description
          "Reboot operation type";
      }
      leaf delay {
        type uint64;
        description
          "Delay in nanoseconds before issuing command";
      }
      leaf message {
        type string;
        description
          "Informational reason for the operation";
      }
      leaf location {
        type location-name;
        description
          "Fully qualified location specification";
      }
      leaf force {
        type boolean;
        description
          "Do not wait for software to shutdown gracefully";
      }
      leaf bootmedia {
        type boot-media;
        description
          "Bootmedia type";
      }
    }
  }
  rpc cancel-reboot-request {
    description
      "Cancel reboot request";
    input {
      leaf location {
        type location-name;
        description
          "Fully qualified location specification";
      }
    }
  }
  rpc reboot-status-request {
    description
      "Retrieves the latest boot status of the specified entity";
    input {
      leaf location {
        type location-name;
        mandatory true;
        description
          "Fully qualified location specification";
      }
    }
    output {
      container reboot-status-response {
        description
          "Latest boot status of the target";
        leaf active {
          type boolean;
          description
            "Set to true if reboot is active";
        }
        leaf wait {
          type uint64;
          description
            "Time left until reboot";
        }
        leaf when {
          type uint64;
          description
            "Time to reboot in nanoseconds since the epoch";
        }
        leaf reason {
          type string;
          description
            "Reason for reboot";
        }
        leaf count {
          type uint32;
          description
            "Number of reboots since active";
        }
      }
    }
  }
}
