module Cisco-IOS-XR-sks-act {
  namespace "http://cisco.com/ns/yang/Cisco-IOS-XR-sks-act";
  prefix sks-act;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR action package configuration.
     
     Copyright (c) 2020 by Cisco Systems, Inc.
     All rights reserved.";

  revision 2020-10-14 {
    description
      "IOS XR 7.4.1 revision.";
    semver:module-version "1.0.0";
  }

  rpc key-generate-mceliece {
    description
      "Generate a mceliece key pair used for exporting/importing sks seeds";
    input {
      leaf key-label {
        type string;
        description
          "Mceliece key label";
      }
    }
  }
  rpc key-zeroize-mceliece {
    description
      "Remove the generated mceliece key pair";
    input {
      leaf key-label {
        type string;
        description
          "Mceliece key label";
      }
    }
  }
  rpc key-import-peer-mceliece {
    description
      "Import a peer's mceliece pubkey used for exporting sks seeds";
    input {
      leaf peer-label {
        type string;
        mandatory true;
        description
          "Name of the peer";
      }
      leaf path {
        type string;
        mandatory true;
        description
          "Path to Mceliece pubkey file";
      }
    }
  }
  rpc key-remove-peer-mceliece {
    description
      "Remove a peer's imported mceliece pubkey";
    input {
      leaf peer-label {
        type string;
        mandatory true;
        description
          "Name of the peer";
      }
    }
  }
  rpc key-export-self-mceliece {
    description
      "Export self mceliece pubkey";
    input {
      leaf key-label {
        type string;
        description
          "Name of the peer";
      }
      leaf path {
        type string;
        description
          "Path to Mceliece pubkey file";
      }
    }
  }
  rpc seed-import-peer-mceliece {
    description
      "Import sks seed for a peer";
    input {
      leaf peer-label {
        type string;
        mandatory true;
        description
          "Name of the peer to which the seed has to be imported";
      }
      leaf path {
        type string;
        mandatory true;
        description
          "Path to the seed file(Encrypted using peers Mceliece key)";
      }
    }
  }
  rpc seed-export-peer-mceliece {
    description
      "Export sks seed for a peer";
    input {
      leaf peer-label {
        type string;
        mandatory true;
        description
          "Name of the peer to which the seed has to be exported";
      }
      leaf path {
        type string;
        description
          "Path to the seed file(Encrypted using peers Mceliece key)";
      }
    }
  }
}
