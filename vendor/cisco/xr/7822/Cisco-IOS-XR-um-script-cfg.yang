module Cisco-IOS-XR-um-script-cfg {
  namespace "http://cisco.com/ns/yang/Cisco-IOS-XR-um-script-cfg";
  prefix um-script-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR script package configuration.
     
     This YANG module augments the
     modules with configuration data.
     
     Copyright (c) 2022 by Cisco Systems, Inc.
     All rights reserved.";

  revision 2022-09-06 {
    description
      "Added precommit support
       2022-02-17
         Added snmp support";
    semver:module-version "1.1.0";
  }
  revision 2021-04-19 {
    description
      "Initial release";
    semver:module-version "1.0.0";
  }

  feature exec-supported {
    description
      "Exec supported";
  }

  feature process-supported {
    description
      "Process supported";
  }

  feature snmp-supported {
    description
      "Snmp supported";
  }

  container script {
    description
      "Commands for activating on-box scripts";
    container execs {
      description
        "Configure exec script";
      list exec {
        if-feature "exec-supported";
        must "checksum/disable-checksum-security or checksum/sha256";
        key "exec-name";
        description
          "Configure exec script";
        leaf exec-name {
          type xr:Cisco-ios-xr-string {
            length "1..800" {
              description
                "specify the filename of the script";
            }
          }
          description
            "Configure exec script";
        }
        container checksum {
          description
            "Specify a checksum for the script, or disable checksum enforcement";
          container disable-checksum-security {
            must "not(../sha256)";
            presence "Indicates a disable-checksum-security node is configured.";
            description
              "Disable checksum enforcement for this script";
          }
          leaf sha256 {
            type xr:Cisco-ios-xr-string {
              length "1..800" {
                description
                  "The SHA256 hash (64 hex characters) ";
              }
            }
            must "not(../disable-checksum-security)";
            description
              "Specify an SHA256 checksum";
          }
        }
      }
    }
    container processes {
      description
        "Configure Process script";
      list process {
        if-feature "process-supported";
        must "checksum/disable-checksum-security or checksum/sha256";
        key "process-name";
        description
          "Configure Process script";
        leaf process-name {
          type xr:Cisco-ios-xr-string {
            length "1..800" {
              description
                "specify the filename of the script";
            }
          }
          description
            "Configure Process script";
        }
        container checksum {
          description
            "Specify a checksum for the script, or disable checksum enforcement";
          container disable-checksum-security {
            must "not(../sha256)";
            presence "Indicates a disable-checksum-security node is configured.";
            description
              "Disable checksum enforcement for this script";
          }
          leaf sha256 {
            type xr:Cisco-ios-xr-string {
              length "1..800" {
                description
                  "The SHA256 hash (64 hex characters) ";
              }
            }
            must "not(../disable-checksum-security)";
            description
              "Specify an SHA256 checksum";
          }
        }
      }
    }
    container snmps {
      description
        "Configure snmp script";
      list snmp {
        if-feature "snmp-supported";
        must "checksum/disable-checksum-security or checksum/sha256";
        key "snmp-name";
        description
          "Configure snmp script";
        leaf snmp-name {
          type xr:Cisco-ios-xr-string {
            length "1..800" {
              description
                "specify the filename of the script";
            }
          }
          description
            "Configure snmp script";
        }
        container checksum {
          description
            "Specify a checksum for the script, or disable checksum enforcement";
          container disable-checksum-security {
            must "not(../sha256)";
            presence "Indicates a disable-checksum-security node is configured.";
            description
              "Disable checksum enforcement for this script";
          }
          leaf sha256 {
            type xr:Cisco-ios-xr-string {
              length "1..800" {
                description
                  "The SHA256 hash (64 hex characters) ";
              }
            }
            must "not(../disable-checksum-security)";
            description
              "Specify an SHA256 checksum";
          }
        }
      }
    }
    container precommit {
      description
        "Configure Precommit script";
      container script-names {
        description
          "Specify the filename of the script (must end in .py)";
        list script-name {
          key "script-name";
          description
            "Specify the filename of the script (must end in .py)";
          leaf script-name {
            type xr:Cisco-ios-xr-string {
              length "1..800" {
                description
                  "Specify the filename of the script (must end in .py)";
              }
              pattern "[a-zA-Z0-9_.-]+";
            }
            description
              "Specify the filename of the script (must end in .py)";
          }
          container checksum {
            description
              "Specify a checksum for the script";
            leaf sha256 {
              type xr:Cisco-ios-xr-string {
                length "1..800" {
                  description
                    "The SHA256 hash (64 hex characters) ";
                }
                pattern "[A-Fa-f0-9]{64}";
              }
              description
                "Specify an SHA256 checksum";
            }
            leaf priority {
              type uint32 {
                range "1..100" {
                  description
                    "priority of script";
                }
              }
              description
                "priority";
            }
          }
        }
      }
    }
  }
}
