submodule Cisco-IOS-XR-l2-snoop-oper-sub1 {
  belongs-to Cisco-IOS-XR-l2-snoop-oper {
    prefix Cisco-IOS-XR-l2-snoop-oper;
  }

  import ietf-inet-types {
    prefix inet;
  }
  import ietf-yang-types {
    prefix yang;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR l2-snoop package operational data.
     
     Copyright (c) 2013-2022 by Cisco Systems, Inc.
     All rights reserved.";

  revision 2022-06-28 {
    description
      "backward compatible edit, in interface-name.
       2022-03-30
         backward compatible addition, in leaf l2fib-replay-time was added";
    semver:module-version "1.1.0";
  }
  revision 2021-06-21 {
    description
      "Added the Snooping oper yang model";
    semver:module-version "1.0.0";
  }
  revision 2019-04-05 {
    description
      "Establish semantic version baseline.";
  }
  revision 2015-11-09 {
    description
      "IOS XR 6.0 revision.";
  }

  typedef Igmpsn-iccp-app-rg-state {
    type enumeration {
      enum "initializing" {
        value 0;
        description
          "Init";
      }
      enum "connecting" {
        value 1;
        description
          "Connecting";
      }
      enum "connected-no-peers" {
        value 2;
        description
          "Connected No Peers";
      }
      enum "connect-peer-present" {
        value 3;
        description
          "Connect Peer Present";
      }
      enum "iccp-down" {
        value 4;
        description
          "ICCP Down";
      }
    }
    description
      "igmp snooping Redundancy Application State";
  }

  typedef Igmpsn-iccp-app-rg-port-state {
    type enumeration {
      enum "interface-initialized" {
        value 0;
        description
          "Init";
      }
      enum "active-no-peers" {
        value 1;
        description
          "Active No Peers";
      }
      enum "active-no-peers-congestion" {
        value 2;
        description
          "Active No Peers Congestion";
      }
      enum "standby-no-peers" {
        value 3;
        description
          "Standby No Peers";
      }
      enum "standby-no-peers-congestion" {
        value 4;
        description
          "Standby No Peers Congestion";
      }
      enum "down-no-peers" {
        value 5;
        description
          "Down No Peers";
      }
      enum "down-no-peers-congestion" {
        value 6;
        description
          "Down No Peers Congestion";
      }
      enum "standby-peers" {
        value 7;
        description
          "Standby Peers";
      }
      enum "standby-peers-congestion" {
        value 8;
        description
          "Standby Peers Congestion";
      }
      enum "standby-peers-sync-request" {
        value 9;
        description
          "Standby Peers Sync Request";
      }
      enum "standby-peers-sync-request-congestion" {
        value 10;
        description
          "Standby Peers Sync Request Congestion";
      }
      enum "standby-peers-sync-req-wait" {
        value 11;
        description
          "Standby Peers Sync Request Wait";
      }
      enum "active-peers" {
        value 12;
        description
          "Active Peers";
      }
      enum "active-peers-congestion" {
        value 13;
        description
          "Active Peers Congestion";
      }
      enum "active-peers-sync" {
        value 14;
        description
          "Active Peers Sync";
      }
      enum "active-peers-sync-congestion" {
        value 15;
        description
          "Active Peers Sync Congestion";
      }
      enum "active-peers-sync-wait" {
        value 16;
        description
          "Active Peers Sync Wait";
      }
      enum "down-peers" {
        value 17;
        description
          "Down Peers";
      }
      enum "down-peers-congestion" {
        value 18;
        description
          "Down Peers Congestion";
      }
      enum "standby-iccp-down" {
        value 19;
        description
          "Standby ICCP Down";
      }
      enum "active-iccp-down" {
        value 20;
        description
          "Active ICCP Down";
      }
      enum "down-iccp-down" {
        value 21;
        description
          "Down ICCP Down";
      }
    }
    description
      "ICCP Redundancy Group Port State";
  }

  typedef Igmpsn-bag-iccp-app-redundancy-state {
    type enumeration {
      enum "redundancy-state-down" {
        value 0;
        description
          "Redundancy State Down";
      }
      enum "redundancy-state-standby" {
        value 1;
        description
          "Redundancy State Standby";
      }
      enum "redundancy-state-active" {
        value 2;
        description
          "Redundancy State Active";
      }
    }
    description
      "ICCP Application Redundancy State";
  }

  typedef Set-bool {
    type enumeration {
      enum "0" {
        value 0;
        description
          "False";
      }
      enum "1" {
        value 1;
        description
          "True";
      }
    }
    description
      "Set bool";
  }

  typedef Ipv6-address {
    type inet:ipv6-address;
    description
      "IPV6 Address type";
  }

  typedef Igmpsn-afi {
    type enumeration {
      enum "ipv4-unicast" {
        value 0;
        description
          "IP v4 unicast";
      }
      enum "ipv6-unicast" {
        value 1;
        description
          "IP v6 unicast";
      }
    }
    description
      "Address family";
  }

  grouping IGMPSN-EDM-PORT-GROUP-SOURCE-BAG {
    description
      "IGMPSN EDM PORT GROUP SOURCE BAG";
    container source {
      description
        "Source";
      uses IGMPSN-ADDRTYPE;
    }
    container expires {
      description
        "Source expires in seconds";
      uses RUNNING-TIMER;
    }
    leaf uptime {
      type uint64;
      units "second";
      description
        "Uptime in seconds";
    }
    leaf static-source {
      type boolean;
      description
        "Static source";
    }
    leaf dynamic-source {
      type boolean;
      description
        "Dynamic source";
    }
    leaf evpn-source {
      type boolean;
      description
        "EVPN source";
    }
    leaf admitted-weight {
      type uint32;
      description
        "Admitted weight";
    }
    leaf nv-offload {
      type boolean;
      description
        "Offload enabled";
    }
    leaf cli-nv-offload {
      type boolean;
      description
        "CLI Offload disabled";
    }
    leaf shg-nv-offload {
      type boolean;
      description
        "SHG Offload disabled";
    }
    leaf mrouter-nv-offload {
      type boolean;
      description
        "MRouter Offload disabled";
    }
    leaf topo-not-supported-nv-offload {
      type boolean;
      description
        "Topo not supported Offload disabled";
    }
    list igmpsn-edm-moi-id {
      description
        "EVPN moi ID list";
      uses IGMPSN-EDM-MOI-ID-BAG;
    }
  }

  grouping IGMPSN-EDM-PORT-GROUP-BAG {
    description
      "IGMPSN EDM PORT GROUP BAG";
    container group-address-xr {
      description
        "Group address";
      uses IGMPSN-ADDRTYPE;
    }
    container expires {
      description
        "Group expires in seconds";
      uses RUNNING-TIMER;
    }
    container v2-host-present {
      description
        "IGMP V2/MLD V1 host present timer";
      uses RUNNING-TIMER;
    }
    leaf bridge-domain-name {
      type string {
        length "0..65";
      }
      description
        "Bridge domain name";
    }
    leaf interface-name {
      type string {
        length "0..321";
      }
      description
        "Port name";
    }
    leaf pseudowire {
      type boolean;
      description
        "Pseudowire";
    }
    leaf version {
      type uint8;
      description
        "Version";
    }
    leaf uptime {
      type uint64;
      units "second";
      description
        "Uptime in seconds";
    }
    leaf static-group {
      type boolean;
      description
        "Static group";
    }
    leaf dynamic-group {
      type boolean;
      description
        "Dynamic group";
    }
    leaf evpn-group {
      type boolean;
      description
        "BGP learnt group";
    }
    leaf port-mode-is-exclude {
      type boolean;
      description
        "Port mode is exclude";
    }
    leaf group-mode-is-exclude {
      type boolean;
      description
        "Group mode is exclude";
    }
    leaf source-count {
      type int32;
      description
        "Source count";
    }
    leaf group-policy-applied {
      type boolean;
      description
        "Group policy applied";
    }
    leaf admitted-weight {
      type uint32;
      description
        "Admitted weight";
    }
    leaf nv-offload {
      type boolean;
      description
        "Offload enabled";
    }
    leaf cli-nv-offload {
      type boolean;
      description
        "CLI Offload disabled";
    }
    leaf shg-nv-offload {
      type boolean;
      description
        "SHG Offload disabled";
    }
    leaf mrouter-nv-offload {
      type boolean;
      description
        "MRouter Offload disabled";
    }
    leaf topo-not-supported-nv-offload {
      type boolean;
      description
        "Topo not supported Offload disabled";
    }
    leaf group-id {
      type uint32;
      description
        "ICCP Group ID";
    }
    leaf iccp-port-redundancy-state {
      type Igmpsn-bag-iccp-app-redundancy-state;
      description
        "ICCP Group port redundancy state";
    }
    list port-group-source {
      description
        "Port group source list";
      uses IGMPSN-EDM-PORT-GROUP-SOURCE-BAG;
    }
    list igmpsn-edm-moi-id {
      description
        "EVPN moi ID list";
      uses IGMPSN-EDM-MOI-ID-BAG;
    }
  }

  grouping IGMPSN-EDM-SUMMARY-BAG {
    description
      "IGMP/MLD snooping summary info";
    container packet-statistics {
      description
        "Summary packet statistics";
      uses IGMPSN-PKT-STATS-BAG;
    }
    container evpn-statistics {
      description
        "EVPN statistics";
      uses IGMPSN-EVPN-STATS-BAG;
    }
    container common-statistics {
      description
        "Summary common statistics";
      uses IGMPSN-COMMON-STATS-BAG;
    }
    container iccp-statistics {
      description
        "Summary ICCP statistics";
      uses IGMPSN-ICCP-STATS-BAG;
    }
    container iccp-group-port-statistics {
      description
        "Summary ICCP Group Port statistics";
      uses IGMPSN-ICCP-GROUP-PORT-STATS-BAG;
    }
    container iccp-traffic-statistics {
      description
        "Summary ICCP traffic statistics";
      uses IGMPSN-ICCP-TRAFFIC-STATS-BAG;
    }
    container iccp-app-iccp-state {
      description
        "Summary ICCP App ICCP state";
      uses ICCP-APP-ICCP-STATE-BAG;
    }
    container iccp-app-statistics {
      description
        "Summary ICCP App ICCP statistics";
      uses ICCP-APP-ICCP-STATS-BAG;
    }
    container iccp-app-iccp-group-statistics {
      description
        "Summary ICCP App ICCP Group statistics";
      uses ICCP-APP-ICCP-GROUP-STATS-BAG;
    }
    container iccp-app-ig-port-statistics {
      description
        "Summary ICCP App ICCP Group Port statistics";
      uses ICCP-APP-IG-PORT-STATS-BAG;
    }
    leaf number-of-bridge-domains {
      type uint32;
      description
        "Number of bridge domains";
    }
    leaf number-of-igmp-snooping-bridge-domain {
      type uint32;
      description
        "Number of bridge domains with IGMP/MLD snooping
         enabled";
    }
    leaf number-of-ports {
      type uint32;
      description
        "Number of ports";
    }
    leaf number-of-igmp-snooping-ports {
      type uint32;
      description
        "Number of ports with IGMP/MLD snooping enabled";
    }
    leaf number-of-mrouters {
      type uint32;
      description
        "Number of mrouters";
    }
    leaf number-of-stp-ports {
      type uint32;
      description
        "Number of STP ports";
    }
    leaf number-of-ig-ports {
      type uint32;
      description
        "Number of ICCP Group ports";
    }
    leaf number-of-groups {
      type uint32;
      description
        "Number of groups";
    }
    leaf number-of-group-o-ports {
      type uint32;
      description
        "Number of group o-ports";
    }
    leaf number-of-group-sources {
      type uint32;
      description
        "Number of group sources";
    }
    leaf number-of-group-source-statics {
      type uint32;
      description
        "Number of static group sources";
    }
    leaf number-of-group-source-includes {
      type uint32;
      description
        "Number of include group sources";
    }
    leaf number-of-group-source-excludes {
      type uint32;
      description
        "Number of exclude group sources";
    }
    leaf number-of-group-source-include-ports {
      type uint32;
      description
        "Number of group source include ports";
    }
    leaf number-of-group-source-exclude-ports {
      type uint32;
      description
        "Number of group source exclude ports";
    }
    leaf number-plfm-oor-cnt {
      type uint32;
      description
        "Number of platform OOR clear notifications
         received";
    }
    leaf star-star-oor-fail-cnt {
      type uint32;
      description
        "Star Star Mroute OOR Fail Count";
    }
    leaf star-goor-fail-cnt {
      type uint32;
      description
        "StarG Mroute OOR Fail Count";
    }
    leaf sgoor-fail-cnt {
      type uint32;
      description
        "SG Mroute OOR Fail Count";
    }
    leaf l2fib-elapsed-time {
      type uint32;
      description
        "L2FIB elapsed time";
    }
    leaf bdxc-created-notifications {
      type uint32;
      description
        "BDXC created notifications";
    }
    leaf bdxc-deleted-notifications {
      type uint32;
      description
        "BDXC deleted notifications";
    }
    leaf bdxcefp-added-notifications {
      type uint32;
      description
        "BDXC EFP added notifications";
    }
    leaf bdxcefp-removed-notifications {
      type uint32;
      description
        "BDXC EFP removed notifications";
    }
    leaf bdxcefpstp-change-notifications {
      type uint32;
      description
        "BDXC EFP STP change notifications";
    }
    leaf bdxc-topology-change-notifications {
      type uint32;
      description
        "BDXC topology change notifications";
    }
    leaf bridge-domain-added {
      type uint32;
      description
        "Bridge domain added";
    }
    leaf bridge-domain-deleted {
      type uint32;
      description
        "Bridge domain deleted";
    }
    leaf bridge-domain-profile-changed {
      type uint32;
      description
        "Bridge domain profile changed";
    }
    leaf bridge-domain-profile-added {
      type uint32;
      description
        "Bridge domain profile added";
    }
    leaf bridge-domain-profile-removed {
      type uint32;
      description
        "Bridge domain profile removed";
    }
    leaf bridge-domain-profile-update-failed {
      type uint32;
      description
        "Bridge domina profile update failed";
    }
    leaf bridge-domain-not-found {
      type uint32;
      description
        "Bridge domain not found";
    }
    leaf bridge-domain-port-not-found {
      type uint32;
      description
        "Bridge domain port not found";
    }
    leaf efp-added {
      type uint32;
      description
        "EFP added";
    }
    leaf efp-deleted {
      type uint32;
      description
        "EFP deleted";
    }
    leaf efp-profile-changed {
      type uint32;
      description
        "EFP profile changed";
    }
    leaf efp-profile-unchanged {
      type uint32;
      description
        "EFP profile unchanged";
    }
    leaf efp-profile-added {
      type uint32;
      description
        "EFP profile added";
    }
    leaf efp-profile-removed {
      type uint32;
      description
        "EFP profile removed";
    }
    leaf efp-profile-update-failed {
      type uint32;
      description
        "EFP profile update failed";
    }
    leaf efp-oper-state-changed-to-up {
      type uint32;
      description
        "EFP oper state changed to up";
    }
    leaf efp-oper-state-changed-to-down {
      type uint32;
      description
        "EFP oper state changed to down";
    }
    leaf efpstp-state-changed-to-forwarding {
      type uint32;
      description
        "EFP STP state changed to forwarding";
    }
    leaf efpstp-state-changed-to-blocked {
      type uint32;
      description
        "EFP STP state changed to blocked";
    }
    leaf efpstp-state-changed-to-not-participating {
      type uint32;
      description
        "EFP STP state changed to not participating";
    }
    leaf efp-bridge-domain-mismatch {
      type uint32;
      description
        "EFP bridge domain mismatch";
    }
    leaf efp-interface-handle-mismatch {
      type uint32;
      description
        "EFP interface handle mismatch";
    }
    leaf efp-interface-name-mismatch {
      type uint32;
      description
        "EFP interface name mismatch";
    }
    leaf l2fib-no-memory {
      type uint32;
      description
        "L2FIB no memory";
    }
    leaf bridge-domain-create-failed {
      type uint32;
      description
        "Bridge domain create failed";
    }
    leaf bridge-domain-port-create-failed {
      type uint32;
      description
        "Bridge domain create failed";
    }
    leaf bridge-domain-port-state-change-failed {
      type uint32;
      description
        "Bridge domain port state change failed";
    }
    leaf bridge-domain-batch-start-called {
      type uint32;
      description
        "Bridge domain start called";
    }
    leaf bridge-domain-batch-end-called {
      type uint32;
      description
        "Bridge domain batch end called";
    }
    leaf bridge-domain-mark-called {
      type uint32;
      description
        "Bridge domain mark called";
    }
    leaf bridge-domain-sweep-called {
      type uint32;
      description
        "Bridge domain sweep called";
    }
    leaf efp-batch-start-called {
      type uint32;
      description
        "EFP batch start called";
    }
    leaf efp-batch-end-called {
      type uint32;
      description
        "EFP batch end called";
    }
    leaf efp-mark-called {
      type uint32;
      description
        "EFP mark called";
    }
    leaf efp-sweep-called {
      type uint32;
      description
        "EFP sweep called";
    }
    leaf l2fib-replay-called {
      type uint32;
      description
        "L2FIB replay called";
    }
    leaf mroute-messages-sent {
      type uint32;
      description
        "Mroute messages sent";
    }
    leaf config-messages-sent {
      type uint32;
      description
        "Configure messages sent";
    }
    leaf bdxc-send-called {
      type uint32;
      description
        "BDXC send called";
    }
    leaf bdxc-send-failures {
      type uint32;
      description
        "BDXC send failures";
    }
    leaf mgid-allocations {
      type uint32;
      description
        "MGID allocations";
    }
    leaf mgid-free {
      type uint32;
      description
        "MGID frees";
    }
    leaf mgid-allocation-failures {
      type uint32;
      description
        "MGID allocation failures";
    }
    leaf impossible-errors {
      type uint32;
      description
        "Impossible errors";
    }
    leaf bdxc-congestion {
      type boolean;
      description
        "BDXC congestion";
    }
    leaf bdxc-congestion-count {
      type uint32;
      description
        "BDXC congestion count";
    }
    leaf bdxc-congestion-clear-count {
      type uint32;
      description
        "BDXC congestion clear count";
    }
    leaf bdxc-congestion-notify-count {
      type uint32;
      description
        "BDXC congestion notify count";
    }
    leaf last-bdxc-congestion-time {
      type uint32;
      description
        "Last BDXC congestion time";
    }
    leaf l2fib-replay-time {
      type uint32;
      description
        "L2FIB Replay time";
    }
    leaf net-elapsed-time {
      type uint32;
      description
        "Net elapsed time";
    }
    leaf connection-open-failed {
      type uint32;
      description
        "Connection open failed";
    }
    leaf socket-event {
      type uint32;
      description
        "Socket event";
    }
    leaf packet-server-code-abort {
      type uint32;
      description
        "Packet server code abort";
    }
    leaf connection-open-event {
      type uint32;
      description
        "Connection open event";
    }
    leaf connection-close-event {
      type uint32;
      description
        "Connection close event";
    }
    leaf connection-unknown-event {
      type uint32;
      description
        "Connection unknown event";
    }
    leaf connection-setretry-failed {
      type uint32;
      description
        "Connection setretry failed";
    }
    leaf connection-get-fd-failed {
      type uint32;
      description
        "Connection get fd failed";
    }
    leaf packet-event {
      type uint32;
      description
        "Packet event";
    }
    leaf packet-event-disconnect {
      type uint32;
      description
        "Packet event disconnect";
    }
    leaf packet-event-empty {
      type uint32;
      description
        "Packet event empty";
    }
    leaf packet-event-empty-watermark {
      type uint32;
      description
        "Packet event empty watermark";
    }
    leaf packet-event-receive-error {
      type uint32;
      description
        "Packet event rx error";
    }
    leaf packet-event-receive-error-evm-retry {
      type uint32;
      description
        "Packet event rx error evm retry";
    }
    leaf packet-event-receive-chunk-pulse {
      type uint32;
      description
        "Packet event rx chunk pulse";
    }
    leaf receive-packet-null {
      type uint32;
      description
        "Receive packet null";
    }
    leaf receive-pakman-error {
      type uint32;
      description
        "Receive pakman error";
    }
    leaf receive-packet-free-error {
      type uint32;
      description
        "Receive packet free error";
    }
    leaf receive-bridge-domain-port-not-found {
      type uint32;
      description
        "Receive bridge domain port not found";
    }
    leaf receive-pim-packet-not-hello {
      type uint32;
      description
        "Receive PIM packet not hello";
    }
    leaf receive-igmp-packet-attempt {
      type uint32;
      description
        "Receive IGMP/MLD packet attempt";
    }
    leaf receive-igmp-packet-success {
      type uint32;
      description
        "Receive IGMP/MLD packet success";
    }
    leaf receive-pim-packet-attempt {
      type uint32;
      description
        "Receive PIM packet attempt";
    }
    leaf receive-pim-packet-success {
      type uint32;
      description
        "Receive PIM packet success";
    }
    leaf transmit-packet-bad-socket {
      type uint32;
      description
        "Transmit packet bad socket";
    }
    leaf transmit-packet-no-packet-buffers {
      type uint32;
      description
        "Transmit packet no packet buffers";
    }
    leaf transmit-pakman-error {
      type uint32;
      description
        "Transmit pakman error";
    }
    leaf transmit-packet-format-error {
      type uint32;
      description
        "Transmit packet format error";
    }
    leaf transmit-igmp-packet-attempt {
      type uint32;
      description
        "Transmit IGMP/MLD packet attempt";
    }
    leaf transmit-igmp-packet-success {
      type uint32;
      description
        "Transmit IGMP/MLD packet success";
    }
    leaf net-no-memory {
      type uint32;
      description
        "Net no memory";
    }
    leaf internal-elapsed-time {
      type uint32;
      description
        "Internal elapsed time";
    }
    leaf malloc-failure {
      type uint32;
      description
        "Malloc failure";
    }
    leaf v3-group-source-specific-query-construct-error {
      type uint32;
      description
        "IGMP V3/MLD V2 group source specific query
         construct error";
    }
    leaf v3-group-source-specific-query-split {
      type uint32;
      description
        "IGMP V3/MLD V2 group source specific query split";
    }
    leaf v3-report-construct-error {
      type uint32;
      description
        "IGMP V3/MLD V2 report construct error";
    }
    leaf v3-report-split {
      type uint32;
      description
        "IGMP V3/MLD V2 report split";
    }
    leaf v3-record-split {
      type uint32;
      description
        "IGMP V3/MLD V2 record split";
    }
    leaf receive-buffers {
      type uint32;
      description
        "Number of AIPC buffers received";
    }
    leaf release-buffers {
      type uint32;
      description
        "Number of AIPC buffers released";
    }
    leaf send-blocks {
      type uint32;
      description
        "Number of AIPC buffers send blocked";
    }
    leaf release-fail-buffers {
      type uint32;
      description
        "Number of AIPC buffers release failed";
    }
    leaf null-buffer-handles {
      type uint32;
      description
        "Number of AIPC NULL buffer handles";
    }
    leaf rx-ipc-open-notif {
      type uint32;
      description
        "Number of AIPC open notifications received";
    }
    leaf rx-ipc-close-notif {
      type uint32;
      description
        "Number of AIPC close notifications received";
    }
    leaf rx-ipc-error-notif {
      type uint32;
      description
        "Number of AIPC error notifications received";
    }
    leaf rx-ipc-lwm-notif {
      type uint32;
      description
        "Number of AIPC LWM notifications received";
    }
    leaf rx-ipc-hwm-notif {
      type uint32;
      description
        "Number of AIPC HWM notifications received";
    }
    leaf rx-ipc-input-wait-notif {
      type uint32;
      description
        "Number of AIPC input waiting notifications
         received";
    }
    leaf rx-ipc-send-status-notif {
      type uint32;
      description
        "Number of AIPC send status notifications
         received";
    }
    leaf rx-ipc-publish-notif {
      type uint32;
      description
        "Number of AIPC publish notifications received";
    }
    leaf rx-ipc-q-full-notif {
      type uint32;
      description
        "Number of AIPC queue full notifications received";
    }
    leaf rx-ipc-output-notif {
      type uint32;
      description
        "Number of AIPC output notifications received";
    }
    leaf rx-ipc-connect-notif {
      type uint32;
      description
        "Number of AIPC connect notifications received";
    }
    leaf rx-igmp-pak-success {
      type uint32;
      description
        "Number of IGMP protocol messages received";
    }
    leaf rx-add-mrouter-msg {
      type uint32;
      description
        "Number of IGMP Mrouter Add messages received";
    }
    leaf rx-delete-mrouter-msg {
      type uint32;
      description
        "Number of IGMP Mrouter Delete messages received";
    }
    leaf rx-sweep-mrouter-msg {
      type uint32;
      description
        "Number of IGMP Mrouter Sweep messages received";
    }
    leaf rx-unknown-mrouter-msg {
      type uint32;
      description
        "Number of IGMP Mrouter Unknown messages received";
    }
    leaf tx-buffer-errors {
      type uint32;
      description
        "Number of AIPC transmission errors";
    }
    leaf tx-buffers {
      type uint32;
      description
        "Number of AIPC buffers transmited";
    }
    leaf tx-protocol-buffers {
      type uint32;
      description
        "Number of IGMP protocol buffers transmitted";
    }
    leaf tx-unknown-buffers {
      type uint32;
      description
        "Number of IGMP Unknown buffers transmited";
    }
    leaf evpn-up-events {
      type uint32;
      description
        "Total number of time igmpsn connected to EVPN";
    }
    leaf evpn-down-events {
      type uint32;
      description
        "Total number of time igmpsn disconnected to EVPN";
    }
    leaf evpn-conn-status {
      type boolean;
      description
        "EVPN Connection Status";
    }
  }

  grouping SET-INT32 {
    description
      "Set int32 value union";
    leaf is-set {
      type Set-bool;
      description
        "IsSet";
    }
    leaf value {
      when "../is-set = '1'" {
        description
          "../IsSet = '1'";
      }
      type int32;
      description
        "Value";
    }
  }

  grouping IGMPSN-EDM-INTF-BAG {
    description
      "IGMP/MLD snooping port entry";
    container querier-address {
      description
        "Querier address";
      uses IGMPSN-ADDRTYPE;
    }
    container group-limit {
      description
        "Group limit";
      uses SET-INT32;
    }
    container packet-statistics {
      description
        "Port packet statistics";
      uses IGMPSN-PKT-STATS-BAG;
    }
    container evpn-statistics {
      description
        "EVPN statistics";
      uses IGMPSN-EVPN-STATS-BAG;
    }
    container common-statistics {
      description
        "Port common statistics";
      uses IGMPSN-COMMON-STATS-BAG;
    }
    container iccp-group-port-statistics {
      description
        "Port ICCP Group Port statistics";
      uses IGMPSN-ICCP-GROUP-PORT-STATS-BAG;
    }
    container iccp-traffic-statistics {
      description
        "Port ICCP traffic statistics";
      uses IGMPSN-ICCP-TRAFFIC-STATS-BAG;
    }
    container iccp-app-ig-port-statistics {
      description
        "Port ICCP App ICCP Group Port statistics";
      uses ICCP-APP-IG-PORT-STATS-BAG;
    }
    leaf interface-name {
      type string {
        length "0..321";
      }
      description
        "Port name";
    }
    leaf operational-state-up {
      type boolean;
      description
        "Operational state up";
    }
    leaf bridge-domain-name {
      type string {
        length "0..65";
      }
      description
        "Bridge domain name";
    }
    leaf stp-port {
      type boolean;
      description
        "STP port";
    }
    leaf stp-forwarding {
      type boolean;
      description
        "STP forwarding";
    }
    leaf pseudowire {
      type boolean;
      description
        "Pseudowire";
    }
    leaf group-id {
      type uint32;
      description
        "ICCP Group ID";
    }
    leaf iccp-port-redundancy-state {
      type Igmpsn-bag-iccp-app-redundancy-state;
      description
        "ICCP Group port redundancy state";
    }
    leaf ig-port-time-of-last-red-state-change {
      type uint32;
      description
        "ICCP Group Port time of last redundancy state
         change";
    }
    leaf profile-name {
      type string {
        length "0..33";
      }
      description
        "Profile name";
    }
    leaf immediate-leave {
      type boolean;
      description
        "Immediate leave";
    }
    leaf explicit-tracking {
      type boolean;
      description
        "Explicit tracking";
    }
    leaf static-mrouter {
      type boolean;
      description
        "Static mrouter";
    }
    leaf router-guard {
      type boolean;
      description
        "Router guard";
    }
    leaf mrouter-is-dynamic {
      type boolean;
      description
        "Mrouter is dynamic";
    }
    leaf is-querier-port {
      type boolean;
      description
        "Is querier port";
    }
    leaf mrouter-expires {
      type int32;
      description
        "Mrouter expires";
    }
    leaf number-of-port-groups {
      type uint32;
      description
        "Number of port groups";
    }
    leaf number-of-port-groups-static {
      type uint32;
      description
        "Number of static port groups";
    }
    leaf number-of-port-groups-dynamic {
      type uint32;
      description
        "Number of dynamic port groups";
    }
    leaf number-of-port-groups-source {
      type uint32;
      description
        "Number of dynamic port source groups";
    }
    leaf number-of-port-group-sources-static {
      type uint32;
      description
        "Number of static port source groups";
    }
    leaf number-of-port-group-sources-include {
      type uint32;
      description
        "Number of include port group sources";
    }
    leaf number-of-port-group-sources-exclude {
      type uint32;
      description
        "Number of exclude port group sources";
    }
    leaf admitted-weight {
      type uint32;
      description
        "Admitted weight";
    }
    leaf num-of-group-source-synced-to-evpn {
      type uint32;
      description
        "Number of port group source synced to EVPN";
    }
    leaf num-of-group-synced-to-evpn {
      type uint32;
      description
        "Number of port group synced to EVPN";
    }
    leaf is-evpn-enabled {
      type boolean;
      description
        "Is this a EVPN enabled interface";
    }
    leaf is-evpn-proxy-enabled {
      type boolean;
      description
        "Is this a EVPN Proxy  enabled interface";
    }
    list igmpsn-edm-moi-id {
      description
        "EVPN moi ID list";
      uses IGMPSN-EDM-MOI-ID-BAG;
    }
  }

  grouping IGMPSN-EDM-PROFILE-SUMMARY-BAG {
    description
      "IGMP/MLD snoop profile summary parameters";
    leaf profile-count {
      type uint32;
      description
        "Profile count";
    }
    leaf bridge-domain-count {
      type uint32;
      description
        "Bridge domain count";
    }
    leaf port-count {
      type uint32;
      description
        "Port count";
    }
  }

  grouping ICCP-APP-IG-PORT-STATS-BAG {
    description
      "ICCP Group port statistics";
    leaf port-active-rx {
      type uint32;
      description
        "ICCP Group Port Active events received";
    }
    leaf port-standby-rx {
      type uint32;
      description
        "ICCP Group Port Standby events received";
    }
    leaf port-down-rx {
      type uint32;
      description
        "ICCP Group Port Down events received";
    }
    leaf port-sync-req-rx {
      type uint32;
      description
        "Received ICCP Sync Requests";
    }
    leaf port-sync-req-rx-drop {
      type uint32;
      description
        "Received ICCP Sync Requests dropped";
    }
    leaf port-sync-req-tx {
      type uint32;
      description
        "Sent ICCP Sync Requests";
    }
    leaf port-sync-req-tx-drop {
      type uint32;
      description
        "Sent ICCP Sync Requests dropped";
    }
    leaf port-sync-rx {
      type uint32;
      description
        "Received ICCP Syncs";
    }
    leaf port-sync-rx-drop {
      type uint32;
      description
        "Received ICCP Syncs dropped";
    }
    leaf port-sync-invalid-rx {
      type uint32;
      description
        "Received ICCP Syncs invalid";
    }
    leaf port-sync-tx {
      type uint32;
      description
        "Sent ICCP Syncs";
    }
    leaf port-sync-tx-drop {
      type uint32;
      description
        "Sent ICCP Syncs dropped";
    }
    leaf port-app-state-rx {
      type uint32;
      description
        "Received ICCP App States";
    }
    leaf port-app-state-rx-drop {
      type uint32;
      description
        "Received ICCP App States dropped";
    }
    leaf port-app-state-tx {
      type uint32;
      description
        "Sent ICCP App States";
    }
    leaf port-app-state-tx-drop {
      type uint32;
      description
        "Sent ICCP App States dropped";
    }
    leaf port-start-retry-timer {
      type uint32;
      description
        "Retry timer started";
    }
  }

  grouping IGMPSN-ICCP-TRAFFIC-STATS-BAG {
    description
      "ICCP Traffic Statistics";
    leaf elapsed-time {
      type uint32;
      description
        "Running time for statistics";
    }
    leaf iccp-rx-buffer-parse-failures {
      type uint32;
      description
        "ICCP Rx buffer parse failures";
    }
    leaf iccp-get-tx-buffer-failures {
      type uint32;
      description
        "ICCP Get Tx buffer failures";
    }
    leaf iccp-tx-buffer-send-failures {
      type uint32;
      description
        "ICCP Tx buffer send failures";
    }
    leaf recvd-iccp-app-data-msgs {
      type uint32;
      description
        "Received ICCP App Data messages";
    }
    leaf recvd-iccp-app-data-naks {
      type uint32;
      description
        "Received ICCP App Data NAKs";
    }
    leaf recvd-iccp-app-data-tlvs {
      type uint32;
      description
        "Received ICCP App Data TLVs";
    }
    leaf recvd-iccp-app-state-tlvs {
      type uint32;
      description
        "Received ICCP App State TLVs";
    }
    leaf recvd-iccp-app-state-start-of-sync {
      type uint32;
      description
        "Received ICCP App State start of sync";
    }
    leaf recvd-iccp-app-state-end-of-sync {
      type uint32;
      description
        "Received ICCP App State end of sync";
    }
    leaf recvd-iccpig-request-sync-tlvs {
      type uint32;
      description
        "Received ICCP ICCP Group Request Sync TLVs";
    }
    leaf recvd-iccp-request-sync-tlvs {
      type uint32;
      description
        "Received ICCP Request Sync TLVs";
    }
    leaf recvd-iccp-port-membership-tlvs {
      type uint32;
      description
        "Received ICCP Port Membership TLVs";
    }
    leaf recvd-iccp-port-membership-adds {
      type uint32;
      description
        "Received ICCP Port Membership adds";
    }
    leaf recvd-iccp-port-membership-removes {
      type uint32;
      description
        "Received ICCP Port Membership removes";
    }
    leaf recvd-iccp-querier-info-tlvs {
      type uint32;
      description
        "Received ICCP Querier Info TLVs";
    }
    leaf recvd-iccp-querier-info-delete-tlvs {
      type uint32;
      description
        "Received ICCP Querier Info delete TLVs";
    }
    leaf recvd-iccp-dynamic-mrouter-tlvs {
      type uint32;
      description
        "Received ICCP Dynamic Mrouter TLVs";
    }
    leaf recvd-iccp-dynamic-mrouter-delete-tlvs {
      type uint32;
      description
        "Received ICCP Dynamic Mrouter delete TLVs";
    }
    leaf recvd-iccp-isolation-info-msgs {
      type uint32;
      description
        "Received ICCP Isolation Info messages";
    }
    leaf recvd-iccp-app-state-sync-ignored {
      type uint32;
      description
        "Received ICCP App State sync messages ignored";
    }
    leaf recvd-iccp-app-state-ignored {
      type uint32;
      description
        "Received ICCP App State messages ignored";
    }
    leaf recvd-iccp-app-data-unknown-ig {
      type uint32;
      description
        "Received ICCP App Data unknownICCP Group";
    }
    leaf recvd-iccp-app-data-unknown-ig-port {
      type uint32;
      description
        "Received ICCP App Data unknown ICCP Group port";
    }
    leaf recvd-iccp-app-data-wrong-ig {
      type uint32;
      description
        "Received ICCP App Data wrongICCP Group";
    }
    leaf recvd-iccp-app-data-bd-inactive {
      type uint32;
      description
        "Received ICCP App Data BD inactive";
    }
    leaf recvd-iccp-app-data-bd-port-inactive {
      type uint32;
      description
        "Received ICCP App Data BD port inactive";
    }
    leaf recvd-iccp-app-data-ig-port-not-standby {
      type uint32;
      description
        "Received ICCP App Data ICCP Group port not
         standby";
    }
    leaf recvd-iccp-app-data-ig-port-not-active {
      type uint32;
      description
        "Received ICCP App Data ICCP Group port not
         active";
    }
    leaf recvd-iccp-app-data-unsupported-ig-tlv-type {
      type uint32;
      description
        "Received ICCP App Data unsupported ICCP Group
         TLV type";
    }
    leaf recvd-iccp-app-data-truncated {
      type uint32;
      description
        "Received ICCP App Data truncated";
    }
    leaf recvd-iccp-app-data-length-error {
      type uint32;
      description
        "Received ICCP App Data length error";
    }
    leaf recvd-iccp-app-data-unsupported-tlv-type {
      type uint32;
      description
        "Received ICCP App Data unsupported TLV type";
    }
    leaf recvd-iccp-port-membership-no-querier {
      type uint32;
      description
        "Received ICCP Port Membership No Querier";
    }
    leaf recvd-iccp-port-membership-tlv-error {
      type uint32;
      description
        "Received ICCP Port Membership TLV error";
    }
    leaf recvd-iccp-port-membership-tlv-too-long {
      type uint32;
      description
        "Received ICCP Port Membership TLV too long";
    }
    leaf recvd-iccp-querier-info-tlv-error {
      type uint32;
      description
        "Received ICCP Querier Info TLV error";
    }
    leaf recvd-iccp-dynamic-mrouter-tlv-error {
      type uint32;
      description
        "Received ICCP Dynamic Mrouter TLV error";
    }
    leaf recvd-iccp-isolation-info-unknown-rg {
      type uint32;
      description
        "Received ICCP Isolation Info unknown Redundancy
         Group";
    }
    leaf iccp-tx-buffer-send-count {
      type uint32;
      description
        "ICCP Tx buffer send count";
    }
    leaf iccp-app-state-replay-attempts {
      type uint32;
      description
        "ICCP App State replay attempts";
    }
    leaf sent-iccp-group-connect-tlvs {
      type uint32;
      description
        "Sent ICCP Group Connect TLVs";
    }
    leaf sent-iccp-group-disconnect-tlvs {
      type uint32;
      description
        "Sent ICCP Group Disconnect TLVs";
    }
    leaf sent-iccp-request-sync-tlvs {
      type uint32;
      description
        "Sent ICCP Request Sync TLVs";
    }
    leaf sent-iccp-port-membership-tlvs {
      type uint32;
      description
        "Sent ICCP Port Membership TLVs";
    }
    leaf sent-iccp-port-membership-adds {
      type uint32;
      description
        "Sent ICCP Port Membership adds";
    }
    leaf sent-iccp-port-membership-removes {
      type uint32;
      description
        "Sent ICCP Port Membership removes";
    }
    leaf sent-iccp-querier-info-tlvs {
      type uint32;
      description
        "Sent ICCP Querier Info TLVs";
    }
    leaf sent-iccp-querier-info-delete-tlvs {
      type uint32;
      description
        "Sent ICCP Querier Info delete TLVs";
    }
    leaf sent-iccp-dynamic-mrouter-tlvs {
      type uint32;
      description
        "Sent ICCP Dynamic Mrouter TLVs";
    }
    leaf sent-iccp-dynamic-mrouter-delete-tlvs {
      type uint32;
      description
        "Sent ICCP Dynamic Mrouter delete TLVs";
    }
    leaf sent-iccp-app-state-refused {
      type uint32;
      description
        "Request to send ICCP App State refused";
    }
    leaf iccp-app-state-replay-failures {
      type uint32;
      description
        "ICCP App State replay failures";
    }
    leaf iccp-request-sync-tlvs-tx-failures {
      type uint32;
      description
        "ICCP Request Sync TLV Tx failures";
    }
    leaf iccp-port-membership-tlvs-tx-failures {
      type uint32;
      description
        "ICCP Port Membership TLV Tx failures";
    }
    leaf iccp-querier-info-tlvs-tx-failures {
      type uint32;
      description
        "ICCP Querier Info TLV Tx failures";
    }
    leaf iccp-querier-info-delete-tx-failures {
      type uint32;
      description
        "ICCP Querier Info delete TLV Tx failures";
    }
    leaf iccp-dynamic-mrouter-tlvs-tx-failures {
      type uint32;
      description
        "ICCP Dynamic Mrouter TLV Tx failures";
    }
    leaf iccp-dynamic-mrouter-delete-tlvs-tx-failures {
      type uint32;
      description
        "ICCP Dynamic Mrouter delete TLV Tx failures";
    }
  }

  grouping IGMPSN-ICCP-GROUP-PORT-STATS-BAG {
    description
      "igmp snooping Redundancy Group Port Statistics";
    leaf elapsed-time {
      type uint32;
      description
        "Running time for statistics";
    }
    leaf iccp-group-port-create-down-events {
      type uint32;
      description
        "ICCP Group Port Create Down events";
    }
    leaf iccp-group-port-create-standby-events {
      type uint32;
      description
        "ICCP Group Port Create Standby events";
    }
    leaf iccp-group-port-create-active-events {
      type uint32;
      description
        "ICCP Group Port Create Active events";
    }
    leaf iccp-group-port-down-events {
      type uint32;
      description
        "ICCP Group Port Down events";
    }
    leaf iccp-group-port-standby-events {
      type uint32;
      description
        "ICCP Group Port Standby events";
    }
    leaf iccp-group-port-active-events {
      type uint32;
      description
        "ICCPGroup Port Active events";
    }
  }

  grouping IGMPSN-ICCP-STATS-BAG {
    description
      "igmp snooping Redundancy Statistics";
    leaf elapsed-time {
      type uint32;
      description
        "Running time for statistics";
    }
    leaf iccp-up-events {
      type uint32;
      description
        "ICCP Up events";
    }
    leaf iccp-down-events {
      type uint32;
      description
        "ICCP Down events";
    }
    leaf iccp-congestion-detected-events {
      type uint32;
      description
        "ICCP Congestion Detected events";
    }
    leaf iccp-congestion-cleared-events {
      type uint32;
      description
        "ICCP Congestion Cleared events";
    }
    leaf iccp-group-peer-up-events {
      type uint32;
      description
        "ICCP Group Peer Up events";
    }
    leaf iccp-group-peer-down-events {
      type uint32;
      description
        "ICCP Group Peer Down events";
    }
    leaf iccp-group-connect-attempts {
      type uint32;
      description
        "ICCP Group Connect attempts";
    }
    leaf iccp-group-connect-failures {
      type uint32;
      description
        "ICCP Group Connect failures";
    }
    leaf iccp-group-disconnect-attempts {
      type uint32;
      description
        "ICCP Group Disconnect attempts";
    }
    leaf iccp-group-disconnect-failures {
      type uint32;
      description
        "ICCP Group Disconnect failures";
    }
  }

  grouping IGMPSN-COMMON-STATS-BAG {
    description
      "IGMPSN COMMON STATS BAG";
    leaf elapsed-time {
      type uint32;
      description
        "Running time for statistics";
    }
    leaf stale-port-groups-deleted {
      type uint32;
      description
        "Stale port groups deleted";
    }
    leaf stale-port-group-sources-deleted {
      type uint32;
      description
        "Stale port group sources deleted";
    }
  }

  grouping IGMPSN-EVPN-STATS-BAG {
    description
      "IGMPSN EVPN STATS BAG";
    leaf evpn-reset-time {
      type uint32;
      description
        "EVPN reset time";
    }
    leaf evpn-up-events {
      type uint32;
      description
        "EVPN up events";
    }
    leaf evpn-down-events {
      type uint32;
      description
        "EVPN down events";
    }
    leaf evpn-message-received {
      type uint32;
      description
        "EVPN message received";
    }
    leaf evpn-type7-add-received {
      type uint32;
      description
        "Number of Join add received";
    }
    leaf evpn-type7-withdraw-received {
      type uint32;
      description
        "Number of join withdraw received";
    }
    leaf evpn-type8-add-received {
      type uint32;
      description
        "Number of Leave add received";
    }
    leaf evpn-type8-withdraw-received {
      type uint32;
      description
        "Number of Leave withdraw received";
    }
    leaf evpn-message-received-ignored {
      type uint32;
      description
        "EVPN message received and ignored";
    }
    leaf evpn-message-received-unsupported {
      type uint32;
      description
        "EVPN unsupported message received";
    }
    leaf evpn-message-sent {
      type uint32;
      description
        "EVPN message sent";
    }
    leaf evpn-type7-add-sent {
      type uint32;
      description
        "Number of Join add sent";
    }
    leaf evpn-type7-with-sent {
      type uint32;
      description
        "Number of join withdraw sent";
    }
    leaf evpn-type8-add-sent {
      type uint32;
      description
        "Number of Leave add sent";
    }
    leaf evpn-type8-withdraw-sent {
      type uint32;
      description
        "Number of Leave withdraw sent";
    }
    leaf current-evpn-remove-queue {
      type uint32;
      description
        "EVPN Current Retry queue size";
    }
    leaf cumulative-evpn-remove-queue {
      type uint32;
      description
        "EVPN Cumulative Retry queue size";
    }
    leaf evpn-replay-time {
      type uint32;
      description
        "EVPN replay time";
    }
  }

  grouping IGMPSN-PKT-STATS-BAG {
    description
      "IGMPSN PKT STATS BAG";
    leaf elapsed-time {
      type uint32;
      description
        "Running time for statistics";
    }
    leaf received-igmp-general-queries {
      type uint32;
      description
        "Received IGMP/MLD general queries";
    }
    leaf received-igmp-group-specific-queries {
      type uint32;
      description
        "Received IGMP/MLD group specific queriers";
    }
    leaf received-igmp-group-source-specific-querier {
      type uint32;
      description
        "Received IGMP group source specific queriers";
    }
    leaf received-igmpv1-reports {
      type uint32;
      description
        "Received IGMP V1/MLD reports";
    }
    leaf received-igmpv2-reports {
      type uint32;
      description
        "Received IGMP V2/MLD V1 reports";
    }
    leaf received-igmpv3-reports {
      type uint32;
      description
        "Received IGMP V3/MLD V2 reports";
    }
    leaf received-evpn-igmpv1-reports {
      type uint32;
      description
        "Received EVPN IGMP V1/MLD reports";
    }
    leaf received-evpn-igmpv2-reports {
      type uint32;
      description
        "Received EVPN IGMP V2/MLD V1 reports";
    }
    leaf received-evpn-igmpv3-reports {
      type uint32;
      description
        "Received EVPN IGMP V3/MLD V2 reports";
    }
    leaf received-evpn-proxy-v2-reports {
      type uint32;
      description
        "Received EVPN Proxy V3/MLD V2 reports";
    }
    leaf received-evpn-proxy-v3-reports {
      type uint32;
      description
        "Received EVPN Proxy V3/MLD V2 reports";
    }
    leaf received-evpn-proxy-del-v2-reports {
      type uint32;
      description
        "Received EVPN Proxy Del V3/MLD V2 reports";
    }
    leaf received-evpn-proxy-del-v3-reports {
      type uint32;
      description
        "Received EVPN Proxy Del V3/MLD V2 reports";
    }
    leaf received-igmpv2-leaves {
      type uint32;
      description
        "Received IGMP V2/MLD V1 leaves";
    }
    leaf received-evpn-igmpv2-leaves {
      type uint32;
      description
        "Received EVPN IGMP V2/MLD V1 leaves";
    }
    leaf received-igmp-global-leaves {
      type uint32;
      description
        "Received IGMP/MLD global leaves";
    }
    leaf received-pim-hellos {
      type uint32;
      description
        "Received PIM hellos";
    }
    leaf received-igmpv3-is-include-group-records {
      type uint32;
      description
        "Received IGMP V3/MLD V2 is include group Records";
    }
    leaf received-igmpv3-change-to-include-group-records {
      type uint32;
      description
        "Received IGMP V3/MLD V2 Change to include group
         records";
    }
    leaf received-igmpv3-is-exclude-group-records {
      type uint32;
      description
        "Received IGMP V3/MLD V2 is exclude group records";
    }
    leaf received-igmpv3-change-to-exclude-group-records {
      type uint32;
      description
        "Received IGMP V3/MLD V2 change to exclude group
         records";
    }
    leaf received-igmpv3-allow-new-sources-group-records {
      type uint32;
      description
        "Received IGMP V3/MLD V2 allow new sources group
         records";
    }
    leaf received-igmpv3-block-old-sources-group-records {
      type uint32;
      description
        "Received IGMP V3/MLD V2 block old sources group
         records";
    }
    leaf received-evpn-igmpv3-is-include-group-records {
      type uint32;
      description
        "Received IGMP V3/MLD V2 is include group Records";
    }
    leaf received-evpn-igmpv3-change-to-include-group-records {
      type uint32;
      description
        "Received IGMP V3/MLD V2 Change to include group
         records";
    }
    leaf received-evpn-igmpv3-is-exclude-group-records {
      type uint32;
      description
        "Received IGMP V3/MLD V2 is exclude group records";
    }
    leaf received-evpn-igmpv3-change-to-exclude-group-records {
      type uint32;
      description
        "Received IGMP V3/MLD V2 change to exclude group
         records";
    }
    leaf received-evpn-igmpv3-allow-new-sources-group-records {
      type uint32;
      description
        "Received IGMP V3/MLD V2 allow new sources group
         records";
    }
    leaf received-evpn-igmpv3-block-old-sources-group-records {
      type uint32;
      description
        "Received IGMP V3/MLD V2 block old sources group
         records";
    }
    leaf sent-igmp-general-queries {
      type uint32;
      description
        "Sent IGMP/MLD general queriers";
    }
    leaf sent-igmp-group-specific-queries {
      type uint32;
      description
        "Sent IGMP/MLD group specific queries";
    }
    leaf sent-igmp-group-source-specific-queries {
      type uint32;
      description
        "Sent IGMP/MLD group source specific queries";
    }
    leaf sent-igmpv2-reports {
      type uint32;
      description
        "Sent IGMP V2/MLD V1 reports";
    }
    leaf sent-igmpv2-leaves {
      type uint32;
      description
        "Sent IGMP V2/MLD V1 leaves";
    }
    leaf sent-igmpv3-reports {
      type uint32;
      description
        "Sent IGMP V3/MLD V2 reports";
    }
    leaf sent-igmp-global-leaves {
      type uint32;
      description
        "Sent IGMP/MLD global leaves";
    }
    leaf received-igmp-general-queries-flooded {
      type uint32;
      description
        "Received IGMP/MLD general queries flooded";
    }
    leaf received-igmp-group-specific-queries-flooded {
      type uint32;
      description
        "Received IGMP/MLD group specific queries flooded";
    }
    leaf received-igmp-group-source-specific-queries-flooded {
      type uint32;
      description
        "Received IGMP/MLD group source specific queries
         flooded";
    }
    leaf received-igmpv2-reports-forwarded-to-mrouters {
      type uint32;
      description
        "Received IGMP V2/MLD V1 reports forwarded to
         mrouters";
    }
    leaf received-igmpv2-reports-flooded {
      type uint32;
      description
        "Received IGMP V2/MLD V1 reports flooded";
    }
    leaf received-igmpv3-reports-forwarded-to-mrouters {
      type uint32;
      description
        "Received IGMP V3/MLD V2 reports forwarded to
         mrouters";
    }
    leaf received-igmpv3-reports-flooded {
      type uint32;
      description
        "Received IGMP V3/MLD V2 reports flooded";
    }
    leaf received-igmpv2-leaves-forwarded-to-mrouters {
      type uint32;
      description
        "Received IGMP V2/MLD V1 leaves forwarded to
         mrouters";
    }
    leaf received-igmpv2-leaves-flooded {
      type uint32;
      description
        "Received IGMP V2/MLD V1 leavs flooded";
    }
    leaf received-pim-hellos-flooded {
      type uint32;
      description
        "Received PIM hellos flooded";
    }
    leaf received-packets-flooded {
      type uint32;
      description
        "Received packets flooded";
    }
    leaf received-packets-forwarded-to-members {
      type uint32;
      description
        "Received packets forwarded to members";
    }
    leaf received-packets-forwarded-to-mrouters {
      type uint32;
      description
        "Received packets forwarded to mrouters";
    }
    leaf received-packets-consumed {
      type uint32;
      description
        "Received packets consumed";
    }
    leaf reports-suppressed {
      type uint32;
      description
        "Received packets suppressed";
    }
    leaf blocks-ignored-inv2-compat-mode {
      type uint32;
      description
        "Blocks ignored in IGMP V2/MLD V1 compatibility
         mode";
    }
    leaf exclude-source-lists-ignored-inv2-compat-mode {
      type uint32;
      description
        "Exclude src lists ignored in IGMP V2/MLD V1
         compatibility mode";
    }
    leaf access-group-permits {
      type uint32;
      description
        "Access group permits";
    }
    leaf access-group-denials {
      type uint32;
      description
        "Access group denials";
    }
    leaf group-limit-exceeds {
      type uint32;
      description
        "Group limits exceeds";
    }
    leaf received-ip-packets-on-inactive-bridge-domain {
      type uint32;
      description
        "Received IP packets on inactive bridge domain";
    }
    leaf received-ip-packets-on-inactive-port {
      type uint32;
      description
        "Received IP packets on inactive port";
    }
    leaf received-ip-packets-martiain {
      type uint32;
      description
        "Received IP packets martian";
    }
    leaf received-ip-packets-bad-protocol {
      type uint32;
      description
        "Received IP packets bad protocol";
    }
    leaf received-ip-packets-da-not-multicast {
      type uint32;
      description
        "Received IP packets DA not multicast";
    }
    leaf received-ip-packets-no-rrt-alert {
      type uint32;
      description
        "Received IP packets no router alert";
    }
    leaf received-ip-packets-no-router-alert-check {
      type uint32;
      description
        "Received IP packets no router alert check";
    }
    leaf received-ip-packets-bad-igmp-checksum {
      type uint32;
      description
        "Received IP packets bad IGMP checksum";
    }
    leaf received-ip-packets-ttl-not-one {
      type uint32;
      description
        "Received IP packets TTL not one";
    }
    leaf received-ip-packets-ttl-not-one-check {
      type uint32;
      description
        "Received IP packets TTL not one check";
    }
    leaf received-igmp-queries-too-short {
      type uint32;
      description
        "Received IGMP/MLD queries too short";
    }
    leaf received-igmp-group-source-specific-queries-too-short {
      type uint32;
      description
        "Received IGMP/MLD V3 GSS queries too short";
    }
    leaf received-igmpv1-reports-too-short {
      type uint32;
      description
        "Received IGMP V1/MLD reports too short";
    }
    leaf received-igmpv2-reports-too-short {
      type uint32;
      description
        "Received IGMP V2/MLD V1 reports too short";
    }
    leaf received-igmpv3-reports-too-short {
      type uint32;
      description
        "Received IGMP V3/MLD V2 reports too short";
    }
    leaf received-igmpv2-leaves-too-short {
      type uint32;
      description
        "Received IGMP V2/MLD V1 leaves too short";
    }
    leaf received-igmp-msgs-unknown-type {
      type uint32;
      description
        "Received IGMP/MLD messages unknown type";
    }
    leaf received-igmp-msgs-greater-than-maximum-version {
      type uint32;
      description
        "Received IGMP/MLD messages greater than maximum
         version";
    }
    leaf received-igmp-msgs-less-than-minimum-version {
      type uint32;
      description
        "Received IGMP/MLD messages less than minimum
         version";
    }
    leaf received-igmp-queries-bad-source {
      type uint32;
      description
        "Received IGMP/MLD queries bad source";
    }
    leaf received-igmp-queries-dropped-by-router {
      type uint32;
      description
        "Received IGMP/MLD queries fropped by router";
    }
    leaf received-igmp-general-queries-da-no-all-nodes {
      type uint32;
      description
        "Received IGMP/MLD general queries DA not all
         node";
    }
    leaf received-igmp-group-specific-queries-invalid-group {
      type uint32;
      description
        "Received IGMP/MLD group specific queries invalid
         group";
    }
    leaf received-igmp-group-specific-queries-da-not-group {
      type uint32;
      description
        "Received IGMP/MLD group specific queries DA not
         group";
    }
    leaf received-igmp-group-specific-queries-not-from-querier {
      type uint32;
      description
        "Received IGMP/MLD group specific queries not
         from querier";
    }
    leaf received-igmp-group-specific-queries-unknown-group {
      type uint32;
      description
        "Received IGMP/MLD group specific queries unknown
         group";
    }
    leaf received-igmp-reports-invalid-group {
      type uint32;
      description
        "Received IGMP/MLD reports invalid group";
    }
    leaf received-igmp-reports-link-local-group {
      type uint32;
      description
        "Received IGMP/MLD reports link local group";
    }
    leaf received-igmp-reports-da-not-group {
      type uint32;
      description
        "Received IGMP/MLD reports da not group";
    }
    leaf received-igmp-reports-no-querier {
      type uint32;
      description
        "Received IGMP/MLD reports no querier";
    }
    leaf received-igmp-leaves-invalid-group {
      type uint32;
      description
        "Received IGMP/MLD leaves invalid group";
    }
    leaf received-igmp-leaves-invalid-da {
      type uint32;
      description
        "Received IGMP/MLD leaves invalid DA";
    }
    leaf received-igmp-leaves-no-querier {
      type uint32;
      description
        "Received IGMP/MLD leaves no querier";
    }
    leaf received-igmp-leaves-non-member {
      type uint32;
      description
        "Received IGMP/MLD leaves non member";
    }
    leaf received-igmp-leaves-non-dynamic-member {
      type uint32;
      description
        "Received IGMP/MLD leaves non-dynamic member";
    }
    leaf received-igmp-leaves-nonv2-member {
      type uint32;
      description
        "Received IGMP/MLD leaves non V2/V1 member";
    }
    leaf received-igmpv3-reports-invalid-group {
      type uint32;
      description
        "Received IGMP V3/MLD V2 reports invalid group";
    }
    leaf received-igmpv3-reports-link-local-group {
      type uint32;
      description
        "Received IGMP V3/MLD V2 reports link local group";
    }
    leaf received-igmpv3-reports-da-not-all-v3-routers {
      type uint32;
      description
        "Received IGMP V3/MLD V2 reports DA not all V3
         routers";
    }
    leaf received-igmpv3-reports-no-querier {
      type uint32;
      description
        "Received IGMP V3/MLD V2 reports no querier";
    }
    leaf received-igmpv3-reports-older-version-querier {
      type uint32;
      description
        "Received IGMP V3/MLD V2 reports older version
         querier";
    }
    leaf received-igmpv3-reports-invalid-group-record-type {
      type uint32;
      description
        "Received IGMP V3/MLD V2 reports invalid group
         record type";
    }
    leaf received-igmpv3-reports-no-sources {
      type uint32;
      description
        "Received IGMP V3/MLD V2 reports no sources";
    }
    leaf received-igmpv3-leaves-non-member {
      type uint32;
      description
        "Received IGMP V3/MLD V2 leaves non member";
    }
    leaf received-pim-msgs-dropped-by-router-guard {
      type uint32;
      description
        "Received PIM messages dropped by router guard";
    }
    leaf received-igmp-msgs-p2mp-bud-tail-dropped {
      type uint32;
      description
        "Received IGMP messages in P2MP Bud and Tail node
         dropped";
    }
    leaf received-igmp-queries-on-multihome-port {
      type uint32;
      description
        "Received IGMP Queries on Multihomed Port";
    }
    leaf received-igmpv1-reports-on-multihome-port {
      type uint32;
      description
        "Received IGMP V1 Report on Multihomed Port";
    }
    leaf received-igmp-proxy-general-queries {
      type uint32;
      description
        "Received IGMP/MLD proxy general queries";
    }
    leaf received-igmp-proxy-gs-queries {
      type uint32;
      description
        "Received IGMP/MLD proxy group specific queries";
    }
    leaf received-igmp-proxy-reports {
      type uint32;
      description
        "Received IGMP/MLD proxy reports";
    }
    leaf sources-not-reported {
      type uint32;
      description
        "Sources not reported";
    }
    leaf tx-error-no-querier-in-bd {
      type uint32;
      description
        "Msg generation failed, no Querier in BD";
    }
    leaf tx-error-no-l2-info-for-bd {
      type uint32;
      description
        "Msg generation failed, no L2 Info for BD";
    }
  }

  grouping IGMPSN-EDM-INTERNAL-QUERIER-STATS-BAG {
    description
      "IGMPSN EDM INTERNAL QUERIER STATS BAG";
    leaf elapsed-time {
      type uint32;
      description
        "Running time for statistics";
    }
    leaf received-general-queries {
      type uint32;
      description
        "Received general queries";
    }
    leaf received-general-queries-when-disabled {
      type uint32;
      description
        "Received general queries when disabled";
    }
    leaf received-general-queries-as-queries {
      type uint32;
      description
        "Received general queries as querier";
    }
    leaf received-general-queries-as-non-querier {
      type uint32;
      description
        "Received general queries as non querier";
    }
    leaf received-general-queries-as-winnder {
      type uint32;
      description
        "Received general queries as winner";
    }
    leaf received-general-queries-as-loser {
      type uint32;
      description
        "Received general queries as loser";
    }
    leaf received-global-leaves {
      type uint32;
      description
        "Received global leaves";
    }
    leaf received-global-leaves-when-disabled {
      type uint32;
      description
        "Received global leaves when disabled";
    }
    leaf received-global-leaves-as-non-querier {
      type uint32;
      description
        "Received global leaves as non querier";
    }
    leaf received-global-leaves-ignored {
      type uint32;
      description
        "Received global leaves ignored";
    }
    leaf received-pim-enabled-notifications {
      type uint32;
      description
        "Received PIM enabled notifications";
    }
    leaf received-pim-disabled-notifications {
      type uint32;
      description
        "Received PIM disabled notifications";
    }
    leaf receivedy-local-query-solicitations {
      type uint32;
      description
        "Received local query solicitations";
    }
    leaf sent-general-queries {
      type uint32;
      description
        "SentGeneralQueries";
    }
  }

  grouping IGMPSN-EDM-MRTR-BAG {
    description
      "IGMPSN EDM MRTR BAG";
    leaf static-m-router {
      type boolean;
      description
        "Static mrouter";
    }
    leaf dynamic-m-router {
      type boolean;
      description
        "Dynamic mrouter";
    }
    leaf interface-name {
      type string {
        length "0..321";
      }
      description
        "Port name";
    }
    leaf pseudowire {
      type boolean;
      description
        "Pseudowire";
    }
  }

  grouping IGMPSN-EDM-BD-BAG {
    description
      "IGMP/MLD snooping bridge domain summary info";
    container configured-system-ip-address {
      description
        "Configured system IP address";
      uses IGMPSN-ADDRTYPE;
    }
    container querier-address {
      description
        "Querier address";
      uses IGMPSN-ADDRTYPE;
    }
    container internal-querier-stats {
      description
        "Internal querier statistics";
      uses IGMPSN-EDM-INTERNAL-QUERIER-STATS-BAG;
    }
    container packet-statistics {
      description
        "Bridge domain packet statistics";
      uses IGMPSN-PKT-STATS-BAG;
    }
    container evpn-statistics {
      description
        "EVPN statistics";
      uses IGMPSN-EVPN-STATS-BAG;
    }
    container common-statistics {
      description
        "Bridge domain common statistics";
      uses IGMPSN-COMMON-STATS-BAG;
    }
    container iccp-statistics {
      description
        "Bridge domain ICCP statistics";
      uses IGMPSN-ICCP-STATS-BAG;
    }
    container iccp-group-port-statistics {
      description
        "Bridge domain ICCP Group Port statistics";
      uses IGMPSN-ICCP-GROUP-PORT-STATS-BAG;
    }
    container iccp-traffic-statistics {
      description
        "Bridge domain ICCP traffic statistics";
      uses IGMPSN-ICCP-TRAFFIC-STATS-BAG;
    }
    container iccp-app-ig-port-statistics {
      description
        "Bridge domain ICCP App ICCP Group Port
         statistics";
      uses ICCP-APP-IG-PORT-STATS-BAG;
    }
    container client-address {
      description
        "Client address";
      uses IGMPSN-ADDRTYPE;
    }
    leaf bridge-domain-name {
      type string {
        length "0..65";
      }
      description
        "Bridge domain name";
    }
    leaf profile-name {
      type string {
        length "0..33";
      }
      description
        "Profile name";
    }
    leaf snoop-active {
      type boolean;
      description
        "Snooping active in bridge domain";
    }
    leaf number-of-ports {
      type uint32;
      description
        "Number of ports in bridge domain";
    }
    leaf number-of-mrouters {
      type uint32;
      description
        "Number of mrouters in bridge domain";
    }
    leaf number-of-stp-ports {
      type uint32;
      description
        "Number of STP ports in bridge domain";
    }
    leaf number-of-ig-ports {
      type uint32;
      description
        "Number of ICCP Group ports in bridge domain";
    }
    leaf number-of-groups {
      type uint32;
      description
        "Number of groups in bridge domain";
    }
    leaf number-of-group-o-ports {
      type uint32;
      description
        "Number of group o ports in bridge domain";
    }
    leaf number-of-group-sources {
      type uint32;
      description
        "Number of group sources in bridge domain";
    }
    leaf number-of-group-source-statics {
      type uint32;
      description
        "Number of statics group sources";
    }
    leaf number-of-group-source-includes {
      type uint32;
      description
        "Number of include group sources";
    }
    leaf number-of-group-source-excludes {
      type uint32;
      description
        "Number of exclude group sources";
    }
    leaf number-of-group-source-include-ports {
      type uint32;
      description
        "Number of include group source ports";
    }
    leaf number-of-group-source-exclude-ports {
      type uint32;
      description
        "Number of exclude group source ports";
    }
    leaf configured-report-suppression {
      type boolean;
      description
        "Configured TCN query suppression";
    }
    leaf configured-tcn-query-solicit {
      type boolean;
      description
        "Configured TCN query solicit";
    }
    leaf configured-tcn-flood {
      type boolean;
      description
        "Configured TCN flood";
    }
    leaf configured-router-alert-check {
      type boolean;
      description
        "Configured router alert check";
    }
    leaf configured-ttl-check {
      type boolean;
      description
        "Configured TTL check";
    }
    leaf offload-enabled {
      type boolean;
      description
        "nV Multicast Offload enabled";
    }
    leaf evpn-proxy-enabled {
      type boolean;
      description
        "EVPN Selective Multicast enabled";
    }
    leaf configured-mrouter-forwarding {
      type boolean;
      description
        "Configured Mrouter Forwarding";
    }
    leaf configured-igmp-snooping-disabled {
      type boolean;
      description
        "Configured IGMPSnooping status";
    }
    leaf configured-p2mp-capability {
      type boolean;
      description
        "Configured P2MP Capability";
    }
    leaf configured-default-profile {
      type boolean;
      description
        "Configured Default IGMPSnooping Profile";
    }
    leaf configured-internal-querier-supprt {
      type boolean;
      description
        "Configured internal querier support";
    }
    leaf configured-internal-querier-version {
      type uint8;
      description
        "Configured internal querier version";
    }
    leaf configured-internal-querier-query-timeout {
      type uint32;
      units "second";
      description
        "Configured internal querier timeout (secs)";
    }
    leaf configured-internal-querier-query-interval {
      type uint16;
      units "second";
      description
        "Configured internal querier interval (secs)";
    }
    leaf configured-internal-querier-max-response-time {
      type uint8;
      units "second";
      description
        "Configured internal querier max response time
         (1/10 secs)";
    }
    leaf configured-internal-querier-robust-variable {
      type uint8;
      description
        "Configured internal querier robust variable";
    }
    leaf configured-internal-querier-tcn-query-interval {
      type uint16;
      units "second";
      description
        "Configured internal querier TCN query interval
         (secs)";
    }
    leaf configured-internal-querier-tcn-query-count {
      type uint8;
      description
        "Configured internal querier TCN query count";
    }
    leaf configured-internal-querier-tcn-query-mrt {
      type uint8;
      units "second";
      description
        "Configured internal querier TCN query MRT 1/10
         secs)";
    }
    leaf configured-querier-query-interval {
      type uint16;
      units "second";
      description
        "Configured querier query interval (secs)";
    }
    leaf configured-querier-lmq-interval {
      type uint16;
      units "second";
      description
        "Configured querier LMQ interval (1/10 secs)";
    }
    leaf configured-querier-lmq-count {
      type uint8;
      description
        "Configured querier LMQ count";
    }
    leaf configured-querier-robust-variable {
      type uint8;
      description
        "Configured querier robustness variable";
    }
    leaf configured-tcn-flood-query-count {
      type uint8;
      description
        "Configured TCN flood query count";
    }
    leaf configured-minimum-version {
      type uint8;
      description
        "Configured minimum version";
    }
    leaf configured-maximum-version {
      type uint8;
      description
        "Configured maximum version";
    }
    leaf configured-unsolicated-report-interval {
      type uint8;
      units "second";
      description
        "Configured unsolicated report interval (1/10
         secs)";
    }
    leaf querier-port-name {
      type string {
        length "0..321";
      }
      description
        "Querier port name";
    }
    leaf querier-port-pseudowire {
      type boolean;
      description
        "Querier port psweudowire";
    }
    leaf querier-version {
      type uint8;
      description
        "Querier version";
    }
    leaf querier-query-interval {
      type uint16;
      description
        "Querier query interval";
    }
    leaf querier-robust-variable {
      type uint8;
      description
        "Querier robust variable";
    }
    leaf querier-max-response-time {
      type uint16;
      description
        "Querier max response time";
    }
    leaf querier-time-since-last-g-query {
      type int32;
      description
        "Querier time since last general query";
    }
    leaf topology-change-flood-mode {
      type boolean;
      description
        "Topology change flood mode";
    }
    leaf gqs-since-topology-change-start {
      type uint8;
      description
        "GQS since topology change start";
    }
    leaf ig-report-standby-state-disabled {
      type boolean;
      description
        "ICCP Group report standby state disabled";
    }
    leaf startup-query-port-up-disabled {
      type boolean;
      description
        "Startup query on port-up disabled";
    }
    leaf startup-query-ig-port-active {
      type boolean;
      description
        "Startup query on ICCP Group port active";
    }
    leaf startup-query-tcn {
      type boolean;
      description
        "Startup query on TCN";
    }
    leaf startup-query-tcn-sync {
      type boolean;
      description
        "Startup query TCN sync";
    }
    leaf startup-query-tcn-always {
      type boolean;
      description
        "Startup query TCN always";
    }
    leaf startup-query-process-start {
      type boolean;
      description
        "Startup query on process start";
    }
    leaf startup-query-process-start-sync {
      type boolean;
      description
        "Startup query process start sync";
    }
    leaf startup-query-interval {
      type uint16;
      units "second";
      description
        "Startup query interval (secs)";
    }
    leaf startup-query-count {
      type uint8;
      description
        "Startup query count";
    }
    leaf startup-query-mrt {
      type uint8;
      description
        "Startup query MRT (1/10 sec)";
    }
    leaf internal-querier-present {
      type boolean;
      description
        "Internal querier present";
    }
    leaf star-star-mroute-pd-data {
      type yang:hex-string;
      description
        "Star star mroute platform dependent opaque data";
    }
    leaf client-port-name {
      type string {
        length "0..321";
      }
      description
        "Client port name";
    }
    leaf client-port-pseudowire {
      type boolean;
      description
        "Client port pseudowire";
    }
    leaf client-l2-info {
      type yang:hex-string;
      description
        "Client l2 info";
    }
    leaf client-packet-priority {
      type uint32;
      description
        "Client packet priority";
    }
    leaf querier-l2-info {
      type yang:hex-string;
      description
        "Querier l2 info";
    }
    leaf querier-packet-priority {
      type uint32;
      description
        "Querier packet priority";
    }
    leaf platform-out-of-resources {
      type boolean;
      description
        "Platform Out Of Resources";
    }
    leaf star-star-oor-fail-cnt {
      type uint32;
      description
        "Star Star Mroute OOR Fail Count";
    }
    leaf star-goor-fail-cnt {
      type uint32;
      description
        "StarG Mroute OOR Fail Count";
    }
    leaf sgoor-fail-cnt {
      type uint32;
      description
        "SG Mroute OOR Fail Count";
    }
    list mrouter {
      description
        "Maximum and current groups accepted for each
         interface";
      uses IGMPSN-EDM-MRTR-BAG;
    }
  }

  grouping IGMPSN-PROFILE-STATIC-GROUP-SOURCE-BAG {
    description
      "IGMPSN PROFILE STATIC GROUP SOURCE BAG";
    container source-address {
      description
        "Source address";
      uses IGMPSN-ADDRTYPE;
    }
  }

  grouping IGMPSN-PROFILE-STATIC-GROUP-BAG {
    description
      "IGMPSN PROFILE STATIC GROUP BAG";
    container group-address {
      description
        "Group address";
      uses IGMPSN-ADDRTYPE;
    }
    leaf star-g {
      type boolean;
      description
        "Star G flag";
    }
    list source {
      description
        "Source list";
      uses IGMPSN-PROFILE-STATIC-GROUP-SOURCE-BAG;
    }
  }

  grouping IGMPSN-PROFILE-PARAM-FLAGS-BAG {
    description
      "IGMPSN PROFILE PARAM FLAGS BAG";
    leaf system-ip-address-set {
      type boolean;
      description
        "System IP address set";
    }
    leaf minimum-version-set {
      type boolean;
      description
        "Minimum version set";
    }
    leaf report-suppression-set {
      type boolean;
      description
        "Report suppression set";
    }
    leaf tcn-query-solicit-set {
      type boolean;
      description
        "TCN query solicit set";
    }
    leaf tcn-flood-set {
      type boolean;
      description
        "TCN flood set";
    }
    leaf tcn-flood-query-count-set {
      type boolean;
      description
        "TCN flood query count set";
    }
    leaf router-alert-check-set {
      type boolean;
      description
        "Router alert check set";
    }
    leaf ttl-check-set {
      type boolean;
      description
        "TTL check set";
    }
    leaf mrouter-forwarding-set {
      type boolean;
      description
        "Mrouter Forwarding set";
    }
    leaf internal-querier-support-set {
      type boolean;
      description
        "Internal querier support set";
    }
    leaf internal-querier-version-set {
      type boolean;
      description
        "Internal querier version set";
    }
    leaf internal-querier-query-timeout-set {
      type boolean;
      description
        "Internal querier timeout set";
    }
    leaf internal-querier-query-interval-set {
      type boolean;
      description
        "Internal querier quer interval set";
    }
    leaf internal-querier-max-response-time-set {
      type boolean;
      description
        "Internal querier maximum response time set";
    }
    leaf internal-querier-robust-variable-set {
      type boolean;
      description
        "Internal querier robustness variable set";
    }
    leaf internal-querier-tcn-query-count-set {
      type boolean;
      description
        "Internal querier TCN query count set";
    }
    leaf internal-querier-tcn-query-interval-set {
      type boolean;
      description
        "Internal querier TCN query interval set";
    }
    leaf internal-querier-tcn-query-mrt-set {
      type boolean;
      description
        "Internal querier TCN query MRT set";
    }
    leaf querier-query-interval-set {
      type boolean;
      description
        "Querier query interval set";
    }
    leaf querier-robust-variable-set {
      type boolean;
      description
        "Querier robust variable set";
    }
    leaf querier-lmq-interval-set {
      type boolean;
      description
        "Querier LMQ interval set";
    }
    leaf querier-lmq-count-set {
      type boolean;
      description
        "Querier LMQ count set";
    }
    leaf unsolicited-report-interval-set {
      type boolean;
      description
        "Unsolicitated report interval set";
    }
    leaf immediate-leave-set {
      type boolean;
      description
        "Immediate leave set";
    }
    leaf explicit-tracking-set {
      type boolean;
      description
        "Explicit tracking set";
    }
    leaf static-mrouter-set {
      type boolean;
      description
        "Static mrouter set";
    }
    leaf router-guard-set {
      type boolean;
      description
        "Router guard set";
    }
    leaf access-group-set {
      type boolean;
      description
        "Access group set";
    }
    leaf group-policy-set {
      type boolean;
      description
        "Group policy set";
    }
    leaf group-limit-set {
      type boolean;
      description
        "Group limit set";
    }
    leaf ig-report-standby-state-set {
      type boolean;
      description
        "ICCP Group report standby state set";
    }
    leaf startup-query-count-set {
      type boolean;
      description
        "Startup query count set";
    }
    leaf startup-query-interval-set {
      type boolean;
      description
        "Startup query interval set";
    }
    leaf startup-query-mrt-set {
      type boolean;
      description
        "Startup query MRT set";
    }
    leaf startup-query-port-up-set {
      type boolean;
      description
        "Startup query on port-up set";
    }
    leaf startup-query-ig-port-active-set {
      type boolean;
      description
        "Startup query on ICCP Group port active set";
    }
    leaf startup-query-tcn-set {
      type boolean;
      description
        "Startup query on TCN set";
    }
    leaf startup-query-tcn-sync-set {
      type boolean;
      description
        "Startup query TCN sync set";
    }
    leaf startup-query-tcn-always-set {
      type boolean;
      description
        "Startup query TCN always set";
    }
    leaf startup-query-process-start-set {
      type boolean;
      description
        "Startup query on process start set";
    }
    leaf startup-query-process-start-sync-set {
      type boolean;
      description
        "Startup query process start sync set";
    }
    leaf default-profile-set {
      type boolean;
      description
        "Default profile set";
    }
  }

  grouping IGMPSN-EDM-PROFILE-BAG {
    description
      "IGMP/MLD snoop profile parameters";
    container set-flags {
      description
        "Set flags";
      uses IGMPSN-PROFILE-PARAM-FLAGS-BAG;
    }
    container system-ip-addr {
      description
        "System ip addr";
      uses IGMPSN-ADDRTYPE;
    }
    leaf name {
      type string {
        length "0..33";
      }
      description
        "Profile name";
    }
    leaf is-configured {
      type boolean;
      description
        "Profile is configured";
    }
    leaf minimum-version {
      type uint8;
      description
        "Minimum version";
    }
    leaf report-suppression {
      type boolean;
      description
        "Report suppression";
    }
    leaf tcn-query-solicit {
      type boolean;
      description
        "TCN query solicit";
    }
    leaf tcn-flood {
      type boolean;
      description
        "TCN flood";
    }
    leaf tcn-flood-query-count {
      type uint8;
      description
        "TCN flood query count";
    }
    leaf router-alert-check {
      type boolean;
      description
        "Router alert check";
    }
    leaf ttl-check {
      type boolean;
      description
        "TTL check";
    }
    leaf mrouter-forwarding {
      type boolean;
      description
        "Mrouter Forwarding";
    }
    leaf internal-querier-support {
      type boolean;
      description
        "Internal querier support";
    }
    leaf internal-querier-version {
      type uint8;
      description
        "Internal querier version";
    }
    leaf internal-querier-query-timeout {
      type uint32;
      units "second";
      description
        "Internal querier query timeout (secs)";
    }
    leaf internal-querier-query-interval {
      type uint16;
      units "second";
      description
        "Internal querier query interval (secs)";
    }
    leaf internal-querier-max-response-time {
      type uint8;
      description
        "Internal querier max response time (1/10 sec)";
    }
    leaf internal-querier-robust-variable {
      type uint8;
      description
        "Internal querier robust variable";
    }
    leaf internal-querier-tcn-query-interval {
      type uint16;
      units "second";
      description
        "Internal querier TCN query interval (secs)";
    }
    leaf internal-querier-tcn-query-count {
      type uint8;
      description
        "Internal querier TCN query count";
    }
    leaf internal-querier-tcn-query-mrt {
      type uint8;
      description
        "Internal querier TCN query MRT (1/10 sec)";
    }
    leaf querier-query-interval {
      type uint16;
      units "second";
      description
        "Querier query interval (secs)";
    }
    leaf querier-max-response-time {
      type uint16;
      units "second";
      description
        "Querier max response time (1/10 secs)";
    }
    leaf querier-lmq-interval {
      type uint8;
      units "second";
      description
        "Querier LMQ interval (1/10 secs)";
    }
    leaf querier-lmq-count {
      type uint8;
      description
        "Querier LMQ count";
    }
    leaf querier-robust-variable {
      type uint8;
      description
        "Querier robust variable";
    }
    leaf unsolicited-report-interval {
      type uint8;
      units "second";
      description
        "Unsolicited report interval(1/10 secs)";
    }
    leaf immediate-leave {
      type boolean;
      description
        "Immediate leave";
    }
    leaf explicit-tracking {
      type boolean;
      description
        "Explicit tracking";
    }
    leaf static-mrouter {
      type boolean;
      description
        "Static mrouter";
    }
    leaf router-guard {
      type boolean;
      description
        "Router guard";
    }
    leaf access-group-acl-name {
      type string {
        length "0..33";
      }
      description
        "Access group ACL name";
    }
    leaf access-group-acl-configured {
      type boolean;
      description
        "Access group ACL configured";
    }
    leaf group-policy-name {
      type string {
        length "0..257";
      }
      description
        "Group policy name";
    }
    leaf group-limit {
      type int32;
      description
        "Group limit";
    }
    leaf threshold-limit {
      type int32;
      description
        "Threshold limit";
    }
    leaf ig-report-standby-state {
      type boolean;
      description
        "ICCP Group report standby state";
    }
    leaf startup-query-interval {
      type uint16;
      units "second";
      description
        "Startup query interval (secs)";
    }
    leaf startup-query-count {
      type uint8;
      description
        "Startup query count";
    }
    leaf startup-query-mrt {
      type uint8;
      description
        "Startup query MRT (1/10 sec)";
    }
    leaf startup-query-port-up {
      type boolean;
      description
        "Startup query on port-up";
    }
    leaf startup-query-ig-port-active {
      type boolean;
      description
        "Startup query on ICCP Group port active";
    }
    leaf startup-query-tcn {
      type boolean;
      description
        "Startup query on TCN";
    }
    leaf startup-query-tcn-sync {
      type boolean;
      description
        "Startup query TCN sync";
    }
    leaf startup-query-tcn-always {
      type boolean;
      description
        "Startup query TCN always";
    }
    leaf startup-query-process-start {
      type boolean;
      description
        "Startup query on process start";
    }
    leaf startup-query-process-start-sync {
      type boolean;
      description
        "Startup query process start sync";
    }
    leaf bridge-domain-count {
      type uint32;
      description
        "Bridge domain count";
    }
    leaf port-count {
      type uint32;
      description
        "Port count";
    }
    leaf default-profile {
      type boolean;
      description
        "Default Profile Enable";
    }
    list static-group {
      description
        "Static group list";
      uses IGMPSN-PROFILE-STATIC-GROUP-BAG;
    }
  }

  grouping ICCP-APP-ICCP-STATS-BAG {
    description
      "ICCP Application Statistics";
    leaf received-up-events {
      type uint32;
      description
        "ICCP Up events received";
    }
    leaf received-down-events {
      type uint32;
      description
        "ICCP Down events received";
    }
    leaf received-congestion-clear-events {
      type uint32;
      description
        "ICCP Congestion Clear events received";
    }
    leaf congestion-clear-drop-events {
      type uint32;
      description
        "ICCP Congestion Clear events dropped";
    }
    leaf received-congestion-detected-events {
      type uint32;
      description
        "ICCP Congestion Detected events received";
    }
    leaf congestion-detected-drop-events {
      type uint32;
      description
        "ICCP Congestion Detected events dropped";
    }
    leaf sent-failure-events {
      type uint32;
      description
        "ICCP Tx Failure";
    }
  }

  grouping IGMPSN-ICCP-APP-STATS-BAG {
    description
      "ICCP Application Statistics";
    container port-statistics-per-iccp {
      description
        "Port stats per ICCP";
      uses IGMPSN-ICCP-APP-RG-PORT-STATS-ST;
    }
    container group-statistics-per-iccp {
      description
        "ICCP Group stats per ICCP";
      uses ICCP-APP-ICCP-GROUP-STATS-BAG;
    }
    container iccp-app-statistics {
      description
        "ICCP stats";
      uses ICCP-APP-ICCP-STATS-BAG;
    }
    leaf is-initialized {
      type boolean;
      description
        "ICCP Init state";
    }
  }

  grouping IGMPSN-ICCP-APP-RG-PORT-STATS-BAG {
    description
      "ICCP Redundancy Group Port Statistics";
    container port-statistics {
      description
        "ICCP Group Port stats";
      uses IGMPSN-ICCP-APP-RG-PORT-STATS-ST;
    }
    leaf is-initialized {
      type boolean;
      description
        "ICCP Init state";
    }
    leaf group-id {
      type uint32;
      description
        "ICCP Group ID";
    }
  }

  grouping IGMPSN-ICCP-APP-RG-PEER-DATA-BAG {
    description
      "igmp snooping Redundancy Group Peer data";
    leaf peer-timestamp {
      type uint32;
      units "second";
      description
        "Peer timestamp  (realtime in seconds)";
    }
  }

  grouping ICCP-APP-ICCP-STATE-BAG {
    description
      "ICCP Application State";
    leaf is-initialized {
      type boolean;
      description
        "ICCP Init state";
    }
    leaf congestion-detected {
      type boolean;
      description
        "ICCP Congestion Detected";
    }
    leaf is-up {
      type boolean;
      description
        "ICCP up/down status";
    }
    leaf iccp-create-time {
      type uint32;
      units "second";
      description
        "ICCP Creation timestamp (realtime in seconds)";
    }
    leaf redundancy-groups {
      type uint32;
      description
        "ICCP Redundancy Group Count";
    }
    leaf redundancy-timestamp {
      type uint32;
      units "second";
      description
        "ICCP Redundancy Group table timestamp (realtime
         in seconds)";
    }
  }

  grouping IGMPSN-ICCP-APP-RG-DATA-BAG {
    description
      "ICCP Redundancy Group Data";
    leaf is-initialized {
      type boolean;
      description
        "ICCP Init state";
    }
    leaf group-id-xr {
      type uint32;
      description
        "ICCP Group Id";
    }
    leaf peers {
      type uint32;
      description
        "ICCP Group Peer Count";
    }
    leaf group-state {
      type Igmpsn-iccp-app-rg-state;
      description
        "ICCP Group state";
    }
    leaf old-group-state {
      type Igmpsn-iccp-app-rg-state;
      description
        "Old ICCP Group state";
    }
    leaf number-of-ports {
      type uint32;
      description
        "Redundancy Group Port Count";
    }
    leaf standby-ports {
      type uint32;
      description
        "ICCP Group Standby Interface Count";
    }
    leaf active-ports {
      type uint32;
      description
        "ICCP Group Active Interface Count";
    }
    leaf down-ports {
      type uint32;
      description
        "ICCP Group Down Interface Count";
    }
    leaf create-time {
      type uint32;
      units "second";
      description
        "ICCP Group Creation time (realtime in seconds)";
    }
  }

  grouping ICCP-APP-ICCP-GROUP-STATS-BAG {
    description
      "ICCP Group Statistics";
    leaf received-peer-up-events {
      type uint32;
      description
        "ICCP Group Peer Up events received";
    }
    leaf received-peer-down-events {
      type uint32;
      description
        "ICCP Group Peer Down events received";
    }
    leaf received-sync-events {
      type uint32;
      description
        "ICCP Group Sync Request events received";
    }
    leaf connect-transmit-events {
      type uint32;
      description
        "ICCP Group Connect transmit events";
    }
    leaf connect-transmit-failure-events {
      type uint32;
      description
        "ICCP Group Connect transmit failure events";
    }
    leaf disconnect-transmit-events {
      type uint32;
      description
        "ICCP Group Disconnect transmit events";
    }
    leaf disconnect-transmit-failure-events {
      type uint32;
      description
        "ICCP Group Disconnect transmit failure events";
    }
    leaf start-retry-timer-events {
      type uint32;
      description
        "ICCP Group Start Retry Timer events";
    }
  }

  grouping IGMPSN-ICCP-APP-RG-PORT-STATS-ST {
    description
      "ICCP Group Port Statistics";
    leaf active-rx {
      type uint32;
      description
        "ICCP Interface Active events received";
    }
    leaf standby-rx {
      type uint32;
      description
        "ICCP Interface Standby events received";
    }
    leaf down-rx {
      type uint32;
      description
        "ICCP Interface Down events received";
    }
    leaf sync-req-rx {
      type uint32;
      description
        "ICCP Interface Sync Request events received";
    }
    leaf sync-req-rx-drop {
      type uint32;
      description
        "ICCP Interface Sync Request events received and
         dropped";
    }
    leaf sync-req-tx {
      type uint32;
      description
        "ICCP Interface Sync Request transmit events";
    }
    leaf sync-req-tx-drop {
      type uint32;
      description
        "ICCP Interface Sync Request trasnmit events
         dropped";
    }
    leaf sync-rx {
      type uint32;
      description
        "ICCP Interface Sync events received";
    }
    leaf sync-rx-drop {
      type uint32;
      description
        "ICCP Interface Sync events received and dropped";
    }
    leaf sync-start-rx {
      type uint32;
      description
        "ICCP Interface Sync Start events received";
    }
    leaf sync-start-rx-drop {
      type uint32;
      description
        "ICCP Interface Sync Start events received and
         dropped";
    }
    leaf sync-end-rx {
      type uint32;
      description
        "ICCP Interface Sync End events received";
    }
    leaf sync-end-rx-drop {
      type uint32;
      description
        "ICCP Interface Sync End events received and
         dropped";
    }
    leaf sync-unsolicited-rx {
      type uint32;
      description
        "ICCP Interface Sync Unsolicited events received";
    }
    leaf sync-end-unsolicited-rx-drop {
      type uint32;
      description
        "ICCP Interface Sync End Unsolicited events
         received and dropped";
    }
    leaf sync-invalid-rx {
      type uint32;
      description
        "ICCP Interface Sync Invalid event received";
    }
    leaf sync-tx {
      type uint32;
      description
        "ICCP Interface Sync transmit events";
    }
    leaf sync-tx-drop {
      type uint32;
      description
        "ICCP Interface Sync transmit events dropped";
    }
    leaf app-state-rx {
      type uint32;
      description
        "ICCP Interface App State events received";
    }
    leaf app-state-rx-drop {
      type uint32;
      description
        "ICCP Interface App State events received and
         dropped";
    }
    leaf app-state-tx {
      type uint32;
      description
        "ICCP Interface App State transmit events";
    }
    leaf app-state-tx-drop {
      type uint32;
      description
        "ICCP Interface App State transmit events dropped";
    }
    leaf start-retry-timer {
      type uint32;
      description
        "ICCP Interface Start Retry Timer events";
    }
  }

  grouping IGMPSN-ICCP-APP-RG-STATS-BAG {
    description
      "ICCP Redundancy Group Statistics";
    container port-statistics {
      description
        "ICCP Group Port stats";
      uses IGMPSN-ICCP-APP-RG-PORT-STATS-ST;
    }
    container group-statistics {
      description
        "ICCP Group stats";
      uses ICCP-APP-ICCP-GROUP-STATS-BAG;
    }
    leaf is-initialized {
      type boolean;
      description
        "ICCP Init state";
    }
    leaf group-id-xr {
      type uint32;
      description
        "ICCP Group Id";
    }
  }

  grouping IGMPSN-ICCP-APP-RG-PORT-DATA-BAG {
    description
      "ICCP Redundancy Group Port Data";
    leaf is-initialized {
      type boolean;
      description
        "ICCP Init state";
    }
    leaf group-id {
      type uint32;
      description
        "ICCP Group Id";
    }
    leaf redundancy-state {
      type Igmpsn-bag-iccp-app-redundancy-state;
      description
        "ICCP Group Port Redundancy state";
    }
    leaf port-state {
      type Igmpsn-iccp-app-rg-port-state;
      description
        "ICCP Group Port state";
    }
    leaf old-port-state {
      type Igmpsn-iccp-app-rg-port-state;
      description
        "Old ICCP Group Port state";
    }
    leaf creation-time {
      type uint32;
      units "second";
      description
        "ICCP Group Port creation timestamp (realtime in
         seconds)";
    }
    leaf redundancy-state-timestamp {
      type uint32;
      units "second";
      description
        "Port Redundancy state timestamp (realtime in
         seconds)";
    }
    leaf sync-timestamp {
      type uint32;
      units "second";
      description
        "Sync timstamp (realtime in seconds)";
    }
    leaf request-id {
      type uint16;
      description
        "Request Id";
    }
    leaf static-m-router {
      type boolean;
      description
        "Static mrouter";
    }
    leaf dynamic-m-router {
      type boolean;
      description
        "Dynamic mrouter";
    }
    leaf number-of-port-groups {
      type uint32;
      description
        "Number of port groups";
    }
    leaf number-of-port-groups-source {
      type uint32;
      description
        "Number of dynamic port source groups";
    }
    leaf is-querier-port {
      type boolean;
      description
        "Is querier port";
    }
  }

  grouping IGMPSN-EDM-GROUP-SOURCE-PORT-BAG {
    description
      "IGMPSN EDM GROUP SOURCE PORT BAG";
    container expires {
      description
        "Source expires in seconds";
      uses RUNNING-TIMER;
    }
    leaf interface-name {
      type string {
        length "0..321";
      }
      description
        "Port name";
    }
    leaf uptime {
      type uint64;
      units "second";
      description
        "Uptime in seconds";
    }
    leaf pseudowire {
      type boolean;
      description
        "Pseudwire";
    }
    leaf port-exclude {
      type boolean;
      description
        "Port exclude";
    }
    leaf static-oport {
      type boolean;
      description
        "Static o-port";
    }
    leaf dynamic-oport {
      type boolean;
      description
        "Dynamic o-port";
    }
    leaf evpn-remote-oport {
      type boolean;
      description
        "BGP learnt o-port";
    }
    leaf explicit-tracking-enabled {
      type boolean;
      description
        "Is explicit tracking enabled";
    }
    leaf group-id {
      type uint32;
      description
        "ICCP Group ID";
    }
    leaf iccp-port-redundancy-state {
      type Igmpsn-bag-iccp-app-redundancy-state;
      description
        "ICCP Group port redundancy state";
    }
    list igmpsn-edm-moi-id {
      description
        "EVPN moi ID list";
      uses IGMPSN-EDM-MOI-ID-BAG;
    }
  }

  grouping IGMPSN-EDM-GROUP-SOURCE-BAG {
    description
      "IGMPSN EDM GROUP SOURCE BAG";
    container source {
      description
        "Source";
      uses IGMPSN-ADDRTYPE;
    }
    leaf uptime {
      type uint64;
      units "second";
      description
        "Uptime in seconds";
    }
    leaf include-port-count {
      type int32;
      description
        "Include port count";
    }
    leaf exclude-port-count {
      type int32;
      description
        "Exclude port count";
    }
    leaf static-port-count {
      type int32;
      description
        "static port count";
    }
    leaf sg-mroute-pd-data {
      type yang:hex-string;
      description
        "SG mroute platform dependent opaque data";
    }
    list include-port {
      description
        "Include port list";
      uses IGMPSN-EDM-GROUP-SOURCE-PORT-BAG;
    }
    list exclude-port {
      description
        "Exclude port list";
      uses IGMPSN-EDM-GROUP-SOURCE-PORT-BAG;
    }
  }

  grouping IGMPSN-EDM-MOI-ID-BAG {
    description
      "IGMPSN EDM MOI ID BAG";
    leaf moi-id {
      type uint32;
      description
        "EVPN peer moi_id";
    }
    leaf label {
      type uint32;
      description
        "Label assigned to EVPN peer";
    }
  }

  grouping RUNNING-TIMER {
    description
      "Running Timer union";
    leaf timer-running {
      type Set-bool;
      description
        "TimerRunning";
    }
    leaf value {
      when "../timer-running = '1'" {
        description
          "../TimerRunning = '1'";
      }
      type int32;
      description
        "Value";
    }
  }

  grouping IGMPSN-EDM-GROUP-O-PORT-BAG {
    description
      "IGMPSN EDM GROUP O PORT BAG";
    container expires {
      description
        "Group expires in seconds";
      uses RUNNING-TIMER;
    }
    leaf interface-name {
      type string {
        length "0..321";
      }
      description
        "Port name";
    }
    leaf version {
      type uint8;
      description
        "Version";
    }
    leaf uptime {
      type uint64;
      units "second";
      description
        "Uptime in seconds";
    }
    leaf pseudowire {
      type boolean;
      description
        "Pseudowire";
    }
    leaf static-oport {
      type boolean;
      description
        "Static o-port";
    }
    leaf dynamic-oport {
      type boolean;
      description
        "Dynamic o-port";
    }
    leaf evpn-remote-oport {
      type boolean;
      description
        "BGP learnt o-port";
    }
    leaf explicit-tracking-enabled {
      type boolean;
      description
        "Is explicit tracking enabled";
    }
    leaf group-id {
      type uint32;
      description
        "ICCP Group ID";
    }
    leaf iccp-port-redundancy-state {
      type Igmpsn-bag-iccp-app-redundancy-state;
      description
        "ICCP Group port redundancy state";
    }
    list igmpsn-edm-moi-id {
      description
        "EVPN moi ID list";
      uses IGMPSN-EDM-MOI-ID-BAG;
    }
  }

  grouping IGMPSN-ADDRTYPE {
    description
      "IGMPSN ADDRTYPE";
    leaf af-name {
      type Igmpsn-afi;
      description
        "AFName";
    }
    leaf ipv4-address {
      when "../af-name = 'ipv4-unicast'" {
        description
          "../AFName = 'IPv4Unicast'";
      }
      type inet:ipv4-address;
      description
        "IPv4 Addr";
    }
    leaf ipv6-address {
      when "../af-name = 'ipv6-unicast'" {
        description
          "../AFName = 'IPv6Unicast'";
      }
      type Ipv6-address;
      description
        "IPV6 Addr";
    }
  }

  grouping IGMPSN-EDM-GROUP-BAG {
    description
      "IGMPSN EDM GROUP BAG";
    container group-address-xr {
      description
        "Group address";
      uses IGMPSN-ADDRTYPE;
    }
    leaf bridge-domain-name {
      type string {
        length "0..65";
      }
      description
        "Bridge domain name";
    }
    leaf version {
      type uint8;
      description
        "Version";
    }
    leaf uptime {
      type uint64;
      units "second";
      description
        "Uptime in seconds";
    }
    leaf group-exclude {
      type boolean;
      description
        "Group exclude";
    }
    leaf oport-count {
      type int32;
      description
        "O port count";
    }
    leaf source-count {
      type int32;
      description
        "Source count";
    }
    leaf include-source-count {
      type int32;
      description
        "Include source count";
    }
    leaf exclude-source-count {
      type int32;
      description
        "Exclude source count";
    }
    leaf static-source-count {
      type int32;
      description
        "Static source count";
    }
    leaf star-g-mroute-pd-data {
      type yang:hex-string;
      description
        "StarG mroute platform dependent opaque data";
    }
    leaf platform-data {
      type string {
        length "0..128";
      }
      description
        "Platform Data ";
    }
    list oport {
      description
        "O-port list";
      uses IGMPSN-EDM-GROUP-O-PORT-BAG;
    }
    list source {
      description
        "Source list";
      uses IGMPSN-EDM-GROUP-SOURCE-BAG;
    }
  }

  grouping IGMPSN-PORT-NAME-BAG {
    description
      "IGMPSN PORT NAME BAG";
    leaf name {
      type string {
        length "0..321";
      }
      description
        "Port name";
    }
    leaf pseudowire {
      type boolean;
      description
        "Pseudowire";
    }
  }

  grouping IGMPSN-BD-NAME-BAG {
    description
      "IGMPSN BD NAME BAG";
    leaf name {
      type string {
        length "0..65";
      }
      description
        "Bridge domain name";
    }
  }

  grouping IGMPSN-EDM-PROFILE-REFERENCE-BAG {
    description
      "IGMP/MLD snoop profile reference";
    leaf profile-name-xr {
      type string {
        length "0..33";
      }
      description
        "Profile name";
    }
    list bridge-domain-name {
      description
        "Bridge domain name list";
      uses IGMPSN-BD-NAME-BAG;
    }
    list port-name {
      description
        "Port name list";
      uses IGMPSN-PORT-NAME-BAG;
    }
  }
}
