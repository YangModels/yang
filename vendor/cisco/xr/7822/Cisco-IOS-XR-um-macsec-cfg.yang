module Cisco-IOS-XR-um-macsec-cfg {
  namespace "http://cisco.com/ns/yang/Cisco-IOS-XR-um-macsec-cfg";
  prefix um-macsec-cfg;

  import Cisco-IOS-XR-types {
    prefix xr;
  }
  import Cisco-IOS-XR-um-interface-cfg {
    prefix a1;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR macsec package configuration.
     
     This YANG module augments the
     modules with configuration data.
     
     Copyright (c) 2020-2022 by Cisco Systems, Inc.
     All rights reserved.";

  revision 2022-07-11 {
    description
      "Added missing description statement to nodes
       2022-06-01
         Adjusted controller augmentation hierarchy";
    semver:module-version "1.1.0";
  }
  revision 2021-01-05 {
    description
      "Initial release";
    semver:module-version "1.0.0";
  }

  grouping IF-BODY {
    description
      "Grouping for interface";
    container macsec {
      description
        "Enable MACSec for the interface";
      container psk-keychain {
        description
          "Configure MACsec Key Agreement(MKA) PSK Keychain";
        leaf keychain-name {
          type xr:Cisco-ios-xr-string {
            length "1..32" {
              description
                "Name of keychain to be used to get keys, maximum length 32";
            }
          }
          description
            "Name of keychain to be used to get keys, maximum length 32";
        }
        leaf fallback-psk-keychain {
          type xr:Cisco-ios-xr-string {
            length "1..32" {
              description
                "Name of keychain to be used to get fallback PSK keys, maximum length 32";
            }
          }
          description
            "Configure MKA fallback PSK Keychain";
        }
        leaf policy {
          type xr:Cisco-ios-xr-string {
            length "1..16" {
              description
                "MACsec Policy name, maximum length 16";
            }
          }
          description
            "Enter the policy name, maximum length 16";
        }
      }
    }
    container eap {
      presence "Indicates a eap node is configured.";
      description
        "Configure MACsec Key Agreement(MKA) to use EAP";
      leaf policy {
        type xr:Cisco-ios-xr-string {
          length "1..16" {
            description
              "Policy name";
          }
        }
        description
          "Enter the policy name";
      }
    }
    container macsec-service {
      description
        "Enable MACSec as a service";
      leaf decrypt-port {
        type xr:Interface-name {
          pattern "GigabitEthernet*";
        }
        must "../psk-keychain";
        description
          "Enter the sub-interface name for MacSec decryption";
      }
      leaf psk-keychain {
        type xr:Cisco-ios-xr-string {
          length "1..32" {
            description
              "Name of key-chain to be used to get keys";
          }
        }
        must "../decrypt-port";
        description
          "Configure MACsec Key Agreement(MKA) PSK Keychain";
      }
      leaf policy {
        type xr:Cisco-ios-xr-string {
          length "1..16" {
            description
              "Policy name";
          }
        }
        must "../decrypt-port";
        description
          "Enter the policy name";
      }
    }
  }

  grouping CONT-BODY {
    description
      "Grouping for controller";
    container macsec {
      description
        "Enable MACSec for the interface";
      container psk-keychain {
        description
          "Configure MACsec Key Agreement(MKA) PSK Keychain";
        leaf keychain-name {
          type xr:Cisco-ios-xr-string {
            length "1..32" {
              description
                "Name of keychain to be used to get keys, maximum length 32";
            }
          }
          description
            "Name of keychain to be used to get keys, maximum length 32";
        }
        leaf fallback-psk-keychain {
          type xr:Cisco-ios-xr-string {
            length "1..32" {
              description
                "Name of keychain to be used to get fallback PSK keys, maximum length 32";
            }
          }
          description
            "Configure MKA fallback PSK Keychain";
        }
        leaf policy {
          type xr:Cisco-ios-xr-string {
            length "1..16" {
              description
                "MACsec Policy name, maximum length 16";
            }
          }
          description
            "Enter the policy name, maximum length 16";
        }
      }
    }
    container eap {
      presence "Indicates a eap node is configured.";
      description
        "Configure MACsec Key Agreement(MKA) to use EAP";
      leaf policy {
        type xr:Cisco-ios-xr-string {
          length "1..16" {
            description
              "Policy name";
          }
        }
        description
          "Enter the policy name";
      }
    }
  }

  augment "/a1:interfaces/a1:interface" {
    description
      "This augment extends active nodes configuration";
    uses IF-BODY;
  }
  augment "/a1:interfaces/a1:interface-preconfigure" {
    description
      "This augment extends preconfigured nodes
       configuration";
    uses IF-BODY;
  }
  augment "/a1:controllers/a1:controller" {
    description
      "This augment extends active nodes configuration";
    uses CONT-BODY;
  }
  augment "/a1:controllers/a1:controller-preconfigure" {
    description
      "This augment extends preconfigured nodes
       configuration";
    uses CONT-BODY;
  }
  container macsec-policy {
    description
      "MACSec Policy configuration";
    container policy-names {
      description
        "Enter the policy name of max-length 16";
      list policy-name {
        key "policy-name";
        description
          "Enter the policy name of max-length 16";
        leaf policy-name {
          type xr:Cisco-ios-xr-string {
            length "1..16" {
              description
                "Enter the policy name of max-length 16";
            }
          }
          description
            "Enter the policy name of max-length 16";
        }
        leaf key-server-priority {
          type uint32 {
            range "0..255" {
              description
                "Enter the key server priority for the node";
            }
          }
          description
            "Key Server Priority for the node";
        }
        leaf cipher-suite {
          type enumeration {
            enum "GCM-AES-128" {
              value 1;
              description
                "GCM AES 128 bit encryption";
            }
            enum "GCM-AES-256" {
              value 2;
              description
                "GCM AES 256 bit encryption";
            }
            enum "GCM-AES-XPN-128" {
              value 3;
              description
                "GCM AES XPN 128 bit encryption";
            }
            enum "GCM-AES-XPN-256" {
              value 4;
              description
                "GCM AES XPN 256 bit encryption";
            }
          }
          description
            "Cipher-Suite used for encryption";
        }
        leaf window-size {
          type uint32 {
            range "0..1024" {
              description
                "Enter the window size";
            }
          }
          description
            "window-size used for encryption";
        }
        leaf conf-offset {
          type enumeration {
            enum "CONF-OFFSET-0" {
              value 0;
              description
                "Offset 0";
            }
            enum "CONF-OFFSET-30" {
              value 30;
              description
                "Offset 30";
            }
            enum "CONF-OFFSET-50" {
              value 50;
              description
                "Offset 50";
            }
          }
          description
            "conf-offset used for encryption";
        }
        leaf security-policy {
          type enumeration {
            enum "should-secure" {
              value 0;
              description
                "Enable should secure";
            }
            enum "must-secure" {
              value 1;
              description
                "Enable must secure";
            }
          }
          description
            "Must Secure/Should Secure for Data encryption";
        }
        leaf vlan-tags-in-clear {
          type uint32 {
            range "1..2" {
              description
                "Enter the value";
            }
          }
          description
            "Specify the number of vlan-tags in clear (1 or 2)";
        }
        leaf policy-exception {
          type enumeration {
            enum "lacp-in-clear" {
              value 1;
              description
                "DEPRECATED-Allow LACP(Link aggregation control plane protocol) Packets in clear Text, recommended to use 'allow lacp-in-clear'";
            }
          }
          description
            "macsec policy exception to allow packets in clear text";
        }
        leaf sak-rekey-interval {
          type uint32 {
            range "1..43200" {
              description
                "DEPRECATED-Interval(in minutes)<1-43200>, Default: OFF, recommended to use 'seconds' option";
            }
          }
          description
            "Interval after which key-server generates new SAK for a Secured Session";
        }
        leaf seconds {
          type uint32 {
            range "60..2592000" {
              description
                "Enter SAK rekey interval(in seconds) ";
            }
          }
          description
            "Interval(in seconds)<60-2592000>, Default: OFF";
        }
        container include-icv-indicator {
          presence "Indicates a include-icv-indicator node is configured.";
          description
            "Include ICV Indicator paramset in MKPDU";
        }
        container delay-protection {
          presence "Indicates a delay-protection node is configured.";
          description
            "enable data delay protection";
        }
        container use-eapol-pae-in-icv {
          presence "Indicates a use-eapol-pae-in-icv node is configured.";
          description
            "enable use eapol pae address in icv";
        }
        container suspend-on-request {
          description
            "disable suspend-on-request from peers in issu";
          container disable {
            presence "Indicates a disable node is configured.";
            description
              "disable suspend-on-request from peers in issu";
          }
        }
        container suspend-for {
          description
            "disable MKA suspension when in issu";
          container disable {
            presence "Indicates a disable node is configured.";
            description
              "disable MKA suspension when in issu";
          }
        }
        container enable-legacy-fallback {
          presence "Indicates a enable-legacy-fallback node is configured.";
          description
            "enable keepalive fallback ca";
        }
        container enable-legacy-sak-write {
          presence "Indicates a enable-legacy-sak-write node is configured.";
          description
            "To interop with legacy ncs5500 coherent systems";
        }
        container allow {
          description
            "macsec policy exceptions to allow in clear-text";
          container lacp-in-clear {
            presence "Indicates a lacp-in-clear node is configured.";
            description
              "Allow LACP((Link aggregation control plane protocol) Packets in clear Text";
          }
          container pause-frame-in-clear {
            presence "Indicates a pause-frame-in-clear node is configured.";
            description
              "Allow pause-frame packets in clear text";
          }
        }
        container ppk {
          presence "Indicates a ppk node is configured.";
          description
            "To use PPK supported MACsec session";
          leaf sks-profile {
            type xr:Cisco-ios-xr-string {
              length "1..253" {
                description
                  "Name of sks profile name to be used";
              }
            }
            description
              "use sks profile for PPK generation";
          }
        }
      }
    }
  }
  container macsec {
    description
      "MACSec global configuration";
    container shutdown {
      presence "Indicates a shutdown node is configured.";
      description
        "Disable macsec on all data ports, has no impact on macsec configs";
    }
  }
}
