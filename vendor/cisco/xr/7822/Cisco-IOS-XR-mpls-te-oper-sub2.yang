submodule Cisco-IOS-XR-mpls-te-oper-sub2 {
  belongs-to Cisco-IOS-XR-mpls-te-oper {
    prefix Cisco-IOS-XR-mpls-te-oper;
  }

  import ietf-inet-types {
    prefix inet;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR mpls-te package operational data.
     
     Copyright (c) 2013-2022 by Cisco Systems, Inc.
     All rights reserved.";

  revision 2022-08-30 {
    description
      "Extending self-ping statistics bag
       2022-03-18
         Added self-ping under named-tunnels";
    semver:module-version "1.3.0";
  }
  revision 2021-08-09 {
    description
      "Added load-interval attribute in the tunnel class. IosSetYangSchemaRev Cisco-IOS-XR-mpls-te-oper";
    semver:module-version "1.2.0";
  }
  revision 2021-01-19 {
    description
      "Added bandwidth-protection for auto-backups. Added signalled-bandwidth and soft-preemption for attribute set of autobackups.
       2020-11-05
           Added secondary router id for TE nodes.";
    semver:module-version "1.1.0";
  }
  revision 2020-03-28 {
    description
      "Added dark bandwidth accounting related oper info. Added stateful PCE static delegation related oper info. Added P2MP TE realted oper info. Added new operational leaves sim-rate-set sim-rate pce-address rewrite-lsd-queue tunnel-id-xr controller-handle backup-tunnel-sig-name protected-interface attribute-set-crc32 error delegation-status error context rewrite-lsd-queue simrate-enabled-in-last-application tunnel-id-xr p2mp-id-xr lsp-id-xr source-address-xr simrate-enabled-in-last-application is-expand-timer-running expand-timer-duration expand-timer-remain egress-interface-handle ingress-interface-handle srdb-check-enabled destination-create-time link-if-index create-time is-config-pending attribute-set-crc32 destination-list-crc32 maximum-destination-count maximum-tunnel-count srlg-number-xr tunnel-interface-name lsp-id-xr tunnel-rewrite-ctype tunnel-load-share tunnel-policy-class tunnel-forward-class lmp-is-allocated topology-node-igp-id topology-node-igp-area topology-node-is-router link-id classification-flags current-lsp-bandwidth-requested current-lsp-bandwidth-requested-type standby-lsp-bandwidth-requested standby-lsp-bandwidth-requested-type reopt-lsp-bandwidth-requested reopt-lsp-bandwidth-requested-type standby-reopt-lsp-bandwidth-requested standby-reopt-lsp-bandwidth-requested-type destination-address error tunnel-name-xr interface-name-xr interface-name";
    semver:module-version "1.0.0";
  }
  revision 2019-04-05 {
    description
      "Establish semantic version baseline.";
    semver:module-version "1.0.0";
  }
  revision 2018-08-01 {
    description
      "Removed empty groupings.";
  }
  revision 2017-09-07 {
    description
      "Fixed type translation error.";
  }
  revision 2017-05-01 {
    description
      "Fixing backward compatibility error in module.";
  }
  revision 2015-11-09 {
    description
      "IOS XR 6.0 revision.";
  }

  typedef Tp-mid-lsp-status {
    type enumeration {
      enum "up" {
        description
          "Deprecated";
      }
      enum "down" {
        description
          "Deprecated";
      }
    }
    description
      "Deprecated";
  }

  grouping MPLS-TP-MID-SUMMARY-INFO {
    description
      "Deprecated";
    leaf mid-points {
      type uint32;
      description
        "Deprecated";
    }
    leaf up-forward-ls-ps {
      type uint32;
      description
        "Deprecated";
    }
    leaf down-forward-ls-ps {
      type uint32;
      description
        "Deprecated";
    }
    leaf up-reverse-ls-ps {
      type uint32;
      description
        "Deprecated";
    }
    leaf down-reverse-ls-ps {
      type uint32;
      description
        "Deprecated";
    }
  }

  grouping MPLS-TP-MID-LSP-INFO {
    description
      "Deprecated";
    leaf out-label {
      type uint32;
      description
        "Deprecated";
    }
    leaf out-link {
      type uint32;
      description
        "Deprecated";
    }
    leaf oam-refresh-interval {
      type uint32;
      description
        "Deprecated";
    }
    leaf outgoing-interface {
      type string;
      description
        "Deprecated";
    }
    leaf next-hop-address {
      type inet:ipv4-address;
      description
        "Deprecated";
    }
    leaf in-label {
      type uint32;
      description
        "Deprecated";
    }
    leaf bandwidth {
      type uint32;
      description
        "Deprecated";
    }
  }

  grouping MPLS-TP-MID-INFO {
    description
      "Deprecated";
    leaf midpoint-name {
      type string;
      description
        "Deprecated";
    }
    leaf tunnel-name {
      type string;
      description
        "Deprecated";
    }
    leaf source-node-id {
      type inet:ipv4-address;
      description
        "Deprecated";
    }
    leaf source-global-id {
      type uint32;
      description
        "Deprecated";
    }
    leaf source-tunnel-id {
      type uint32;
      description
        "Deprecated";
    }
    leaf lsp-id {
      type uint32;
      description
        "Deprecated";
    }
    leaf destination-node-id {
      type inet:ipv4-address;
      description
        "Deprecated";
    }
    leaf destination-global-id {
      type uint32;
      description
        "Deprecated";
    }
    leaf destination-tunnel-id {
      type uint32;
      description
        "Deprecated";
    }
    leaf forward-lsp-state {
      type Tp-mid-lsp-status;
      description
        "Deprecated";
    }
    leaf reverse-lsp-state {
      type Tp-mid-lsp-status;
      description
        "Deprecated";
    }
  }

  grouping MPLS-TP-DETAIL-MID-INFO {
    description
      "Deprecated";
    container brief-lsp-information {
      description
        "Deprecated";
      uses MPLS-TP-MID-INFO;
    }
    container forward-lsp {
      description
        "Deprecated";
      uses MPLS-TP-MID-LSP-INFO;
    }
    container reverse-lsp {
      description
        "Deprecated";
      uses MPLS-TP-MID-LSP-INFO;
    }
    leaf forward-lsp-reserved-bandwidth {
      type uint32;
      description
        "Deprecated";
    }
    leaf reverse-lsp-reserved-bandwidth {
      type uint32;
      description
        "Deprecated";
    }
  }
}
