submodule Cisco-IOS-XR-attestation-agent-oper-sub1 {
  belongs-to Cisco-IOS-XR-attestation-agent-oper {
    prefix Cisco-IOS-XR-attestation-agent-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR attestation-agent package operational data.
     
     Copyright (c) 2013-2022 by Cisco Systems, Inc.
     All rights reserved.";

  revision 2022-06-03 {
    description
      "Added new oper model for attestation entities.";
    semver:module-version "1.0.0";
  }
  revision 2019-04-05 {
    description
      "Establish semantic version baseline.";
  }
  revision 2015-11-09 {
    description
      "IOS XR 6.0 revision.";
  }

  grouping SECURE-BOOT-STATUS {
    description
      "SECURE BOOT STATUS";
    leaf secure-boot-enable {
      type boolean;
      description
        "Secure boot enabled or not";
    }
  }
}
