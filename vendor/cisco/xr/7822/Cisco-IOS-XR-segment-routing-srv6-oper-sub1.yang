submodule Cisco-IOS-XR-segment-routing-srv6-oper-sub1 {
  belongs-to Cisco-IOS-XR-segment-routing-srv6-oper {
    prefix Cisco-IOS-XR-segment-routing-srv6-oper;
  }

  import ietf-inet-types {
    prefix inet;
  }
  import ietf-yang-types {
    prefix yang;
  }
  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR segment-routing-srv6 package operational data.
     
     Copyright (c) 2013-2022 by Cisco Systems, Inc.
     All rights reserved.";

  revision 2022-05-19 {
    description
      "New uSID LIB ranges information
       2022-05-12
         Platform capabilities extended for displaying if shift-only drop route is supported
       2022-03-23
         Added support for static adjacency SID status
       2021-11-23
         Display locators delayed-delete status
       2021-11-19
         Platform capabilities report extended with Max Locator supported
       2021-10-15
         New SID CTX type supported uDT46 and DT46
       2021-09-16
         Manager will display platform requested defaults for traffic-class and hoplimit SRv6 encap parameters";
    semver:module-version "5.0.0";
  }
  revision 2021-06-23 {
    description
      "Added id name to OOR summary";
    semver:module-version "4.0.0";
  }
  revision 2020-12-11 {
    description
      "Update manager show command for 2 passes
       2020-10-16
           Rename SID count fields in SID manager summary. sids_count only includes non auto-generated SIDs.
       2020-05-06
           changes in def for some endpoint types and headend types
       2020-04-16
           Changes due to common Srv6 bag and renaming some leaf";
    semver:module-version "3.0.0";
  }
  revision 2019-11-20 {
    description
      "Changes for SRv6 end function
       2019-04-22
         Flex-Algo specific changes";
    semver:module-version "2.0.0";
  }
  revision 2019-04-05 {
    description
      "Establish semantic version baseline.";
    semver:module-version "1.0.1";
  }
  revision 2015-11-09 {
    description
      "IOS XR 6.0 revision.";
  }

  typedef Sid-state {
    type enumeration {
      enum "unknown" {
        description
          "Unknown";
      }
      enum "in-use" {
        description
          "In Use";
      }
      enum "pending" {
        description
          "Pending";
      }
      enum "stale" {
        description
          "Stale";
      }
    }
    description
      "SID manager SID state";
  }

  typedef Sid-allocation {
    type enumeration {
      enum "unknown" {
        description
          "Unknown";
      }
      enum "dynamic" {
        description
          "Dynamic";
      }
      enum "explicit" {
        description
          "Explicit";
      }
    }
    description
      "SID allocation type";
  }

  typedef In6-addr {
    type inet:ipv6-address;
    description
      "In6 addr";
  }

  typedef Srv6af {
    type enumeration {
      enum "no-af" {
        description
          "No AF";
      }
      enum "ipv4-af" {
        description
          "IPv4 AF";
      }
      enum "ipv6-af" {
        description
          "IPv6 AF";
      }
    }
    description
      "SRv6 AF type";
  }

  typedef Mgmt-srv6-endpoint {
    type enumeration {
      enum "unknown" {
        description
          "Unknown Endpoint type";
      }
      enum "end" {
        description
          "End (no PSP/USP)";
      }
      enum "end-with-psp" {
        description
          "End with PSP";
      }
      enum "end-with-usp" {
        description
          "End with USP";
      }
      enum "end-with-psp-usp" {
        description
          "End with PSP/USP";
      }
      enum "end-x" {
        description
          "End.X (no PSP/USP)";
      }
      enum "end-x-with-psp" {
        description
          "End.X with PSP";
      }
      enum "end-x-with-usp" {
        description
          "End.X with USP";
      }
      enum "end-x-with-psp-usp" {
        description
          "End.X with PSP/USP";
      }
      enum "end-tbl" {
        description
          "End.T (no PSP/USP)";
      }
      enum "end-tbl-with-psp" {
        description
          "End.T with PSP";
      }
      enum "end-tbl-with-usp" {
        description
          "End.T with USP";
      }
      enum "end-tbl-with-psp-usp" {
        description
          "End.T with PSP/USP";
      }
      enum "end-b6-insert" {
        description
          "End.B6.Insert";
      }
      enum "end-b6-encaps" {
        description
          "End.B6.Encaps";
      }
      enum "end-bm" {
        description
          "End.BM";
      }
      enum "end-dx6" {
        description
          "End.DX6";
      }
      enum "end-dx4" {
        description
          "End.DX4";
      }
      enum "end-dt6" {
        description
          "End.DT6";
      }
      enum "end-dt4" {
        description
          "End.DT4";
      }
      enum "end-dt46" {
        description
          "End.DT46";
      }
      enum "end-dx2" {
        description
          "End.DX2";
      }
      enum "end-dx2v" {
        description
          "End.DX2V";
      }
      enum "end-dt2u" {
        description
          "End.DT2U";
      }
      enum "end-dt2m" {
        description
          "End.DT2M";
      }
      enum "end-s" {
        description
          "End.S";
      }
      enum "end-b6-insert-red" {
        description
          "End.B6.Insert.Reduced";
      }
      enum "end-b6-encaps-red" {
        description
          "End.B6.Encaps.Reduced";
      }
      enum "end-with-usd" {
        description
          "End with USD";
      }
      enum "end-with-psp-usd" {
        description
          "End with PSP/USD";
      }
      enum "end-with-usp-usd" {
        description
          "End with USP/USD";
      }
      enum "end-with-psp-usp-usd" {
        description
          "End with PSP/USP/USD";
      }
      enum "end-x-with-usd" {
        description
          "End.X with USD";
      }
      enum "end-x-with-psp-usd" {
        description
          "End.X with PSP/USD";
      }
      enum "end-x-with-usp-usd" {
        description
          "End.X with USP/USD";
      }
      enum "end-x-with-psp-usp-usd" {
        description
          "End.X with PSP/USP/USD";
      }
      enum "end-tbl-with-usd" {
        description
          "End.T with USD";
      }
      enum "end-tbl-with-psp-usd" {
        description
          "End.T with PSP/USD";
      }
      enum "end-tbl-with-usp-usd" {
        description
          "End.T with USP/USD";
      }
      enum "end-tbl-with-psp-usp-usd" {
        description
          "End.T with PSP/USP/USD";
      }
      enum "end-op" {
        description
          "End.OP";
      }
      enum "end-otp" {
        description
          "End.OTP";
      }
      enum "un-shift-only" {
        description
          "uN Shift-only";
      }
      enum "un" {
        description
          "uN";
      }
      enum "un-psp" {
        description
          "uN with PSP";
      }
      enum "un-usp" {
        description
          "uN with USP";
      }
      enum "un-psp-usp" {
        description
          "uN with PSP-USP";
      }
      enum "un-usd" {
        description
          "uN with USD";
      }
      enum "un-psp-usd" {
        description
          "uN with PSP-USD";
      }
      enum "un-usp-usd" {
        description
          "uN with USP-USD";
      }
      enum "un-psp-usp-usd" {
        description
          "uN with PSP_USP-USD";
      }
      enum "ua-shift-only" {
        description
          "uA Shift-only";
      }
      enum "ua" {
        description
          "uA";
      }
      enum "ua-psp" {
        description
          "uA with PSP";
      }
      enum "ua-usp" {
        description
          "uA with USP";
      }
      enum "ua-psp-usp" {
        description
          "uA with PSP-USP";
      }
      enum "ua-usd" {
        description
          "uA with USD";
      }
      enum "ua-psp-usd" {
        description
          "uA with PSP-USD";
      }
      enum "ua-usp-usd" {
        description
          "uA with USP-USD";
      }
      enum "ua-psp-usp-usd" {
        description
          "uA with PSP_USP-USD";
      }
      enum "udx6" {
        description
          "uDX6";
      }
      enum "udx4" {
        description
          "uDX4";
      }
      enum "udt6" {
        description
          "uDT6";
      }
      enum "udt4" {
        description
          "uDT4";
      }
      enum "udt46" {
        description
          "uDT46";
      }
      enum "udx2" {
        description
          "uDX2";
      }
      enum "udx2v" {
        description
          "uDX2V";
      }
      enum "udt2u" {
        description
          "uDT2U";
      }
      enum "udt2m" {
        description
          "uDT2M";
      }
      enum "ub6-insert" {
        description
          "uB6 Insert";
      }
      enum "ub6-encaps" {
        description
          "uB6 Encaps";
      }
      enum "ub6-insert-red" {
        description
          "uB6 Insert.Red";
      }
      enum "ub6-encaps-red" {
        description
          "uB6 Encaps.Red";
      }
      enum "ubm" {
        description
          "uBM";
      }
    }
    description
      "SRv6 Endpoint Behavior Type";
  }

  typedef Srv6-out-of-resource-state {
    type enumeration {
      enum "oor-green" {
        description
          "Resources Available";
      }
      enum "oor-yellow" {
        description
          "Resources Warning. Have exceeded minor
           threshold";
      }
      enum "oor-red" {
        description
          "Out of Resources. Have exceeded major threshold";
      }
    }
    description
      "SRv6 Out of Resource State";
  }

  typedef Mgmt-srv6-sid-fmt {
    type enumeration {
      enum "none" {
        value 0;
        description
          "No format";
      }
      enum "base" {
        value 1;
        description
          "Base Format";
      }
      enum "f3216" {
        value 2;
        description
          "Micro-segment F3216 Format";
      }
    }
    description
      "SRv6 SID Format Type";
  }

  typedef Srv6-op-mode {
    type enumeration {
      enum "none" {
        description
          "No mode";
      }
      enum "srv6-base" {
        description
          "SRv6 base";
      }
      enum "srv6-micro-segment" {
        description
          "SRv6 micro-segment";
      }
    }
    description
      "SRv6 operational mode";
  }

  grouping SRV6-STATIC-ENDPOINT-INFO {
    description
      "SRv6 SID Manager Static Endpoint info";
    container sid-behavior {
      description
        "SID Behavior Type";
      uses MGMT-SRV6-ENDPOINT-BEHAVIOR;
    }
    container sid-context {
      description
        "SID Context";
      uses MGMT-SRV6-SID-CTX;
    }
    leaf sid {
      type string;
      description
        "SID Value";
    }
    leaf is-locator-up {
      type boolean;
      description
        "Is Locator Up?";
    }
    leaf is-locator-oor {
      type boolean;
      description
        "Is Locator OOR?";
    }
    leaf is-sid-allocated {
      type boolean;
      description
        "Is a SID allocated?";
    }
    leaf algo-match {
      type boolean;
      description
        "Does the locator algo match configured algo?";
    }
  }

  grouping SRV6-LOCATOR-INTF-INFO {
    description
      "SRv6 locator interface";
    leaf name {
      type string;
      description
        "Interface name";
    }
    leaf if-handle {
      type xr:Hex-integer;
      description
        "Interface handle";
    }
    leaf programmed-prefix {
      type string;
      description
        "Interface prefix/addr programmed";
    }
  }

  grouping SRV6-LOCATOR-INFO {
    description
      "SRv6 Locator info";
    container micro-segment-behavior {
      description
        "Micro-segment behavior";
      uses MGMT-SRV6-ENDPOINT-BEHAVIOR;
    }
    container interface {
      description
        "Locator IM intf info";
      uses SRV6-LOCATOR-INTF-INFO;
    }
    container create-timestamp {
      description
        "Creation timestamp";
      uses MGMT-SIDMGR-TIMESTAMP;
    }
    leaf name {
      type string;
      description
        "Locator Name";
    }
    leaf id {
      type uint32;
      description
        "Locator ID";
    }
    leaf prefix {
      type string;
      description
        "Locator Prefix";
    }
    leaf algorithm-id {
      type uint8;
      description
        "Algorithm Id";
    }
    leaf is-operational {
      type boolean;
      description
        "Locator status is Up or Down";
    }
    leaf is-micro-segment {
      type boolean;
      description
        "A Micro-segment locator";
    }
    leaf is-anycast {
      type boolean;
      description
        "An Anycast locator";
    }
    leaf is-delayed-delete {
      type boolean;
      description
        "Locator will delay deleting route after SID free
         during migration";
    }
    leaf out-of-resources-state {
      type Srv6-out-of-resource-state;
      description
        "Locator Resources State for SIDs";
    }
    leaf sids-count {
      type uint32;
      description
        "Number of allocated SIDs";
    }
  }

  grouping SID-OWNER {
    description
      "SID Owner";
    leaf owner {
      type string;
      description
        "Owner";
    }
  }

  grouping SRV6-SID-INFO {
    description
      "SRv6 SID Manager SID info";
    container sid-behavior {
      description
        "SID Behavior Type";
      uses MGMT-SRV6-ENDPOINT-BEHAVIOR;
    }
    container sid-context {
      description
        "SID Context";
      uses MGMT-SRV6-SID-CTX;
    }
    container create-timestamp {
      description
        "Creation timestamp";
      uses MGMT-SIDMGR-TIMESTAMP;
    }
    leaf sid {
      type string;
      description
        "SID Value";
    }
    leaf allocation-type {
      type Sid-allocation;
      description
        "Allocation Type";
    }
    leaf state {
      type Sid-state;
      description
        "State";
    }
    leaf has-forwarding {
      type boolean;
      description
        "Rewrite done or not";
    }
    leaf locator {
      type string;
      description
        "Associated locator";
    }
    leaf sid-functionvalue {
      type uint32;
      description
        "SID function value";
    }
    list owner {
      description
        "Owner";
      uses SID-OWNER;
    }
  }

  grouping MGMT-SIDMGR-TIMESTAMP {
    description
      "SID Manager Generic Timestamp";
    leaf time-in-nano-seconds {
      type uint64;
      units "nanosecond";
      description
        "Timestamp in nano seconds";
    }
    leaf age-in-nano-seconds {
      type uint64;
      units "nanosecond";
      description
        "Age in nano seconds";
    }
  }

  grouping MGMT-SRV6-SID-CTX-U-DX {
    description
      "SRv6 uDX4/6 SID context";
    leaf table-id {
      type uint32;
      description
        "Table ID";
    }
    leaf next-hop-set-id {
      type uint32;
      description
        "Next Hop Set ID";
    }
    leaf differentiator {
      type string {
        length "0..46";
      }
      description
        "Additional differentiator";
    }
  }

  grouping MGMT-SRV6-SID-CTX-U-DT2M {
    description
      "SRv6 uDT2M SID context";
    container dt2-base-ctx {
      description
        "Common DT2 context";
      uses MGMT-SRV6-SID-CTX-DT2-BASE;
    }
  }

  grouping MGMT-SRV6-SID-CTX-U-DT2U {
    description
      "SRv6 uDT2U SID context";
    container dt2-base-ctx {
      description
        "Common DT2 context";
      uses MGMT-SRV6-SID-CTX-DT2-BASE;
    }
  }

  grouping MGMT-SRV6-SID-CTX-U-DX2 {
    description
      "SRv6 uDX2 SID context";
    leaf evi {
      type uint32;
      description
        "EVI";
    }
    leaf eth-tag {
      type uint32;
      description
        "Ethernet Tag ID";
    }
    leaf differentiator {
      type string {
        length "0..46";
      }
      description
        "Additional differentiator";
    }
  }

  grouping MGMT-SRV6-ADDR-UNION {
    description
      "SRv6 IP address union";
    leaf af-type {
      type Srv6af;
      description
        "AFType";
    }
    leaf ipv4 {
      when "../af-type = 'ipv4-af'" {
        description
          "../AFType = 'IPv4_AF'";
      }
      type inet:ipv4-address;
      description
        "IPv4 address";
    }
    leaf ipv6 {
      when "../af-type = 'ipv6-af'" {
        description
          "../AFType = 'IPv6_AF'";
      }
      type In6-addr;
      description
        "IPv6 address";
    }
  }

  grouping MGMT-SRV6-SID-CTX-U-B6 {
    description
      "SRv6 uB6 SID context";
    container policy-endpoint {
      description
        "Policy Endpoint address";
      uses MGMT-SRV6-ADDR-UNION;
    }
    leaf policy-name {
      type string;
      description
        "Policy name";
    }
    leaf policy-color {
      type uint32;
      description
        "Color associated with the policy";
    }
    leaf policy-endpoint-is-null {
      type boolean;
      description
        "Policy endpoint is null";
    }
    leaf differentiator {
      type string {
        length "0..46";
      }
      description
        "Additional differentiator";
    }
  }

  grouping MGMT-SRV6-SID-CTX-U-DT46 {
    description
      "SRv6 uDT46 SID context";
    leaf vrf-name {
      type string;
      description
        "VRF name";
    }
    leaf differentiator {
      type string {
        length "0..46";
      }
      description
        "Additional differentiator";
    }
  }

  grouping MGMT-SRV6-SID-CTX-DT-BASE {
    description
      "SRv6 uDTx/End.DTx SID base context";
    leaf table-id {
      type uint32;
      description
        "Table ID";
    }
    leaf differentiator {
      type string {
        length "0..46";
      }
      description
        "Additional differentiator";
    }
  }

  grouping MGMT-SRV6-SID-CTX-U-DT {
    description
      "SRv6 uDT4/6 SID context";
    container u-dt-base-ctx {
      description
        "Common uDT context";
      uses MGMT-SRV6-SID-CTX-DT-BASE;
    }
  }

  grouping MGMT-SRV6-SID-CTX-U-N {
    description
      "SRv6 uN SID context";
    container u-n-base-ctx {
      description
        "Common uN context";
      uses MGMT-SRV6-SID-CTX1;
    }
  }

  grouping MGMT-SRV6-SID-CTX-U-A-PSP-USD {
    description
      "SRv6 End.X (PSP) SID context";
    container u-a-base-ctx {
      description
        "Common uA context";
      uses MGMT-SRV6-SID-CTX-U-A;
    }
  }

  grouping MGMT-SRV6-SID-CTX-U-A {
    description
      "SRv6 uA SID context";
    leaf is-protected {
      type boolean;
      description
        "Is protected?";
    }
    leaf opaque-id {
      type uint8;
      description
        "Additional differentiator - opaque to SIDMgr";
    }
    leaf algo-id {
      type uint8;
      description
        "Algorithm Id";
    }
    leaf nexthop-address {
      type inet:ipv6-address;
      description
        "Nexthop IP address";
    }
    leaf if-name {
      type string;
      description
        "Interface name";
    }
    leaf differentiator {
      type string {
        length "0..46";
      }
      description
        "Additional differentiator";
    }
  }

  grouping MGMT-SRV6-SID-CTX-U-A-SHIFT-ONLY {
    description
      "SRv6 End.X (USP) SID context";
    container u-a-base-ctx {
      description
        "Common uA context";
      uses MGMT-SRV6-SID-CTX-U-A;
    }
  }

  grouping MGMT-SRV6-SID-CTX-X-PSP-USD {
    description
      "SRv6 End.X (PSP-USD) SID context";
    container xctx {
      description
        "Common End.X context for End.X (PSP-USD) SID";
      uses MGMT-SRV6-SID-CTX-X;
    }
  }

  grouping MGMT-SRV6-SID-CTX-E-PSP-USD {
    description
      "SRv6 End (PSP-USD) SID context";
    container ectx {
      description
        "Common End context for End (PSP-USD) SID";
      uses MGMT-SRV6-SID-CTX1;
    }
  }

  grouping MGMT-SRV6-SID-CTX-DT2M {
    description
      "SRv6 End.DT2M SID context";
    container dt2-base-ctx {
      description
        "Common DT2 context";
      uses MGMT-SRV6-SID-CTX-DT2-BASE;
    }
  }

  grouping MGMT-SRV6-SID-CTX-DT2-BASE {
    description
      "SRv6 uDT2x/End.DT2x SID base context";
    leaf evi {
      type uint32;
      description
        "EVI";
    }
    leaf opaque-id {
      type uint32;
      description
        "Additional differentiator - opaque to SIDMgr";
    }
    leaf differentiator {
      type string {
        length "0..46";
      }
      description
        "Additional differentiator";
    }
  }

  grouping MGMT-SRV6-SID-CTX-DT2U {
    description
      "SRv6 End.DT2U SID context";
    container dt2-base-ctx {
      description
        "Common DT2 context";
      uses MGMT-SRV6-SID-CTX-DT2-BASE;
    }
  }

  grouping MGMT-SRV6-SID-CTX-DX2 {
    description
      "SRv6 End.DX2 SID context";
    leaf evi {
      type uint32;
      description
        "EVI";
    }
    leaf eth-tag {
      type uint32;
      description
        "Ethernet Tag ID";
    }
    leaf differentiator {
      type string {
        length "0..46";
      }
      description
        "Additional differentiator";
    }
  }

  grouping MGMT-SRV6-SID-CTX-DT46 {
    description
      "SRv6 End.DT46 SID context";
    leaf vrf-name {
      type string;
      description
        "VRF name";
    }
    leaf differentiator {
      type string {
        length "0..46";
      }
      description
        "Additional differentiator";
    }
  }

  grouping MGMT-SRV6-SID-CTX-DT {
    description
      "SRv6 End.DT4/6 SID context";
    leaf table-id {
      type uint32;
      description
        "Table ID";
    }
    leaf differentiator {
      type string {
        length "0..46";
      }
      description
        "Additional differentiator";
    }
  }

  grouping MGMT-SRV6-SID-CTX-DX {
    description
      "SRv6 End.DX4/6 SID context";
    leaf table-id {
      type uint32;
      description
        "Table ID";
    }
    leaf next-hop-set-id {
      type uint32;
      description
        "Next Hop Set ID";
    }
    leaf differentiator {
      type string {
        length "0..46";
      }
      description
        "Additional differentiator";
    }
  }

  grouping MGMT-SRV6-SID-CTX-X {
    description
      "SRv6 End.X SID base context";
    leaf is-protected {
      type boolean;
      description
        "Is protected?";
    }
    leaf opaque-id {
      type uint8;
      description
        "Additional differentiator - opaque to SIDMgr";
    }
    leaf nexthop-address {
      type inet:ipv6-address;
      description
        "Nexthop IP address";
    }
    leaf if-name {
      type string;
      description
        "Interface name";
    }
    leaf differentiator {
      type string {
        length "0..46";
      }
      description
        "Additional differentiator";
    }
  }

  grouping MGMT-SRV6-SID-CTX-X-PSP {
    description
      "SRv6 End.X (PSP) SID context";
    container xctx {
      description
        "Common End.X context for End.X (PSP) SID";
      uses MGMT-SRV6-SID-CTX-X;
    }
  }

  grouping MGMT-SRV6-SID-CTX-RSVD {
    description
      "SRv6 Reserved SID context";
    leaf table-id {
      type uint32;
      description
        "Table Id";
    }
    leaf differentiator {
      type string {
        length "0..46";
      }
      description
        "Additional differentiator";
    }
  }

  grouping MGMT-SRV6-SID-CTX-OP {
    description
      "SRv6 End.OP SID context";
    container op-ctx {
      description
        "Common reserved context for End.OP SID";
      uses MGMT-SRV6-SID-CTX-RSVD;
    }
  }

  grouping MGMT-SRV6-SID-CTX1 {
    description
      "SRv6 End SID context";
    leaf table-id {
      type uint32;
      description
        "Table Id";
    }
    leaf opaque-id {
      type uint16;
      description
        "Additional differentiator - opaque to SIDMgr";
    }
    leaf differentiator {
      type string {
        length "0..46";
      }
      description
        "Additional differentiator";
    }
  }

  grouping MGMT-SRV6-SID-CTX-E-PSP {
    description
      "SRv6 End (PSP) SID context";
    container ectx {
      description
        "Common End context for End (PSP) SID";
      uses MGMT-SRV6-SID-CTX1;
    }
  }

  grouping MGMT-SRV6-SID-CTX-KEY {
    description
      "MGMT SRV6 SID CTX KEY";
    container e-psp {
      when "../sid-context-type = 'end-with-psp'" {
        description
          "../SIDContextType = 'EndWithPSP'";
      }
      description
        "End (PSP) SID context";
      uses MGMT-SRV6-SID-CTX-E-PSP;
    }
    container op {
      when "../sid-context-type = 'end-op'" {
        description
          "../SIDContextType = 'EndOP'";
      }
      description
        "End.OP SID context";
      uses MGMT-SRV6-SID-CTX-OP;
    }
    container x-psp {
      when "../sid-context-type = 'end-x-with-psp'" {
        description
          "../SIDContextType = 'EndXWithPSP'";
      }
      description
        "End.X (PSP) SID context";
      uses MGMT-SRV6-SID-CTX-X-PSP;
    }
    container dx4 {
      when "../sid-context-type = 'end-dx4'" {
        description
          "../SIDContextType = 'EndDX4'";
      }
      description
        "End.DX4 SID context";
      uses MGMT-SRV6-SID-CTX-DX;
    }
    container dt4 {
      when "../sid-context-type = 'end-dt4'" {
        description
          "../SIDContextType = 'EndDT4'";
      }
      description
        "End.DT4 SID context";
      uses MGMT-SRV6-SID-CTX-DT;
    }
    container dx6 {
      when "../sid-context-type = 'end-dx6'" {
        description
          "../SIDContextType = 'EndDX6'";
      }
      description
        "End.DX6 SID context";
      uses MGMT-SRV6-SID-CTX-DX;
    }
    container dt6 {
      when "../sid-context-type = 'end-dt6'" {
        description
          "../SIDContextType = 'EndDT6'";
      }
      description
        "End.DT6 SID context";
      uses MGMT-SRV6-SID-CTX-DT;
    }
    container dt46 {
      when "../sid-context-type = 'end-dt46'" {
        description
          "../SIDContextType = 'EndDT46'";
      }
      description
        "End.DT46 SID context";
      uses MGMT-SRV6-SID-CTX-DT46;
    }
    container dx2 {
      when "../sid-context-type = 'end-dx2'" {
        description
          "../SIDContextType = 'EndDX2'";
      }
      description
        "End.DX2 SID context";
      uses MGMT-SRV6-SID-CTX-DX2;
    }
    container dt2u {
      when "../sid-context-type = 'end-dt2u'" {
        description
          "../SIDContextType = 'EndDT2U'";
      }
      description
        "End.DT2U SID context";
      uses MGMT-SRV6-SID-CTX-DT2U;
    }
    container dt2m {
      when "../sid-context-type = 'end-dt2m'" {
        description
          "../SIDContextType = 'EndDT2M'";
      }
      description
        "End.DT2M SID context";
      uses MGMT-SRV6-SID-CTX-DT2M;
    }
    container e-psp-usd {
      when "../sid-context-type = 'end-with-psp-usd'" {
        description
          "../SIDContextType = 'EndWithPSP_USD'";
      }
      description
        "End (PSP-USD) SID context";
      uses MGMT-SRV6-SID-CTX-E-PSP-USD;
    }
    container x-psp-usd {
      when "../sid-context-type = 'end-x-with-psp-usd'" {
        description
          "../SIDContextType = 'EndXWithPSP_USD'";
      }
      description
        "End.X (PSP-USD) SID context";
      uses MGMT-SRV6-SID-CTX-X-PSP-USD;
    }
    container u-a-shift-only {
      when "../sid-context-type = 'ua-shift-only'" {
        description
          "../SIDContextType = 'UA_ShiftOnly'";
      }
      description
        "uA Shift-only SID context";
      uses MGMT-SRV6-SID-CTX-U-A-SHIFT-ONLY;
    }
    container u-a-psp-usd {
      when "../sid-context-type = 'ua-psp-usd'" {
        description
          "../SIDContextType = 'UA_PSP_USD'";
      }
      description
        "uA PSP-USD SID context";
      uses MGMT-SRV6-SID-CTX-U-A-PSP-USD;
    }
    container u-n-shift-only {
      when "../sid-context-type = 'un-shift-only'" {
        description
          "../SIDContextType = 'UN_ShiftOnly'";
      }
      description
        "uN Shift-only SID context";
      uses MGMT-SRV6-SID-CTX-U-N;
    }
    container u-n-psp-usd {
      when "../sid-context-type = 'un-psp-usd'" {
        description
          "../SIDContextType = 'UN_PSP_USD'";
      }
      description
        "uN PSP-USD SID context";
      uses MGMT-SRV6-SID-CTX-U-N;
    }
    container u-dt4 {
      when "../sid-context-type = 'udt4'" {
        description
          "../SIDContextType = 'UDT4'";
      }
      description
        "uDT4 SID context";
      uses MGMT-SRV6-SID-CTX-U-DT;
    }
    container u-dt6 {
      when "../sid-context-type = 'udt6'" {
        description
          "../SIDContextType = 'UDT6'";
      }
      description
        "uDT6 SID context";
      uses MGMT-SRV6-SID-CTX-U-DT;
    }
    container u-dt46 {
      when "../sid-context-type = 'udt46'" {
        description
          "../SIDContextType = 'UDT46'";
      }
      description
        "uDT46 SID context";
      uses MGMT-SRV6-SID-CTX-U-DT46;
    }
    container u-b6-insert-red {
      when "../sid-context-type = 'ub6-insert-red'" {
        description
          "../SIDContextType = 'UB6_InsertRed'";
      }
      description
        "uB6 Insert.Red SID context";
      uses MGMT-SRV6-SID-CTX-U-B6;
    }
    container udx2 {
      when "../sid-context-type = 'udx2'" {
        description
          "../SIDContextType = 'UDX2'";
      }
      description
        "UDX2 SID context";
      uses MGMT-SRV6-SID-CTX-U-DX2;
    }
    container udt2u {
      when "../sid-context-type = 'udt2u'" {
        description
          "../SIDContextType = 'UDT2U'";
      }
      description
        "uDT2U SID context";
      uses MGMT-SRV6-SID-CTX-U-DT2U;
    }
    container udt2m {
      when "../sid-context-type = 'udt2m'" {
        description
          "../SIDContextType = 'UDT2M'";
      }
      description
        "uDT2M SID context";
      uses MGMT-SRV6-SID-CTX-U-DT2M;
    }
    container udx4 {
      when "../sid-context-type = 'udx4'" {
        description
          "../SIDContextType = 'UDX4'";
      }
      description
        "UDX4 SID context";
      uses MGMT-SRV6-SID-CTX-U-DX;
    }
    container udx6 {
      when "../sid-context-type = 'udx6'" {
        description
          "../SIDContextType = 'UDX6'";
      }
      description
        "UDX6 SID context";
      uses MGMT-SRV6-SID-CTX-U-DX;
    }
    leaf sid-context-type {
      type Mgmt-srv6-endpoint;
      description
        "SIDContextType";
    }
  }

  grouping MGMT-SRV6-SID-CTX {
    description
      "SRv6 SID context";
    container key {
      description
        "SID Key";
      uses MGMT-SRV6-SID-CTX-KEY;
    }
    leaf application-data {
      type yang:hex-string;
      description
        "Application opaque data";
    }
  }

  grouping MGMT-SRV6-ENDPOINT-BEHAVIOR {
    description
      "SRv6 Endpoint Behavior Info";
    leaf type {
      type Mgmt-srv6-endpoint;
      description
        "Behavior type";
    }
    leaf description {
      type string;
      description
        "Behavior description";
    }
  }

  grouping SRV6-LOCAL-SID-INFO {
    description
      "SRv6 SID Manager Local SID info";
    container sid-behavior {
      description
        "SID Behavior";
      uses MGMT-SRV6-ENDPOINT-BEHAVIOR;
    }
    container sid-context {
      description
        "SID Context";
      uses MGMT-SRV6-SID-CTX;
    }
    container create-timestamp {
      description
        "Creation timestamp";
      uses MGMT-SIDMGR-TIMESTAMP;
    }
    leaf sid {
      type string;
      description
        "SID Value";
    }
    leaf sid-block-prefix {
      type string;
      description
        "SID Block Prefix";
    }
    leaf sid-functionvalue {
      type uint32;
      description
        "SID function value";
    }
    leaf locator-ref-count {
      type uint32;
      description
        "Number of Locators sharing this Local SID";
    }
  }

  grouping SRV6-IDBLOCK-INFO {
    description
      "SRv6 ID Block info";
    container local-sids-oor-summary {
      description
        "ID Blocks Local SID Out of Resource info";
      uses SRV6-OOR-SUMMARY;
    }
    leaf prefix {
      type string;
      description
        "ID Block Prefix";
    }
    leaf index {
      type uint32;
      description
        "ID Block Index";
    }
    leaf sids-count {
      type uint32;
      description
        "Number of SIDs";
    }
    leaf locator-ref-count {
      type uint32;
      description
        "Number of Locators Sharing this Block";
    }
  }

  grouping SRV6-PER-BEH-INFO {
    description
      "SRv6 SID HW resource consumption";
    leaf endpoint-behavior {
      type string;
      description
        "End function";
    }
    leaf value {
      type uint32;
      description
        "Value associated with the end function";
    }
  }

  grouping SRV6-PLATFORM-SET-OR-PROPAGATE {
    description
      "SRv6 Platform default encap parameters value set
       or propagate";
    leaf do-propagate {
      type boolean;
      description
        "Propagate from incoming packet or frame";
    }
    leaf value {
      type uint8;
      description
        "Specific value set";
    }
  }

  grouping MGMT-SRV6-PLATFORM-USID-ENDP-SUPPORT {
    description
      "Platform SRv6 uSID endpoint FIB support";
    leaf local-only {
      type boolean;
      description
        "Local only support";
    }
    leaf global-local-combo {
      type boolean;
      description
        "Global-Local combo support";
    }
    leaf separate-shift-and-non-shift {
      type boolean;
      description
        "Separate Shift and Non-shift support";
    }
    leaf shift-only-drop {
      type boolean;
      description
        "Shift-Only Drop route support";
    }
  }

  grouping MGMT-SRV6-PLATFORM-SIG-PARAMS {
    description
      "Platform SRv6 params to be signaled";
    leaf max-sl {
      type uint8;
      description
        "Max value of SegmentLeft field in received SRH";
    }
    leaf max-end-pop-srh {
      type uint8;
      description
        "Max num of SIDs in rcvd SRH for pop";
    }
    leaf max-h-insert {
      type uint8;
      description
        "Max num of SIDs for H.Insert op";
    }
    leaf max-h-encap {
      type uint8;
      description
        "Max num of SIDs for H.Encaps op";
    }
    leaf max-end-d {
      type uint8;
      description
        "Max num of SIDs in rcvd SRH for decap";
    }
  }

  grouping MGMT-SIDMGR-STRING {
    description
      "Generic string";
    leaf string {
      type string;
      description
        "String";
    }
  }

  grouping SRV6-PLATFORM-SUPPORT {
    description
      "SRv6 Platform Support";
    container signaled-parameters {
      description
        "Signaled Parameters";
      uses MGMT-SRV6-PLATFORM-SIG-PARAMS;
    }
    container endpoint-entries {
      description
        "Supported endpoint entries";
      uses MGMT-SRV6-PLATFORM-USID-ENDP-SUPPORT;
    }
    leaf srv6 {
      type boolean;
      description
        "SRv6 support";
    }
    leaf tilfa {
      type boolean;
      description
        "TI LFA support";
    }
    leaf microloop-avoidance {
      type boolean;
      description
        "Microloop-avoidance support";
    }
    list endpoint-behavior {
      description
        "Supported end functions";
      uses MGMT-SIDMGR-STRING;
    }
    list headend-behavior {
      description
        "Supported headend functions";
      uses MGMT-SIDMGR-STRING;
    }
    list security-rule {
      description
        "Security rules";
      uses MGMT-SIDMGR-STRING;
    }
    list counter {
      description
        "Counters";
      uses MGMT-SIDMGR-STRING;
    }
  }

  grouping SRV6-PLATFORM-CFG-SUPPORT {
    description
      "SRv6 Platform Configurable Parameters under srv6
       mode";
    leaf encap-sa {
      type boolean;
      description
        "SRv6 Encap Source Address";
    }
    leaf encap-hop-limit-value {
      type boolean;
      description
        "SRv6 Encap Hoplimit value";
    }
    leaf encap-hop-limit-propagate {
      type boolean;
      description
        "SRv6 Encap Hoplimit propagate";
    }
    leaf encap-traffic-class-value {
      type boolean;
      description
        "SRv6 value Encap TC value";
    }
    leaf encap-traffic-class-propagate {
      type boolean;
      description
        "SRv6 Encap TC propagate";
    }
    leaf lib-range {
      type boolean;
      description
        "SRv6 LIB and ELIB range support";
    }
    leaf wlib-range {
      type boolean;
      description
        "SRv6 WLIB range support";
    }
  }

  grouping SRV6-PLATFORM-CAPABILITY {
    description
      "Platform Capabilities for SRv6";
    container cfg-support {
      description
        "Configurable param support";
      uses SRV6-PLATFORM-CFG-SUPPORT;
    }
    container support {
      description
        "Feature support";
      uses SRV6-PLATFORM-SUPPORT;
    }
    container encap-hop-limit-default {
      description
        "Platform Encap Hop-limit default info";
      uses SRV6-PLATFORM-SET-OR-PROPAGATE;
    }
    container encap-traffic-class-default {
      description
        "Platform Encap Traffic-class default info";
      uses SRV6-PLATFORM-SET-OR-PROPAGATE;
    }
    leaf max-sids {
      type uint32;
      description
        "Maximum Sids";
    }
    leaf sid-holdtime-mins {
      type uint32;
      units "minute";
      description
        "Freed SID holdtime in mins";
    }
    leaf max-locators {
      type uint32;
      description
        "Maximum Locators";
    }
    list sid-resource-usage {
      description
        "SID resource usage info for each supported
         behavior";
      uses SRV6-PER-BEH-INFO;
    }
  }

  grouping SRV6-OOR-SUMMARY {
    description
      "SRv6 SID Manager Out of Resource Summary";
    leaf identifer-name {
      type string;
      description
        "OOR Identifier Name";
    }
    leaf oor-state {
      type Srv6-out-of-resource-state;
      description
        "OOR State for SIDs";
    }
    leaf oor-maximum-sid-count {
      type uint32;
      description
        "Maximum Number of SIDs";
    }
    leaf oor-current-free-sid-count {
      type uint32;
      description
        "Current Number of Free SIDs";
    }
    leaf oor-yellow-free-sid-threshold {
      type uint32;
      description
        "Threshold for Number of Free SID below which OOR
         Yellow State is reached";
    }
    leaf oor-green-free-sid-threshold {
      type uint32;
      description
        "Threshold for Number of Free SID above which OOR
         Green State is restored";
    }
    leaf oor-green-count {
      type uint32;
      description
        "Number of times Resources Warning or Out of
         Resources state has been cleared";
    }
    leaf oor-yellow-count {
      type uint32;
      description
        "Number of times system went into Resources
         Warning state";
    }
    leaf oor-red-count {
      type uint32;
      description
        "Number of times system went into Out of
         Resources state";
    }
  }

  grouping SRV6-SIDMGR-SUMMARY {
    description
      "SRv6 SID Manager summary";
    container sids-out-of-resource-summary {
      description
        "SID resources global Out of Resource info";
      uses SRV6-OOR-SUMMARY;
    }
    leaf locators-count {
      type uint16;
      description
        "Number of locators";
    }
    leaf oper-locators-count {
      type uint16;
      description
        "Number of operational locators";
    }
    leaf sids-count {
      type uint32;
      description
        "Number of allocated SIDs";
    }
    leaf stale-sids-count {
      type uint32;
      description
        "Number of Stale SIDs";
    }
    leaf maximum-sids-count {
      type uint32;
      description
        "Global Maximum number of SIDs";
    }
    list block-local-sid-oor-summary {
      description
        "SIDs local (per block) Out of Resource info";
      uses SRV6-OOR-SUMMARY;
    }
  }

  grouping SRV6-SIDMGR-USID-WLIB-RANGES {
    description
      "SRv6 SID Manager uSID Wide Local ID Ranges";
    leaf ewlib-start {
      type uint32;
      description
        "Start Value for Explicit Wide Local ID Block";
    }
    leaf configured {
      type boolean;
      description
        "True if start values are configured, otherwise
         default";
    }
  }

  grouping SRV6-SIDMGR-USID-LIB-RANGES {
    description
      "SRv6 SID Manager uSID Local ID Block Ranges";
    leaf lib-start {
      type uint32;
      description
        "Start Value for Local ID Block";
    }
    leaf elib-start {
      type uint32;
      description
        "Start Value for Explicit Local ID Block";
    }
    leaf configured {
      type boolean;
      description
        "True if start values are configured, otherwise
         default";
    }
  }

  grouping MGMT-SRV6-SID-FMT {
    description
      "SRv6 SID Format Info";
    leaf type {
      type Mgmt-srv6-sid-fmt;
      description
        "Format type";
    }
    leaf description {
      type string;
      description
        "Format description";
    }
  }

  grouping SRV6-SIDMGR-SID-FMT-INFO {
    description
      "SRv6 SID Manager Per Format Operational Data";
    container format {
      description
        "SRv6 SID Format";
      uses MGMT-SRV6-SID-FMT;
    }
    container usidlib-ranges {
      description
        "SRv6 uSID Local ID Block Ranges";
      uses SRV6-SIDMGR-USID-LIB-RANGES;
    }
    container usidwlib-ranges {
      description
        "SRv6 uSID Wide Local ID Block Ranges";
      uses SRV6-SIDMGR-USID-WLIB-RANGES;
    }
  }

  grouping MGMT-SRV6-OP-MODE {
    description
      "SRv6 operational mode Info";
    leaf type {
      type Srv6-op-mode;
      description
        "Mode type";
    }
    leaf description {
      type string;
      description
        "Mode description";
    }
  }

  grouping MGMT-SRV6-OP-MODE-INFO {
    description
      "SRv6 SID Manager parameters related to operation
       mode";
    container srv6-operational-mode {
      description
        "SRv6 operational mode";
      uses MGMT-SRV6-OP-MODE;
    }
    leaf srv6-operational-mode-enabled {
      type boolean;
      description
        "SRv6 operational mode enabled";
    }
  }

  grouping SRV6-SIDMGR-PARAMS-SET-OR-PROPAGATE {
    description
      "SRv6 SID Manager parameters value set or
       propagate";
    leaf use-default {
      type boolean;
      description
        "Use default value";
    }
    leaf do-propagate {
      type boolean;
      description
        "Propagate from incoming packet or frame";
    }
    leaf value {
      type uint8;
      description
        "Specific value set";
    }
  }

  grouping SRV6-SIDMGR-PARAMS {
    description
      "SRv6 SID Manager parameters";
    container encap-hop-limit {
      description
        "Encap Hop-limit info";
      uses SRV6-SIDMGR-PARAMS-SET-OR-PROPAGATE;
    }
    container encap-traffic-class {
      description
        "Encap Traffic-class info";
      uses SRV6-SIDMGR-PARAMS-SET-OR-PROPAGATE;
    }
    leaf srv6-enabled {
      type boolean;
      description
        "Is SRv6 enabled?";
    }
    leaf configured-encap-source-address {
      type inet:ipv6-address;
      description
        "Configured Encap Source address";
    }
    leaf default-encap-source-address {
      type inet:ipv6-address;
      description
        "Default Encap Source address";
    }
    leaf is-sid-holdtime-configured {
      type boolean;
      description
        "Is SID Holdtime configured?";
    }
    leaf sid-holdtime-mins-configured {
      type uint32;
      units "minute";
      description
        "Configured SID Holdtime in mins";
    }
    list srv6-operational-mode {
      description
        "SRv6 operational modes";
      uses MGMT-SRV6-OP-MODE-INFO;
    }
    list sid-formats-info {
      description
        "SRv6 SID Formats Information";
      uses SRV6-SIDMGR-SID-FMT-INFO;
    }
  }

  grouping SRV6-SIDMGR-INFO {
    description
      "SRv6 SID Manager info";
    container sid-mgr-params {
      description
        "SID Mgr parameters";
      uses SRV6-SIDMGR-PARAMS;
    }
    container sid-mgr-summary {
      description
        "SID Mgr summary info";
      uses SRV6-SIDMGR-SUMMARY;
    }
    container platform-capabilities {
      description
        "Platform Capabilities";
      uses SRV6-PLATFORM-CAPABILITY;
    }
  }
}
