module Cisco-IOS-XR-um-route-policy-cfg {
  namespace "http://cisco.com/ns/yang/Cisco-IOS-XR-um-route-policy-cfg";
  prefix um-route-policy-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR policy-repository package configuration.
     
     This module contains definitions
     for the following management objects:
       routing-policy: Routing policy configuration
     
     Copyright (c) 2022-2023 by Cisco Systems, Inc.
     All rights reserved.";

  revision 2022-12-10 {
    description
      "EVPN Bandwidth Set inclusion";
    semver:module-version "1.0.0";
  }
  revision 2022-01-17 {
    description
      "Inital release";
  }

  container routing-policy {
    description
      "Routing policy configuration";
    xr:xr-xml-map "rpl_cfg:RoutingPolicy";
    container route-policies {
      description
        "All configured policies";
      xr:xr-xml-map "rpl_cfg:RoutePolicyTable";
      list route-policy {
        key "route-policy-name";
        description
          "Information about an individual policy";
        xr:xr-xml-map "rpl_cfg:RoutePolicy";
        leaf route-policy-name {
          type xr:Cisco-ios-xr-string;
          description
            "Route policy name";
          xr:xr-xml-map "rpl_cfg:RoutePolicyName";
        }
        leaf rpl-route-policy {
          type xr:Rpl-policy;
          mandatory true;
          description
            "policy statements";
          xr:xr-xml-map "rpl_cfg:PolicyAsText";
        }
      }
    }
    container sets {
      description
        "All configured sets";
      xr:xr-xml-map "rpl_cfg:Sets";
      container prefix-sets {
        description
          "Information about Prefix sets";
        xr:xr-xml-map "rpl_cfg:PrefixSetTable";
        list prefix-set {
          key "set-name";
          description
            "Information about an individual set";
          xr:xr-xml-map "rpl_cfg:PrefixSet";
          leaf set-name {
            type xr:Cisco-ios-xr-string;
            description
              "Set name";
            xr:xr-xml-map "rpl_cfg:SetName";
          }
          leaf rpl-prefix-set {
            type xr:Rpl-set;
            mandatory true;
            description
              "prefix statements";
            xr:xr-xml-map "rpl_cfg:PrefixSetAsText";
          }
        }
      }
      container large-community-sets {
        description
          "Information about Large Community sets";
        xr:xr-xml-map "rpl_cfg:LargeCommunitySetTable";
        list large-community-set {
          key "set-name";
          description
            "Information about an individual set";
          xr:xr-xml-map "rpl_cfg:LargeCommunitySet";
          leaf set-name {
            type xr:Cisco-ios-xr-string;
            description
              "Set name";
            xr:xr-xml-map "rpl_cfg:SetName";
          }
          leaf large-community-set-as-text {
            type xr:Rpl-set;
            mandatory true;
            description
              "Large Community Set";
            xr:xr-xml-map "rpl_cfg:LargeCommunitySetAsText";
          }
        }
      }
      container mac-sets {
        description
          "Information about Mac sets";
        xr:xr-xml-map "rpl_cfg:MacSetTable";
        list mac-set {
          key "set-name";
          description
            "Information about an individual set";
          xr:xr-xml-map "rpl_cfg:MacSet";
          leaf set-name {
            type xr:Cisco-ios-xr-string;
            description
              "Set name";
            xr:xr-xml-map "rpl_cfg:SetName";
          }
          leaf mac-set-as-text {
            type xr:Rpl-set;
            mandatory true;
            description
              "Mac Set";
            xr:xr-xml-map "rpl_cfg:MacSetAsText";
          }
        }
      }
      container extended-community-opaque-sets {
        description
          "Information about Opaque sets";
        xr:xr-xml-map "rpl_cfg:ExtendedCommunityOpaqueSetTable";
        list extended-community-opaque-set {
          key "set-name";
          description
            "Information about an individual set";
          xr:xr-xml-map "rpl_cfg:ExtendedCommunityOpaqueSet";
          leaf set-name {
            type xr:Cisco-ios-xr-string;
            description
              "Set name";
            xr:xr-xml-map "rpl_cfg:SetName";
          }
          leaf rpl-extended-community-opaque-set {
            type xr:Rpl-set;
            mandatory true;
            description
              "Extended Community Opaque Set";
            xr:xr-xml-map "rpl_cfg:ExtendedCommunityOpaqueSetAsText";
          }
        }
      }
      container ospf-area-sets {
        description
          "Information about OSPF Area sets";
        xr:xr-xml-map "rpl_cfg:OSPFAreaSetTable";
        list ospf-area-set {
          key "set-name";
          description
            "Information about an individual OSPF area set.
             Usage: OSPF area set allows to define named
             set of area numbers        which can be
             referenced in the route-policy. Area sets
             may be used during redistribution of the ospf
             protocol.  Example: ospf-area-set EXAMPLE
             1,
             192.168.1.255
             end-set
             Syntax: OSPF area number can be entered as 32
             bit number or in          the ip address
             format. See example.
             Semantic: Area numbers listed in the set will
             be searched for             a match. In the
             example these are areas 1 and
             192.168.1.255.                                ";
          xr:xr-xml-map "rpl_cfg:OSPFAreaSet";
          leaf set-name {
            type xr:Cisco-ios-xr-string;
            description
              "Set name";
            xr:xr-xml-map "rpl_cfg:SetName";
          }
          leaf rplospf-area-set {
            type xr:Rpl-set;
            mandatory true;
            description
              "OSPF Area Set";
            xr:xr-xml-map "rpl_cfg:OSPFAreaSetAsText";
          }
        }
      }
      container extended-community-cost-sets {
        description
          "Information about Cost sets";
        xr:xr-xml-map "rpl_cfg:ExtendedCommunityCostSetTable";
        list extended-community-cost-set {
          key "set-name";
          description
            "Information about an individual set";
          xr:xr-xml-map "rpl_cfg:ExtendedCommunityCostSet";
          leaf set-name {
            type xr:Cisco-ios-xr-string;
            description
              "Set name";
            xr:xr-xml-map "rpl_cfg:SetName";
          }
          leaf rpl-extended-community-cost-set {
            type xr:Rpl-set;
            mandatory true;
            description
              "Extended Community Cost Set";
            xr:xr-xml-map "rpl_cfg:ExtendedCommunityCostSetAsText";
          }
        }
      }
      container extended-community-soo-sets {
        description
          "Information about SOO sets";
        xr:xr-xml-map "rpl_cfg:ExtendedCommunitySOOSetTable";
        list extended-community-soo-set {
          key "set-name";
          description
            "Information about an individual set";
          xr:xr-xml-map "rpl_cfg:ExtendedCommunitySOOSet";
          leaf set-name {
            type xr:Cisco-ios-xr-string;
            description
              "Set name";
            xr:xr-xml-map "rpl_cfg:SetName";
          }
          leaf rpl-extended-community-soo-set {
            type xr:Rpl-set;
            mandatory true;
            description
              "Extended Community SOO Set";
            xr:xr-xml-map "rpl_cfg:ExtendedCommunitySOOSetAsText";
          }
        }
      }
      container esi-sets {
        description
          "Information about Esi sets";
        xr:xr-xml-map "rpl_cfg:EsiSetTable";
        list esi-set {
          key "set-name";
          description
            "Information about an individual set";
          xr:xr-xml-map "rpl_cfg:EsiSet";
          leaf set-name {
            type xr:Cisco-ios-xr-string;
            description
              "Set name";
            xr:xr-xml-map "rpl_cfg:SetName";
          }
          leaf esi-set-as-text {
            type xr:Rpl-set;
            mandatory true;
            description
              "Esi Set";
            xr:xr-xml-map "rpl_cfg:EsiSetAsText";
          }
        }
      }
      container extended-community-seg-nh-sets {
        description
          "Information about SegNH sets";
        xr:xr-xml-map "rpl_cfg:ExtendedCommunitySegNHSetTable";
        list extended-community-seg-nh-set {
          key "set-name";
          description
            "Information about an individual set";
          xr:xr-xml-map "rpl_cfg:ExtendedCommunitySegNHSet";
          leaf set-name {
            type xr:Cisco-ios-xr-string;
            description
              "Set name";
            xr:xr-xml-map "rpl_cfg:SetName";
          }
          leaf rpl-extended-community-seg-nh-set {
            type xr:Rpl-set;
            mandatory true;
            description
              "Extended Community SegNH Set";
            xr:xr-xml-map "rpl_cfg:ExtendedCommunitySegNHSetAsText";
          }
        }
      }
      container rd-sets {
        description
          "Information about RD sets";
        xr:xr-xml-map "rpl_cfg:RDSetTable";
        list rd-set {
          key "set-name";
          description
            "Information about an individual set";
          xr:xr-xml-map "rpl_cfg:RDSet";
          leaf set-name {
            type xr:Cisco-ios-xr-string;
            description
              "Set name";
            xr:xr-xml-map "rpl_cfg:SetName";
          }
          leaf rplrd-set {
            type xr:Rpl-set;
            mandatory true;
            description
              "RD Set";
            xr:xr-xml-map "rpl_cfg:RDSetAsText";
          }
        }
      }
      container policy-global-set-table {
        description
          "Information about PolicyGlobal sets";
        xr:xr-xml-map "rpl_cfg:PolicyGlobalSetTable";
        leaf policy-global-set {
          type xr:Rpl-set;
          description
            "Information about an individual set";
          xr:xr-xml-map "rpl_cfg:PolicyGlobalSet";
        }
      }
      container extended-community-bandwidth-sets {
        description
          "Information about Bandwidth sets";
        xr:xr-xml-map "rpl_cfg:ExtendedCommunityBandwidthSetTable";
        list extended-community-bandwidth-set {
          key "set-name";
          description
            "Information about an individual set";
          xr:xr-xml-map "rpl_cfg:ExtendedCommunityBandwidthSet";
          leaf set-name {
            type xr:Cisco-ios-xr-string;
            description
              "Set name";
            xr:xr-xml-map "rpl_cfg:SetName";
          }
          leaf rpl-extended-community-bandwidth-set {
            type xr:Rpl-set;
            mandatory true;
            description
              "Extended Community Bandwidth Set";
            xr:xr-xml-map "rpl_cfg:ExtendedCommunityBandwidthSetAsText";
          }
        }
      }
      container community-sets {
        description
          "Information about Community sets";
        xr:xr-xml-map "rpl_cfg:CommunitySetTable";
        list community-set {
          key "set-name";
          description
            "Information about an individual set";
          xr:xr-xml-map "rpl_cfg:CommunitySet";
          leaf set-name {
            type xr:Cisco-ios-xr-string;
            description
              "Set name";
            xr:xr-xml-map "rpl_cfg:SetName";
          }
          leaf rpl-community-set {
            type xr:Rpl-set;
            mandatory true;
            description
              "Community Set";
            xr:xr-xml-map "rpl_cfg:CommunitySetAsText";
          }
        }
      }
      container as-path-sets {
        description
          "Information about AS Path sets";
        xr:xr-xml-map "rpl_cfg:ASPathSetTable";
        list as-path-set {
          key "set-name";
          description
            "Information about an individual set";
          xr:xr-xml-map "rpl_cfg:ASPathSet";
          leaf set-name {
            type xr:Cisco-ios-xr-string;
            description
              "Set name";
            xr:xr-xml-map "rpl_cfg:SetName";
          }
          leaf rplas-path-set {
            type xr:Rpl-set;
            mandatory true;
            description
              "ASPath Set";
            xr:xr-xml-map "rpl_cfg:ASPathSetAsText";
          }
        }
      }
      container tag-sets {
        description
          "Information about Tag sets";
        xr:xr-xml-map "rpl_cfg:TagSetTable";
        list tag-set {
          key "set-name";
          description
            "Information about an individual set";
          xr:xr-xml-map "rpl_cfg:TagSet";
          leaf set-name {
            type xr:Cisco-ios-xr-string;
            description
              "Set name";
            xr:xr-xml-map "rpl_cfg:SetName";
          }
          leaf rpl-tag-set {
            type xr:Rpl-set;
            mandatory true;
            description
              "Tag Set";
            xr:xr-xml-map "rpl_cfg:TagSetAsText";
          }
        }
      }
      container etag-sets {
        description
          "Information about Etag sets";
        xr:xr-xml-map "rpl_cfg:EtagSetTable";
        list etag-set {
          key "set-name";
          description
            "Information about an individual set";
          xr:xr-xml-map "rpl_cfg:EtagSet";
          leaf set-name {
            type xr:Cisco-ios-xr-string;
            description
              "Set name";
            xr:xr-xml-map "rpl_cfg:SetName";
          }
          leaf etag-set-as-text {
            type xr:Rpl-set;
            mandatory true;
            description
              "Etag Set";
            xr:xr-xml-map "rpl_cfg:EtagSetAsText";
          }
        }
      }
      container extended-community-rt-sets {
        description
          "Information about RT sets";
        xr:xr-xml-map "rpl_cfg:ExtendedCommunityRTSetTable";
        list extended-community-rt-set {
          key "set-name";
          description
            "Information about an individual set";
          xr:xr-xml-map "rpl_cfg:ExtendedCommunityRTSet";
          leaf set-name {
            type xr:Cisco-ios-xr-string;
            description
              "Set name";
            xr:xr-xml-map "rpl_cfg:SetName";
          }
          leaf rpl-extended-community-rt-set {
            type xr:Rpl-set;
            mandatory true;
            description
              "Extended Community RT Set";
            xr:xr-xml-map "rpl_cfg:ExtendedCommunityRTSetAsText";
          }
        }
      }
      container extended-community-evpn-bandwidth-sets {
        description
          "Information about EVPN Link Bandwidth sets";
        xr:xr-xml-map "rpl_cfg:ExtendedCommunityEVPNBandwidthSetTable";
        list extended-community-evpn-bandwidth-set {
          key "set-name";
          description
            "Information about an individual set";
          xr:xr-xml-map "rpl_cfg:ExtendedCommunityEVPNBandwidthSet";
          leaf set-name {
            type xr:Cisco-ios-xr-string;
            description
              "Set name";
            xr:xr-xml-map "rpl_cfg:SetName";
          }
          leaf rpl-extended-community-evpn-bandwidth-set {
            type xr:Rpl-set;
            mandatory true;
            description
              "Extended Community EVPN Link Bandwidth Set";
            xr:xr-xml-map "rpl_cfg:ExtendedCommunityEVPNBandwidthSetAsText";
          }
        }
      }
    }
    container limits {
      description
        "Limits for Routing Policy";
      xr:xr-xml-map "rpl_cfg:Limits";
      leaf maximum-lines-of-policy {
        type int32;
        default "131072";
        description
          "Maximum number of lines of policy configuration
           that may be configured in total";
        xr:xr-xml-map "rpl_cfg:MaximumLinesOfPolicy";
      }
      leaf maximum-number-of-policies {
        type int32;
        default "5000";
        description
          "Maximum number of policies that may be
           configured";
        xr:xr-xml-map "rpl_cfg:MaximumNumberOfPolicies";
      }
    }
    leaf set-exit-as-abort {
      type empty;
      description
        "Set exit under RPL config to abort";
      xr:xr-xml-map "rpl_cfg:SetExitAsAbort";
      xr:xr-cli-map "rpl set-exit-as-abort ";
    }
    leaf editor {
      type string;
      description
        "'emacs' or 'vim' or 'nano'";
      xr:xr-xml-map "rpl_cfg:Editor";
      xr:xr-cli-map "rpl editor (emacs)|(nano)|(vim) ";
    }
  }
}
