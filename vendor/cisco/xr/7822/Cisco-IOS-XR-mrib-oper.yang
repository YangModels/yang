module Cisco-IOS-XR-mrib-oper {
  namespace "http://cisco.com/ns/yang/Cisco-IOS-XR-mrib-oper";
  prefix mrib-oper;

  import ietf-inet-types {
    prefix inet;
  }
  import Cisco-IOS-XR-types {
    prefix xr;
  }
  import cisco-semver {
    prefix semver;
  }
  include Cisco-IOS-XR-mrib-oper-sub1 {
    revision-date 2022-04-20;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR mrib package operational data.
     
     This module contains definitions
     for the following management objects:
       ipv6-mrib: IPv6 MRIB operational data
       mrib: MRIB operational data
     
     Copyright (c) 2013-2022 by Cisco Systems, Inc.
     All rights reserved.";

  revision 2022-04-20 {
    description
      "Getting rid of default context path
       2022-02-09
         Increase in interface name length";
    semver:module-version "3.0.0";
  }
  revision 2021-08-27 {
    description
      "non-backward compatible edit in leaf parent-if-handle. type changed from uint32 to type xr:Hex-integer";
    semver:module-version "2.0.0";
  }
  revision 2020-10-29 {
    description
      "Adding RPFID for PIM-SM design
       2020-10-11
           Backward compatible addition in leaf table-mdt-name-tree-sid,table-tree-sid-turnaround and reference-count.";
    semver:module-version "1.1.0";
  }
  revision 2020-02-13 {
    description
      "Fixing CSCvr71562.";
    semver:module-version "1.0.0";
  }
  revision 2019-08-27 {
    description
      "Providing MRIB information.";
  }
  revision 2019-04-05 {
    description
      "Establish semantic version baseline.";
  }
  revision 2015-11-09 {
    description
      "IOS XR 6.0 revision.";
  }

  grouping PROCESS {
    description
      "Common node of active, standby";
    container process {
      description
        "Process";
      container registration-database-entries {
        description
          "MRIB Registration Database Table";
        list registration-database-entry {
          key "vrf-name entry-type next-hop-address";
          description
            "MRIB Registration Database Entry Information";
          leaf vrf-name {
            type xr:Cisco-ios-xr-string;
            description
              "VRF Name";
          }
          leaf entry-type {
            type uint32;
            description
              "Entry Type";
          }
          leaf next-hop-address {
            type xr:Cisco-ios-xr-string;
            description
              "Next-Hop Address";
          }
          uses MRIB-REGDB-BAG;
        }
      }
      container cofo {
        description
          "Collapsed forwarding Information";
        container encap-entries {
          description
            "EncapID information exchanged for collapsed
             forwarding";
          list encap-entry {
            key "encap-id";
            description
              "EncapID information exchanged for collapsed
               forwarding";
            leaf encap-id {
              type uint32;
              description
                "Encap Identifier";
            }
            uses MRIB-COFO-ENCAP-BAG;
          }
        }
        container ip-multicast-infos {
          description
            "IP multicast information exchanged for
             collapsed forwarding";
          list ip-multicast-info {
            key "source group";
            description
              "IP multicast information exchanged for
               collapsed forwarding";
            leaf source {
              type inet:ip-address-no-zone;
              description
                "Source Address";
            }
            leaf group {
              type inet:ip-prefix;
              description
                "Group Address Prefix";
            }
            uses MRIB-COFO-BAG;
          }
        }
        container lsm-infos {
          description
            "LSM information exchanged for collapsed
             forwarding";
          list lsm-info {
            key "fec";
            description
              "LSM information exchanged for collapsed
               forwarding";
            leaf fec {
              type xr:Cisco-ios-xr-string {
                length "1..255";
              }
              description
                "The FEC of the local label for which
                 node-set or FGID data is being exchanged";
            }
            uses LMRIB-COFO-BAG;
          }
        }
        container summary {
          description
            "Summary of statistics for collapsed forwarding";
          uses MRIB-COFO-SUMMARY-BAG;
        }
      }
      container nsr-ends {
        description
          "NSR End Table";
        list nsr-end {
          key "index";
          description
            "NSR End";
          leaf index {
            type uint32;
            description
              "Index";
          }
          uses MRIB-NSR-END-INFO;
        }
      }
      container mrib-bvi-interfaces {
        description
          "MRIB BVI interface mapping";
        list mrib-bvi-interface {
          key "interface-name";
          description
            "BVI Interface Handle";
          leaf interface-name {
            type xr:Interface-name;
            description
              "Interface Name";
          }
          uses MRIB-BVI-INTERFACE-BAG;
        }
      }
      container mrib-bvi-routes {
        description
          "MRIB BVI route table";
        list mrib-bvi-route {
          key "interface-name source-address group-address prefix-length";
          description
            "MRIB BVI route entry";
          leaf interface-name {
            type xr:Interface-name;
            description
              "Interface Name";
          }
          leaf source-address {
            type inet:ip-address-no-zone;
            description
              "Source Address";
          }
          leaf group-address {
            type inet:ip-address-no-zone;
            description
              "Group Address";
          }
          leaf prefix-length {
            type uint32;
            description
              "Prefix Length";
          }
          uses MRIB-BVI-ROUTE-BAG;
        }
      }
      container evpn {
        description
          "EVPN information";
        container bucket-entries {
          description
            "EVPN Bucket DataBase Table information";
          list bucket-entry {
            description
              "Mrib EVPN Bucket Database Entry";
            leaf bucket-id {
              type uint32;
              description
                "Bucket Identifier";
            }
            leaf parent-if-handle {
              type xr:Hex-integer;
              description
                "Parent Handle";
            }
            uses MRIB-EVPN-BKT-BAG;
          }
        }
      }
      container checkpoint-statistics {
        description
          "Checkpoint Statistics";
        uses MRIB-CHKPT-STATS;
      }
      container mdt-interfaces {
        description
          "MRIB IIR interface DB";
        list mdt-interface {
          key "interface-name";
          description
            "Interface handle";
          leaf interface-name {
            type xr:Interface-name;
            description
              "Interface Name";
          }
          uses MRIB-MDT-IFH-BAG;
        }
      }
      container clients {
        description
          "MRIB Client Table";
        list client {
          key "client-name instance-name";
          description
            "MRIB Client DB Entry Information";
          leaf client-name {
            type xr:Cisco-ios-xr-string;
            description
              "Client Name";
          }
          leaf instance-name {
            type xr:Cisco-ios-xr-string;
            description
              "Instance Name";
          }
          uses MRIB-CLIENT-BAG;
        }
      }
      container mpls-forwardings {
        description
          "MRIB Label Table";
        list mpls-forwarding {
          key "label";
          description
            "MRIB Label DB Information";
          leaf label {
            type uint32;
            description
              "Label";
          }
          uses MRIB-MPLS-FORWARDING-BAG;
        }
      }
      container nsf {
        description
          "NSF Information";
        uses MRIB-NSF-BAG;
      }
      container rpf-identifiers {
        description
          "RPF Identifier Table";
        list rpf-identifier {
          key "source-pe-address mrib-allocated";
          description
            "RPF Identifier";
          leaf source-pe-address {
            type inet:ipv4-address-no-zone;
            description
              "Source PE Address";
          }
          leaf mrib-allocated {
            type boolean;
            description
              "MRIB Allocated";
          }
          uses MRIB-RPFID-SPE-INFO;
        }
      }
      container client-filters {
        description
          "MRIB Client Filter Table";
        list client-filter {
          key "client-name instance-name";
          description
            "MRIB Client Filter DB Entry Information";
          leaf client-name {
            type xr:Cisco-ios-xr-string;
            description
              "Client Name";
          }
          leaf instance-name {
            type xr:Cisco-ios-xr-string;
            description
              "Instance Name";
          }
          uses MRIB-FILTER-BAG;
        }
      }
      container encap-identifiers {
        description
          "Encap Identifier Table";
        list encap-identifier {
          key "encap-id";
          description
            "Encap Identifier";
          leaf encap-id {
            type uint32;
            description
              "Encap Identifier";
          }
          uses MRIB-ENCAPID-BAG;
        }
      }
    }
  }

  grouping ACTIVE {
    description
      "Common node of mrib, ipv6-mrib";
    container active {
      description
        "Active Process";
      uses PROCESS;
      uses DATABASE-TABLE;
    }
  }

  grouping DATABASE-TABLE {
    description
      "Common node of active, standby";
    container databases {
      description
        "Database Table";
      list database {
        key "database-name";
        description
          "MRIB Table Information";
        container route-collapse-ipc-tlc {
          description
            "Route Collapse IPC TLC Information";
          uses MRIB-RC-IPC-BAG;
        }
        container gw-summaries {
          description
            "MRIB AMT Gateway Summary Information";
          list gw-summary {
            key "gateway-address gateway-port";
            description
              "MRIB AMT Gateway DB Entry";
            leaf gateway-address {
              type inet:ip-address-no-zone;
              description
                "Gateway Address";
            }
            leaf gateway-port {
              type uint32;
              description
                "Gateway Port";
            }
            uses MRIB-AMT-GW-SUMMARY-BAG;
          }
        }
        container route-collapse-ipc {
          description
            "MRIB Route Collapse IPC Core-egress-node
             Information";
          uses MRIB-RC-IPC-BAG;
        }
        container mplste-backups {
          description
            "MRIB MPLS TE Backup Database Information";
          list mplste-backup {
            key "interface-name";
            description
              "MRIB MPLS TE Backup Database Information";
            leaf interface-name {
              type xr:Interface-name;
              description
                "Interface Name";
            }
            uses MRIB-MPLS-BKUP-BAG;
          }
        }
        container routes {
          description
            "The set of MRIB RouteDB operations";
          list route {
            key "source-address group-address prefix-length";
            description
              "MRIB Route DB Entry Information";
            leaf source-address {
              type inet:ip-address-no-zone;
              description
                "Source Address";
            }
            leaf group-address {
              type inet:ip-address-no-zone;
              description
                "Group Address";
            }
            leaf prefix-length {
              type uint32;
              description
                "Prefix Length";
            }
            uses MRIB-ROUTE-BAG;
          }
        }
        container table-line-card {
          description
            "MRIB Table-LineCard database";
          uses MRIB-TLC-BAG;
        }
        container frr-summary {
          description
            "MRIB FRR DB Summary Information";
          uses MRIB-MPLS-FRR-SUMMARY-BAG;
        }
        container iir-interfaces {
          description
            "MRIB IIR interface DB";
          list iir-interface {
            key "interface-name";
            description
              "MRIB Interface information";
            leaf interface-name {
              type xr:Interface-name;
              description
                "Interface Name";
            }
            uses MRIB-IIR-INTF-BAG;
          }
        }
        container amt-gateway-dbs {
          description
            "The set of AMT Gateway DataBase Table
             information";
          list amt-gateway-db {
            key "gateway-address gateway-port";
            description
              "MRIB AMT Gateway DB Entry";
            leaf gateway-address {
              type inet:ip-address-no-zone;
              description
                "Gateway Address";
            }
            leaf gateway-port {
              type uint32;
              description
                "Gateway Port";
            }
            uses MRIB-AMT-GW-BAG;
          }
        }
        container route-outgoing-interfaces {
          description
            "MRIB RouteDB Outgoing Interface Table ";
          list route-outgoing-interface {
            key "source-address group-address prefix-length";
            description
              "MRIB Route DB Outgoing Interface Entry
               Information";
            leaf source-address {
              type inet:ip-address-no-zone;
              description
                "Source Address";
            }
            leaf group-address {
              type inet:ip-address-no-zone;
              description
                "Group Address";
            }
            leaf prefix-length {
              type uint32;
              description
                "Prefix Length";
            }
            uses MRIB-ROUTE-OLE-BAG;
          }
        }
        container gw-expireds {
          description
            "MRIB AMT Gateway DB Expired Information";
          list gw-expired {
            key "gateway-address gateway-port";
            description
              "MRIB AMT Gateway Expired Entry";
            leaf gateway-address {
              type inet:ip-address-no-zone;
              description
                "Gateway Address";
            }
            leaf gateway-port {
              type uint32;
              description
                "Gateway Port";
            }
            uses MRIB-AMT-GW-EX-BAG;
          }
        }
        container remote-table-line-card {
          description
            "Show the linked remote entry";
          uses MRIB-TLC-BAG;
        }
        container amt-routedb-summaries {
          description
            "MRIB AMT RouteDB Summary Information";
          list amt-routedb-summary {
            key "source-address group-address";
            description
              "MRIB AMT Route Summary Entry";
            leaf source-address {
              type inet:ip-address-no-zone;
              description
                "Source Address";
            }
            leaf group-address {
              type inet:ip-address-no-zone;
              description
                "Group Address";
            }
            uses MRIB-AMT-ROUTE-SUMMARY-BAG;
          }
        }
        container route-collapses {
          description
            "MRIB Route Collapse database";
          list route-collapse {
            key "type group-address";
            description
              "Route Collapse Information";
            leaf type {
              type xr:Cisco-ios-xr-string;
              description
                "Type";
            }
            leaf group-address {
              type inet:ip-address-no-zone;
              description
                "Input MDT grp or prev group";
            }
            uses MRIB-RC-MDT-BAG;
          }
        }
        container label-info {
          description
            "MRIB Label Table Information";
          uses MRIB-LABEL-TABLE-INFO-BAG;
        }
        container frrs {
          description
            "FRR Table";
          list frr {
            key "start-label";
            description
              "MRIB FRR DB Information";
            leaf start-label {
              type uint32;
              description
                "Start Label";
            }
            uses MRIB-MPLS-FRR-BAG;
          }
        }
        container amt-routedb-expireds {
          description
            "MRIB AMT Route Expired Information";
          list amt-routedb-expired {
            key "source-address group-address gw-address port";
            description
              "MRIB AMT Route Expired Entry";
            leaf source-address {
              type inet:ip-address-no-zone;
              description
                "Source Address";
            }
            leaf group-address {
              type inet:ip-address-no-zone;
              description
                "Group Address";
            }
            leaf gw-address {
              type inet:ip-address-no-zone;
              description
                "GW Address";
            }
            leaf port {
              type uint32;
              description
                "Prefix Length";
            }
            uses MRIB-AMT-ROUTE-EX-BAG;
          }
        }
        container table-information {
          description
            "MRIB VRF table information";
          uses MRIB-TABLE-INFO-BAG;
        }
        container summary {
          description
            "MRIB RouteDB Summary Information";
          uses MRIB-DB-SUMM-BAG;
        }
        container amt-routes {
          description
            "The set of AMT Route table information";
          list amt-route {
            key "source-address group-address prefix-length";
            description
              "MRIB AMT Route DB Entry Information";
            leaf source-address {
              type inet:ip-address-no-zone;
              description
                "Source Address";
            }
            leaf group-address {
              type inet:ip-address-no-zone;
              description
                "Group Address";
            }
            leaf prefix-length {
              type uint32;
              description
                "Prefix Length";
            }
            uses MRIB-AMT-ROUTE-BAG;
          }
        }
        leaf database-name {
          type xr:Cisco-ios-xr-string;
          description
            "Database Name";
        }
      }
    }
  }

  grouping STANDBY {
    description
      "Common node of mrib, ipv6-mrib";
    container standby {
      description
        "Standby Process";
      uses PROCESS;
      uses DATABASE-TABLE;
    }
  }

  container ipv6-mrib {
    config false;
    description
      "IPv6 MRIB operational data";
    uses ACTIVE;
    uses STANDBY;
  }
  container mrib {
    config false;
    description
      "MRIB operational data";
    uses ACTIVE;
    uses STANDBY;
  }
}
