submodule Cisco-IOS-XR-snmp-agent-oper-sub1 {

  belongs-to Cisco-IOS-XR-snmp-agent-oper {
    prefix Cisco-IOS-XR-snmp-agent-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR snmp-agent package operational data.

     Copyright (c) 2013-2015 by Cisco Systems, Inc.
     All rights reserved.";

  revision "2015-01-07" {
    description
      "IOS XR 5.3.1 revision.";
  }

  typedef Snmp-corr-vbind-match {
    type enumeration {
      enum index {
        value 0;
        description "Match regexp to varbind index";
      }
      enum value {
        value 1;
        description "Match regexp to varbind value";
      }
    }
    description "Snmp corr vbind match";
  }
  typedef Snmp-corr-rule-state {
    type enumeration {
      enum rule-unapplied {
        value 0;
        description "Rule is in Unapplied state";
      }
      enum rule-applied {
        value 1;
        description "Rule is Applied to specified hosts";
      }
      enum rule-applied-all {
        value 2;
        description "Rule is Applied to all of router";
      }
    }
    description "Snmp corr rule state";
  }

  grouping SNMP-CORR-VBIND {
    description "Varbind";
    leaf oid {
      xr:xr-xml-map "snmp_corr:OID";
      type string;
      description "OID of the varbind";
    }
    leaf value {
      xr:xr-xml-map "snmp_corr:Value";
      type string;
      description "Value of the varbind";
    }
  }

  grouping SNMP-CORR-TRAP-BAG {
    description "Trap Information";
    leaf oid {
      xr:xr-xml-map "snmp_corr:OID";
      type string;
      description "Object ID";
    }
    leaf relative-timestamp {
      xr:xr-xml-map "snmp_corr:RelativeTimestamp";
      type uint32;
      units "second";
      description "Number of hsecs elapsed since snmpd was started";
    }
    leaf timestamp {
      xr:xr-xml-map "snmp_corr:Timestamp";
      type uint64;
      units "millisecond";
      description
        "Time when the trap was generated. It is
        expressed in number of milliseconds since 00:00
        :00 UTC, January 1, 1970";
    }

    list var-bind {
      description "VarBinds on the trap";
      uses SNMP-CORR-VBIND;
    }
  }

  grouping SNMP-CORR-TRAP-BUFFER-BAG {
    description "Trap Buffer Record";

    container trap-info {
      description "Correlated trap information";
      uses SNMP-CORR-TRAP-BAG;
    }
    leaf correlation-id {
      xr:xr-xml-map "snmp_corr:CorrelationID";
      type uint32;
      description "Correlation ID";
    }
    leaf is-root-cause {
      xr:xr-xml-map "snmp_corr:IsRootcause";
      type boolean;
      description "True if this is the rootcause";
    }
    leaf rule-name {
      xr:xr-xml-map "snmp_corr:RuleName";
      type string;
      description "Correlation rule name";
    }
  }

  grouping SNMP-CORR-RULESET-DETAIL-BAG {
    description "Correlation Ruleset detail information";
    leaf rule-set-name-xr {
      xr:xr-xml-map "snmp_corr:rule-set-name-xr";
      type string;
      description "Ruleset Name";
    }

    list rules {
      description "Rules contained in a ruleset";
      uses SNMP-CORR-RULE-SUMMARY-BAG;
    }
  }

  grouping SNMP-CORR-BUFFER-INFO-BAG {
    description "Correlator buffer usage information";
    leaf current-size {
      xr:xr-xml-map "snmp_corr:CurrentSize";
      type uint32;
      description "Current buffer usage";
    }
    leaf configured-size {
      xr:xr-xml-map "snmp_corr:ConfiguredSize";
      type uint32;
      description "Configured buffer size";
    }
  }

  grouping SNMP-CORR-HOST {
    description "Host Definition";
    leaf ip-address {
      xr:xr-xml-map "snmp_corr:IPAddress";
      type string;
      description "IP address of the host";
    }
    leaf port {
      xr:xr-xml-map "snmp_corr:Port";
      type uint16;
      description "Port of the host";
    }
  }

  grouping SNMP-CORR-VBIND-MATCH {
    description "Varbind Match Parameters";
    leaf oid {
      xr:xr-xml-map "snmp_corr:OID";
      type string;
      description "OID of the varbind";
    }
    leaf match-type {
      xr:xr-xml-map "snmp_corr:MatchType";
      type Snmp-corr-vbind-match;
      description "Varbind match type";
    }
    leaf reg-exp {
      xr:xr-xml-map "snmp_corr:RegExp";
      type string;
      description "Regular expression to match";
    }
  }

  grouping SNMP-CORR-TRAP-MATCH {
    description "Trap Match Definition";
    leaf oid {
      xr:xr-xml-map "snmp_corr:OID";
      type string;
      description "OID of the trap";
    }

    list var-bind {
      description "VarBinds of the trap";
      uses SNMP-CORR-VBIND-MATCH;
    }
  }

  grouping SNMP-CORR-RULE-SUMMARY-BAG {
    description "Correlation Rule summary information";
    leaf rule-name {
      xr:xr-xml-map "snmp_corr:RuleName";
      type string;
      description "Correlation Rule Name";
    }
    leaf rule-state {
      xr:xr-xml-map "snmp_corr:RuleState";
      type Snmp-corr-rule-state;
      description
        "Applied state of the rule It could be not
        applied, applied or applied to all";
    }
    leaf buffered-traps-count {
      xr:xr-xml-map "snmp_corr:BufferedTrapsCount";
      type uint32;
      description
        "Number of buffered traps correlated to this rule";
    }
  }

  grouping SNMP-CORR-RULE-DETAIL-BAG {
    description "Correlation Rule detail information";

    container rule-summary {
      description "Rule summary, name, etc";
      uses SNMP-CORR-RULE-SUMMARY-BAG;
    }

    container root-cause {
      description
        "OID/VarBinds defining the rootcause match
        conditions.";
      uses SNMP-CORR-TRAP-MATCH;
    }
    leaf timeout {
      xr:xr-xml-map "snmp_corr:Timeout";
      type uint32;
      description
        "Time window (in ms) for which root/all messages
        are kept in correlater before sending them to
        hosts";
    }

    list non-rootcaus {
      description
        "OIDs/VarBinds defining the nonrootcause match
        conditions.";
      uses SNMP-CORR-TRAP-MATCH;
    }

    list apply-host {
      description "Hosts (IP/port) to which the rule is applied";
      uses SNMP-CORR-HOST;
    }
  }
}
