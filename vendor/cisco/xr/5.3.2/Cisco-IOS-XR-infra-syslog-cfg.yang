module Cisco-IOS-XR-infra-syslog-cfg {

  /*** NAMESPACE / PREFIX DEFINITION ***/

  namespace "http://cisco.com/ns/yang/Cisco-IOS-XR-infra-syslog-cfg";


  prefix "infra-syslog-cfg";

  /*** LINKAGE (IMPORTS / INCLUDES) ***/

  import ietf-inet-types { prefix "inet"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR infra-syslog package configuration.

     This module contains definitions
     for the following management objects:
       syslog-service: Syslog Timestamp Services
       syslog: syslog

     Copyright (c) 2013-2015 by Cisco Systems, Inc.
     All rights reserved.";

  revision "2015-05-27" {
    description
      "Modified schema for logging discriminators.";
  }

  revision "2015-01-07" {
    description
      "IOS XR 5.3.1 revision.";
  }

  typedef Facility {
    type enumeration {
      enum kern {
        value 0;
        description "Kernel Facility";
      }
      enum user {
        value 8;
        description "User Facility";
      }
      enum mail {
        value 16;
        description "Mail Facility";
      }
      enum daemon {
        value 24;
        description "Daemon Facility";
      }
      enum auth {
        value 32;
        description "Auth Facility";
      }
      enum syslog {
        value 40;
        description "Syslog Facility";
      }
      enum lpr {
        value 48;
        description "Lpr Facility";
      }
      enum news {
        value 56;
        description "News Facility";
      }
      enum uucp {
        value 64;
        description "Uucp Facility";
      }
      enum cron {
        value 72;
        description "Cron Facility";
      }
      enum authpriv {
        value 80;
        description "Authpriv Facility";
      }
      enum ftp {
        value 88;
        description "Ftp Facility";
      }
      enum local0 {
        value 128;
        description "Local0 Facility";
      }
      enum local1 {
        value 136;
        description "Local1 Facility";
      }
      enum local2 {
        value 144;
        description "Local2 Facility";
      }
      enum local3 {
        value 152;
        description "Local3 Facility";
      }
      enum local4 {
        value 160;
        description "Local4 Facility";
      }
      enum local5 {
        value 168;
        description "Local5 Facility";
      }
      enum local6 {
        value 176;
        description "Local6 Facility";
      }
      enum local7 {
        value 184;
        description "Local7 Facility";
      }
      enum sys9 {
        value 192;
        description "System9 Facility";
      }
      enum sys10 {
        value 200;
        description "System10 Facility";
      }
      enum sys11 {
        value 208;
        description "System11 Facility";
      }
      enum sys12 {
        value 216;
        description "System12 Facility";
      }
      enum sys13 {
        value 224;
        description "System13 Facility";
      }
      enum sys14 {
        value 232;
        description "System14 Facility";
      }
    }
    description "Facility";
  }
  typedef Logging-levels {
    type enumeration {
      enum emergency {
        value 0;
        description "Emergency Level Msg";
      }
      enum alert {
        value 1;
        description "Alert Level Msg";
      }
      enum critical {
        value 2;
        description "Critical Level Msg";
      }
      enum error {
        value 3;
        description "Error Level Msg";
      }
      enum warning {
        value 4;
        description "Warning Level Msg";
      }
      enum notice {
        value 5;
        description "Notification Level Msg";
      }
      enum info {
        value 6;
        description "Informational Level Msg";
      }
      enum debug {
        value 7;
        description "Debugging Level Msg";
      }
      enum disable {
        value 15;
        description "Disable logging";
      }
    }
    description "Logging levels";
  }
  typedef Time-info {
    type enumeration {
      enum disable {
        value 0;
        description "Exclude";
      }
      enum enable {
        value 1;
        description "Include";
      }
    }
    description "Time info";
  }
  typedef Log-message-severity {
    type enumeration {
      enum emergency {
        value 0;
        description
          "System is unusable                (severity=0)";
      }
      enum alert {
        value 1;
        description
          "Immediate action needed           (severity=1)";
      }
      enum critical {
        value 2;
        description
          "Critical conditions               (severity=2)";
      }
      enum error {
        value 3;
        description
          "Error conditions                  (severity=3)";
      }
      enum warning {
        value 4;
        description
          "Warning conditions                (severity=4)";
      }
      enum notice {
        value 5;
        description
          "Normal but significant conditions (severity=5)";
      }
      enum informational {
        value 6;
        description
          "Informational messages            (severity=6)";
      }
      enum debug {
        value 7;
        description
          "Debugging messages                (severity=7)";
      }
    }
    description "Log message severity";
  }
  typedef Log-collect-frequency {
    type enumeration {
      enum weekly {
        value 1;
        description "Collect log in files on a weekly basis";
      }
      enum daily {
        value 2;
        description "Collect log in files on a daily basis";
      }
    }
    description "Log collect frequency";
  }

  container syslog-service {
    xr:xr-xml-map "infra_syslog_cfg:SyslogService";
    description "Syslog Timestamp Services";

    container timestamps {
      xr:xr-xml-map "infra_syslog_cfg:Timestamps";
      description "Timestamp debug/log messages configuration";

      container log {
        xr:xr-xml-map "infra_syslog_cfg:Log";
        description "Timestamp log messages";

        container log-datetime {
          xr:xr-xml-map "infra_syslog_cfg:LogDatetime";
          description "Timestamp with date and time";

          container log-datetime-value {
            xr:xr-xml-map "infra_syslog_cfg:LogDatetimeValue";
            description "Set timestamp for log message";
            leaf time-stamp-value {
              xr:xr-xml-map "infra_syslog_cfg:TimeStampValue";
              type Time-info;
              default "enable";
              description "Time";
            }
            leaf msec {
              xr:xr-xml-map "infra_syslog_cfg:Msec";
              type Time-info;
              units "second";
              default "enable";
              description "Seconds";
            }
            leaf time-zone {
              xr:xr-xml-map "infra_syslog_cfg:TimeZone";
              type Time-info;
              default "disable";
              description "Timezone";
            }
            leaf year {
              xr:xr-xml-map "infra_syslog_cfg:Year";
              type Time-info;
              default "disable";
              description "Year";
            }
          }
        }
        leaf log-uptime {
          xr:xr-xml-map "infra_syslog_cfg:LogUptime";
          type empty;
          description "Enabled or disabled";
        }
        leaf log-timestamp-disable {
          xr:xr-xml-map "infra_syslog_cfg:LogTimestampDisable";
          type empty;
          description "Enabled or disabled";
        }
      }

      container debug {
        xr:xr-xml-map "infra_syslog_cfg:Debug";
        description "Timestamp debug messages";

        container debug-datetime {
          xr:xr-xml-map "infra_syslog_cfg:DebugDatetime";
          description "Timestamp with date and time";

          container datetime-value {
            xr:xr-xml-map "infra_syslog_cfg:DatetimeValue";
            description "Set time format for debug msg";
            leaf time-stamp-value {
              xr:xr-xml-map "infra_syslog_cfg:TimeStampValue";
              type Time-info;
              default "enable";
              description "Time";
            }
            leaf msec {
              xr:xr-xml-map "infra_syslog_cfg:Msec";
              type Time-info;
              units "second";
              default "enable";
              description "Seconds";
            }
            leaf time-zone {
              xr:xr-xml-map "infra_syslog_cfg:TimeZone";
              type Time-info;
              default "disable";
              description "Timezone";
            }
            leaf year {
              xr:xr-xml-map "infra_syslog_cfg:Year";
              type Time-info;
              default "disable";
              description "Year";
            }
          }
        }
        leaf debug-timestamp-disable {
          xr:xr-xml-map "infra_syslog_cfg:DebugTimestampDisable";
          type empty;
          description "Enabled or disabled";
        }
        leaf debug-uptime {
          xr:xr-xml-map "infra_syslog_cfg:DebugUptime";
          type empty;
          description "Enabled or disabled";
        }
      }
      leaf enable {
        xr:xr-xml-map "infra_syslog_cfg:Enable";
        type empty;
        description "Enable timestamp debug/log messages";
      }
    }
  }

  container syslog {
    xr:xr-xml-map "infra_syslog_cfg:Syslog";
    description "syslog";

    container monitor-logging {
      xr:xr-xml-map "infra_syslog_cfg:MonitorLogging";
      description "Set monitor logging";

      container monitor-discriminator {
        xr:xr-xml-map "infra_syslog_cfg:MonitorDiscriminator";
        description "Set monitor logging discriminators";
        leaf match2 {
          xr:xr-xml-map "infra_syslog_cfg:Match2";
          type string;
          description "match2 discriminator";
        }
        leaf nomatch1 {
          xr:xr-xml-map "infra_syslog_cfg:Nomatch1";
          type string;
          description "No-match1 discriminator";
        }
        leaf match1 {
          xr:xr-xml-map "infra_syslog_cfg:Match1";
          type string;
          description "match1 discriminator";
        }
        leaf nomatch3 {
          xr:xr-xml-map "infra_syslog_cfg:Nomatch3";
          type string;
          description "No-match3 discriminator";
        }
        leaf match3 {
          xr:xr-xml-map "infra_syslog_cfg:Match3";
          type string;
          description "match3 discriminator";
        }
        leaf nomatch2 {
          xr:xr-xml-map "infra_syslog_cfg:Nomatch2";
          type string;
          description "No-match2 discriminator";
        }
      }
      leaf logging-level {
        xr:xr-xml-map "infra_syslog_cfg:LoggingLevel";
        type Logging-levels;
        default "debug";
        description "Monitor Logging Level";
      }
    }

    container history-logging {
      xr:xr-xml-map "infra_syslog_cfg:HistoryLogging";
      description "Set history logging";
      leaf history-size {
        xr:xr-xml-map "infra_syslog_cfg:HistorySize";
        type uint32 {
          range "1..500";
        }
        default "1";
        description "Logging history size";
      }
      leaf logging-level {
        xr:xr-xml-map "infra_syslog_cfg:LoggingLevel";
        type Logging-levels;
        default "warning";
        description "History logging level";
      }
    }

    container logging-facilities {
      xr:xr-xml-map "infra_syslog_cfg:LoggingFacilities";
      description "Modify message logging facilities";
      leaf facility-level {
        xr:xr-xml-map "infra_syslog_cfg:FacilityLevel";
        type Facility;
        default "local7";
        description "Facility Type";
      }
    }

    container trap-logging {
      xr:xr-xml-map "infra_syslog_cfg:TrapLogging";
      description "Set trap logging";
      leaf logging-level {
        xr:xr-xml-map "infra_syslog_cfg:LoggingLevel";
        type Logging-levels;
        default "info";
        description "Trap logging level";
      }
    }

    container buffered-logging {
      xr:xr-xml-map "infra_syslog_cfg:BufferedLogging";
      description "Set buffered logging parameters";

      container buffered-discriminator {
        xr:xr-xml-map "infra_syslog_cfg:BufferedDiscriminator";
        description "Set buffered logging discriminators";
        leaf match2 {
          xr:xr-xml-map "infra_syslog_cfg:Match2";
          type string;
          description "match2 discriminator";
        }
        leaf nomatch1 {
          xr:xr-xml-map "infra_syslog_cfg:Nomatch1";
          type string;
          description "No-match1 discriminator";
        }
        leaf match1 {
          xr:xr-xml-map "infra_syslog_cfg:Match1";
          type string;
          description "match1 discriminator";
        }
        leaf nomatch3 {
          xr:xr-xml-map "infra_syslog_cfg:Nomatch3";
          type string;
          description "No-match3 discriminator";
        }
        leaf match3 {
          xr:xr-xml-map "infra_syslog_cfg:Match3";
          type string;
          description "match3 discriminator";
        }
        leaf nomatch2 {
          xr:xr-xml-map "infra_syslog_cfg:Nomatch2";
          type string;
          description "No-match2 discriminator";
        }
      }
      leaf logging-level {
        xr:xr-xml-map "infra_syslog_cfg:LoggingLevel";
        type Logging-levels;
        default "debug";
        description "Buffer logging level";
      }
      leaf buffer-size {
        xr:xr-xml-map "infra_syslog_cfg:BufferSize";
        type uint32 {
          range "4096..4294967295";
        }
        default "307200";
        description "Logging buffer size";
      }
    }

    container host-server {
      xr:xr-xml-map "infra_syslog_cfg_ext:HostServer";
      description "Configure logging host";

      container vrfs {
        xr:xr-xml-map "infra_syslog_cfg_ext:VRFTable";
        description "VRF table";

        list vrf {
          xr:xr-xml-map "infra_syslog_cfg_ext:VRF";
          key "vrf-name";
          description "VRF specific data";

          container ipv6s {
            xr:xr-xml-map "infra_syslog_cfg_ext:IPv6Table";
            description "List of the IPv6 logging host";

            list ipv6 {
              xr:xr-xml-map "infra_syslog_cfg_ext:IPv6";
              key "address";
              description "IPv6 address of the logging host";

              container ipv6-severity-port {
                xr:xr-xml-map "infra_syslog_cfg_ext:IPv6_SeverityPo"+
                  "rt";
                description "Severity/Port for the logging host";
                leaf severity {
                  xr:xr-xml-map "infra_syslog_cfg_ext:Severity";
                  type int32;
                  default "6";
                  description "Severity for the logging host";
                }
                leaf port {
                  xr:xr-xml-map "infra_syslog_cfg_ext:Port";
                  type int32;
                  default "514";
                  description "Port for the logging host";
                }
              }

              container ipv6-discriminator {
                xr:xr-xml-map "infra_syslog_cfg_ext:IPv6Discriminat"+
                  "or";
                description "Set IPv6 logging discriminators";
                leaf nomatch2 {
                  xr:xr-xml-map "infra_syslog_cfg_ext:Nomatch2";
                  type string;
                  description "No-match2 discriminator";
                }
                leaf match3 {
                  xr:xr-xml-map "infra_syslog_cfg_ext:Match3";
                  type string;
                  description "match3 discriminator";
                }
                leaf nomatch3 {
                  xr:xr-xml-map "infra_syslog_cfg_ext:Nomatch3";
                  type string;
                  description "No-match3 discriminator";
                }
                leaf match1 {
                  xr:xr-xml-map "infra_syslog_cfg_ext:Match1";
                  type string;
                  description "match1 discriminator";
                }
                leaf nomatch1 {
                  xr:xr-xml-map "infra_syslog_cfg_ext:Nomatch1";
                  type string;
                  description "No-match1 discriminator";
                }
                leaf match2 {
                  xr:xr-xml-map "infra_syslog_cfg_ext:Match2";
                  type string;
                  description "match2 discriminator";
                }
              }
              leaf address {
                xr:xr-xml-map "infra_syslog_cfg_ext:Address";
                type inet:ipv6-address-no-zone;
                description "IPv6 address of the logging host";
              }
            }
          }

          container hosts {
            xr:xr-xml-map "infra_syslog_cfg_ext:HostTable";
            description "List of the logging host";

            list host {
              xr:xr-xml-map "infra_syslog_cfg_ext:Host";
              key "host-name";
              description "Name of the logging host";

              container host-name-discriminator {
                xr:xr-xml-map "infra_syslog_cfg_ext:HostnameDiscrim"+
                  "inator";
                description "Set Hostname logging discriminators";
                leaf nomatch2 {
                  xr:xr-xml-map "infra_syslog_cfg_ext:Nomatch2";
                  type string;
                  description "No-match2 discriminator";
                }
                leaf match3 {
                  xr:xr-xml-map "infra_syslog_cfg_ext:Match3";
                  type string;
                  description "match3 discriminator";
                }
                leaf nomatch3 {
                  xr:xr-xml-map "infra_syslog_cfg_ext:Nomatch3";
                  type string;
                  description "No-match3 discriminator";
                }
                leaf match1 {
                  xr:xr-xml-map "infra_syslog_cfg_ext:Match1";
                  type string;
                  description "match1 discriminator";
                }
                leaf nomatch1 {
                  xr:xr-xml-map "infra_syslog_cfg_ext:Nomatch1";
                  type string;
                  description "No-match1 discriminator";
                }
                leaf match2 {
                  xr:xr-xml-map "infra_syslog_cfg_ext:Match2";
                  type string;
                  description "match2 discriminator";
                }
              }

              container host-severity-port {
                xr:xr-xml-map "infra_syslog_cfg_ext:HOST_SeverityPo"+
                  "rt";
                description "Severity/Port for the logging host";
                leaf severity {
                  xr:xr-xml-map "infra_syslog_cfg_ext:Severity";
                  type int32;
                  default "6";
                  description "Severity for the logging host";
                }
                leaf port {
                  xr:xr-xml-map "infra_syslog_cfg_ext:Port";
                  type int32;
                  default "514";
                  description "Port for the logging host";
                }
              }
              leaf host-name {
                xr:xr-xml-map "infra_syslog_cfg_ext:HostName";
                type string;
                description "Name of the logging host";
              }
            }
          }

          container ipv4s {
            xr:xr-xml-map "infra_syslog_cfg_ext:IPv4Table";
            description "List of the IPv4 logging host";

            list ipv4 {
              xr:xr-xml-map "infra_syslog_cfg_ext:IPv4";
              key "address";
              description "IPv4 address of the logging host";

              container ipv4-severity-port {
                xr:xr-xml-map "infra_syslog_cfg_ext:IPv4_SeverityPo"+
                  "rt";
                description "Severity/Port for the logging host";
                leaf severity {
                  xr:xr-xml-map "infra_syslog_cfg_ext:Severity";
                  type int32;
                  default "6";
                  description "Severity for the logging host";
                }
                leaf port {
                  xr:xr-xml-map "infra_syslog_cfg_ext:Port";
                  type int32;
                  default "514";
                  description "Port for the logging host";
                }
              }

              container ipv4-discriminator {
                xr:xr-xml-map "infra_syslog_cfg_ext:IPv4Discriminat"+
                  "or";
                description "Set IPv4 logging discriminators";
                leaf nomatch2 {
                  xr:xr-xml-map "infra_syslog_cfg_ext:Nomatch2";
                  type string;
                  description "No-match2 discriminator";
                }
                leaf match3 {
                  xr:xr-xml-map "infra_syslog_cfg_ext:Match3";
                  type string;
                  description "match3 discriminator";
                }
                leaf nomatch3 {
                  xr:xr-xml-map "infra_syslog_cfg_ext:Nomatch3";
                  type string;
                  description "No-match3 discriminator";
                }
                leaf match1 {
                  xr:xr-xml-map "infra_syslog_cfg_ext:Match1";
                  type string;
                  description "match1 discriminator";
                }
                leaf nomatch1 {
                  xr:xr-xml-map "infra_syslog_cfg_ext:Nomatch1";
                  type string;
                  description "No-match1 discriminator";
                }
                leaf match2 {
                  xr:xr-xml-map "infra_syslog_cfg_ext:Match2";
                  type string;
                  description "match2 discriminator";
                }
              }
              leaf address {
                xr:xr-xml-map "infra_syslog_cfg_ext:Address";
                type inet:ipv4-address-no-zone;
                description "IPv4 address of the logging host";
              }
            }
          }
          leaf vrf-name {
            xr:xr-xml-map "infra_syslog_cfg_ext:VRFName";
            type xr:Cisco-ios-xr-string;
            description "Name of the VRF instance";
          }
        }
      }
    }

    container console-logging {
      xr:xr-xml-map "infra_syslog_cfg:ConsoleLogging";
      description "Set console logging";

      container console-discriminator {
        xr:xr-xml-map "infra_syslog_cfg:ConsoleDiscriminator";
        description "Set console logging discriminators";
        leaf match2 {
          xr:xr-xml-map "infra_syslog_cfg:Match2";
          type string;
          description "match2 discriminator";
        }
        leaf nomatch1 {
          xr:xr-xml-map "infra_syslog_cfg:Nomatch1";
          type string;
          description "No-match1 discriminator";
        }
        leaf match1 {
          xr:xr-xml-map "infra_syslog_cfg:Match1";
          type string;
          description "match1 discriminator";
        }
        leaf nomatch3 {
          xr:xr-xml-map "infra_syslog_cfg:Nomatch3";
          type string;
          description "No-match3 discriminator";
        }
        leaf match3 {
          xr:xr-xml-map "infra_syslog_cfg:Match3";
          type string;
          description "match3 discriminator";
        }
        leaf nomatch2 {
          xr:xr-xml-map "infra_syslog_cfg:Nomatch2";
          type string;
          description "No-match2 discriminator";
        }
      }
      leaf logging-level {
        xr:xr-xml-map "infra_syslog_cfg:LoggingLevel";
        type Logging-levels;
        default "warning";
        description "Console logging level";
      }
    }

    container archive {
      xr:xr-xml-map "infra_syslog_cfg:Archive";
      description "Archive attributes configuration";
      leaf size {
        xr:xr-xml-map "infra_syslog_cfg:Size";
        type uint32 {
          range "1..2047";
        }
        description "Size in MB";
      }
      leaf file-size {
        xr:xr-xml-map "infra_syslog_cfg:FileSize";
        type uint32 {
          range "1..2047";
        }
        description "Size in MB";
      }
      leaf device {
        xr:xr-xml-map "infra_syslog_cfg:Device";
        type string;
        description "'/disk0:' or '/disk1:' or '/harddisk:'";
      }
      leaf threshold {
        xr:xr-xml-map "infra_syslog_cfg:Threshold";
        type uint32 {
          range "1..99";
        }
        units "percentage";
        description "Threshold percent";
      }
      leaf frequency {
        xr:xr-xml-map "infra_syslog_cfg:Frequency";
        type Log-collect-frequency;
        description "Daily basis or weekly basis";
      }
      leaf severity {
        xr:xr-xml-map "infra_syslog_cfg:Severity";
        type Log-message-severity;
        description "Severity log messages";
      }
      leaf length {
        xr:xr-xml-map "infra_syslog_cfg:Length";
        type uint32 {
          range "1..256";
        }
        description "Number of weeks";
      }
    }

    container source-interface-table {
      xr:xr-xml-map "infra_syslog_cfg:SourceInterfaceTable";
      description "Configure source interface";

      container source-interface-values {
        xr:xr-xml-map "infra_syslog_cfg:SourceInterface";
        description
          "Specify interface for source address in logging
          transactions";

        list source-interface-value {
          xr:xr-xml-map "infra_syslog_cfg:SourceInterfaceValue";
          key "src-interface-name-value";
          description "Source interface";

          container source-interface-vrfs {
            xr:xr-xml-map "infra_syslog_cfg:SourceInterfaceVRFTable";
            description "Configure source interface VRF";

            list source-interface-vrf {
              xr:xr-xml-map "infra_syslog_cfg:SourceInterfaceVRF";
              key "vrf-name";
              description "Specify VRF for source interface";
              leaf vrf-name {
                xr:xr-xml-map "infra_syslog_cfg:VRFName";
                type xr:Cisco-ios-xr-string;
                description "Name of the VRF instance";
              }
            }
          }
          leaf src-interface-name-value {
            xr:xr-xml-map "infra_syslog_cfg:SrcInterfaceNameValue";
            type xr:Interface-name;
            description "Which Interface";
          }
        }
      }
    }
    leaf host-name-prefix {
      xr:xr-xml-map "infra_syslog_cfg:HostnamePrefix";
      type string;
      description "Hostname prefix string";
    }
    leaf local-log-file-size {
      xr:xr-xml-map "infra_syslog_cfg:LocalLogFileSize";
      type uint32 {
        range "0..4294967295";
      }
      default "32768";
      description "Locallog buffer size";
    }
    leaf enable-console-logging {
      xr:xr-xml-map "infra_syslog_cfg:EnableConsoleLogging";
      type boolean;
      description "Enabled or disabled";
    }
    leaf suppress-duplicates {
      xr:xr-xml-map "infra_syslog_cfg:SuppressDuplicates";
      type empty;
      description "Enabled or disabled";
    }
  }
}
