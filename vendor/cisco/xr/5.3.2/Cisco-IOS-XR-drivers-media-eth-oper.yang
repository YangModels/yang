module Cisco-IOS-XR-drivers-media-eth-oper {

  /*** NAMESPACE / PREFIX DEFINITION ***/

  namespace "http://cisco.com/ns/yang"+
    "/Cisco-IOS-XR-drivers-media-eth-oper";


  prefix "drivers-media-eth-oper";

  /*** LINKAGE (IMPORTS / INCLUDES) ***/

  import Cisco-IOS-XR-types { prefix "xr"; }

  include Cisco-IOS-XR-drivers-media-eth-oper-sub1 {
    revision-date 2015-01-07;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR drivers-media-eth package operational data.

     This module contains definitions
     for the following management objects:
       ethernet-interface: Ethernet operational data

     Copyright (c) 2013-2015 by Cisco Systems, Inc.
     All rights reserved.";

  revision "2015-01-07" {
    description
      "IOS XR 5.3.1 revision.";
  }


  container ethernet-interface {
    xr:xr-xml-map "drivers_media_eth_intf_oper:EthernetInterface";
    config false;
    description "Ethernet operational data";

    container statistics {
      xr:xr-xml-map "drivers_media_eth_intf_oper:StatisticsTable";
      description "Ethernet controller statistics table";

      list statistic {
        xr:xr-xml-map "drivers_media_eth_intf_oper:Statistics";
        key "interface-name";
        description "Ethernet statistics information";
        leaf interface-name {
          xr:xr-xml-map "drivers_media_eth_intf_oper:InterfaceName";
          type xr:Interface-name;
          description "The name of the interface";
        }
        uses ETHERNET-PORT-STATS-TYPE;
      }
    }

    container interfaces {
      xr:xr-xml-map "drivers_media_eth_intf_oper:InterfaceTable";
      description "Ethernet controller info table";

      list interface {
        xr:xr-xml-map "drivers_media_eth_intf_oper:Interface";
        key "interface-name";
        description "Ethernet controller information";
        leaf interface-name {
          xr:xr-xml-map "drivers_media_eth_intf_oper:InterfaceName";
          type xr:Interface-name;
          description "The name of the interface";
        }
        uses ETHERNET-CONTROLLER-DRIVER-BAG-V2-TYPE;
      }
    }

    container berts {
      xr:xr-xml-map "drivers_media_eth_intf_oper:BERTTable";
      description "Ethernet controller BERT table";

      list bert {
        xr:xr-xml-map "drivers_media_eth_intf_oper:BERT";
        key "interface-name";
        description "Ethernet BERT information";
        leaf interface-name {
          xr:xr-xml-map "drivers_media_eth_intf_oper:InterfaceName";
          type xr:Interface-name;
          description "The name of the interface";
        }
        uses ETH-SHOWCTRL-BERT;
      }
    }
  }
}
