module Cisco-IOS-XR-asr9k-lc-ethctrl-cfg {

  /*** NAMESPACE / PREFIX DEFINITION ***/

  namespace "http://cisco.com/ns/yang"+
    "/Cisco-IOS-XR-asr9k-lc-ethctrl-cfg";


  prefix "asr9k-lc-ethctrl-cfg";

  /*** LINKAGE (IMPORTS / INCLUDES) ***/

  import Cisco-IOS-XR-types { prefix "xr"; }

  import Cisco-IOS-XR-ifmgr-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR asr9k-lc-ethctrl package configuration.

     This YANG module augments the
       Cisco-IOS-XR-ifmgr-cfg
     module with configuration data.

     Copyright (c) 2013-2016 by Cisco Systems, Inc.
     All rights reserved.";

  revision "2015-11-09" {
    description
      "IOS XR 6.0 revision.";
  }

  typedef Ether-ctrl-transport-mode {
    type enumeration {
      enum wan {
        value 1;
        description "WAN";
      }
      enum otnopu1e {
        value 2;
        description "OTNOPUle";
      }
      enum otnopu2e {
        value 3;
        description "OTNOPU2e";
      }
    }
    description "Ether ctrl transport mode";
  }
  typedef Permit-pluggable-pid {
    type enumeration {
      enum all {
        value 1;
        description "ALL PIDs";
      }
    }
    description "Permit pluggable pid";
  }
  typedef Permit-pluggable {
    type enumeration {
      enum all {
        value 1;
        description "ALL types";
      }
    }
    description "Permit pluggable";
  }

  augment "/a1:interface-configurations/a1:interface-configuration" {

    container ethernet-control {
      description "EthernetControl";

      container transceiver {
        description "Transceiver";

        container permit {
          description "Permit";
          leaf type {
            type Permit-pluggable;
            description "Permit pluggable type all";
          }
          leaf pid {
            type Permit-pluggable-pid;
            description "Permit pluggable PID (Product ID) all";
          }
        }
      }
      leaf transport-mode {
        type Ether-ctrl-transport-mode;
        description "Set the transport mode on an interface";
      }
      leaf small-frame-padding {
        type empty;
        description "Enable small frame padding on an interface";
      }
    }
    description
      "This augment extends the configuration data of
      'Cisco-IOS-XR-ifmgr-cfg'";
  }
}
