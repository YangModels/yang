submodule Cisco-IOS-XR-atm-vcm-oper-sub3 {

  belongs-to Cisco-IOS-XR-atm-vcm-oper {
    prefix Cisco-IOS-XR-atm-vcm-oper;
  }

  /*** LINKAGE (IMPORTS / INCLUDES) ***/

  import Cisco-IOS-XR-types { prefix "xr"; }

  include Cisco-IOS-XR-atm-vcm-oper-sub4 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR atm-vcm package operational data.

     Copyright (c) 2013-2016 by Cisco Systems, Inc.
     All rights reserved.";

  revision "2015-11-09" {
    description
      "IOS XR 6.0 revision.";
  }

  typedef Class-link-oam-inherit-level {
    type enumeration {
      enum vc-configured-onvc {
        value 0;
        description "Configured on VC";
      }
      enum vc-class-onvc {
        value 1;
        description "Class on VC";
      }
      enum vc-class-on-sub-interface {
        value 2;
        description "Class on sub-if";
      }
      enum vc-class-on-main-interface {
        value 3;
        description "Class on main-if";
      }
      enum vc-global-default {
        value 4;
        description "Global default values";
      }
      enum vc-inherit-level-unknown {
        value 5;
        description "Unknown (invalid)";
      }
    }
    description "ATM VC-class inheritence level for class-link";
  }
  typedef Vc-manage-level {
    type enumeration {
      enum manage {
        value 1;
        description "Managed";
      }
      enum not-managed {
        value 2;
        description "Not managed";
      }
    }
    description "ATM Class link manage level";
  }

  grouping ATM-CLASS-LINK-OAM-AIS-RDI {
    description "ATM class link AIS/RDI information";
    leaf ais-rdi-up-count {
      type uint32;
      description "AIS RDI up count";
    }
    leaf ais-rdi-up-time {
      type uint32;
      units "second";
      description
        "Time (in seconds) with no AIS/RDI cells before
        declaring a VC as up";
    }
    leaf ais-rdi-inherit-level {
      type Class-link-oam-inherit-level;
      description "AIS RDI inherit level";
    }
  }

  grouping ATM-CLASS-LINK-OAM-RETRY {
    description "ATM class link retry information";
    leaf retry-up-count {
      type uint32;
      description "Retry Count";
    }
    leaf down-count {
      type uint32;
      description "Down Count";
    }
    leaf retry-frequency {
      type uint32;
      description "Retry frequency";
    }
    leaf retry-inherit-level {
      type Class-link-oam-inherit-level;
      description "Retry inherit level";
    }
  }

  grouping ATM-CLASS-LINK-OAM-PVC {
    description "ATM class link PVC information";
    leaf manage-level {
      type Vc-manage-level;
      description "Manage Level";
    }
    leaf pvc-frequency {
      type uint32;
      description "PVC Frequency";
    }
    leaf keep-vc-up {
      type boolean;
      description "Keep vc up";
    }
    leaf ais-rdi-failure {
      type boolean;
      description "AIS RDI failure";
    }
    leaf manage-inherit-level {
      type Class-link-oam-inherit-level;
      description "Manage inherit level";
    }
  }

  grouping ATM-CLASS-LINK-ENCAPSULATION {
    description "ATM class link encapsulation information";
    leaf encapsulation-type {
      type Vc-encap;
      description "Encapsulation type";
    }
    leaf encapsulation-inherit-level {
      type Vc-inherit-level;
      description "Encapsulation inherit level";
    }
  }

  grouping ATM-CLASS-LINK-SHAPING {
    description "ATM class link shaping information";
    leaf shaping-type {
      type Vc-traf-shaping;
      description "ATM VC traffic shaping type";
    }
    leaf peak-output-rate {
      type uint32;
      units "kbit/s";
      description "Peak output rate in Kbps";
    }
    leaf average-output-rate {
      type uint32;
      description "Average output rate";
    }
    leaf burst-output-rate {
      type uint32;
      description "Burst output rate";
    }
    leaf shaping-inherit-level {
      type Vc-inherit-level;
      description "Shaping inherit level";
    }
  }

  grouping ATM-CLASS-LINK-OAM {
    description "ATM class link oam information";

    container class-link-shaping {
      description "Traffic Shaping detail of VC class";
      uses ATM-CLASS-LINK-SHAPING;
    }

    container class-link-encapsulation {
      description "Encapsulation details of VC class";
      uses ATM-CLASS-LINK-ENCAPSULATION;
    }

    container oam-pvc {
      description "OAM PVC details of VC class";
      uses ATM-CLASS-LINK-OAM-PVC;
    }

    container oam-retry {
      description "OAM Retry details of VC class";
      uses ATM-CLASS-LINK-OAM-RETRY;
    }

    container ais-rdi {
      description "AIS RDI details of a VC class";
      uses ATM-CLASS-LINK-OAM-AIS-RDI;
    }
  }

  grouping ATM-CLASS-LINK-NOT-SUPPORTED {
    description "ATM VC Class not supported information";
    leaf encapsulation-not-supported {
      type Vc-encap;
      description "Encapsulation type not supported";
    }
    leaf not-supported-inherit-level {
      type Vc-inherit-level;
      description "NotSupportedInheritLevel";
    }
  }

  grouping ATM-CLASS-LINK-VPI-VCI {
    description "ATM class link information";

    container vc-class-not-supported {
      description "Not supported VC class";
      uses ATM-CLASS-LINK-NOT-SUPPORTED;
    }

    container oam-config {
      description "Oam values for class link";
      uses ATM-CLASS-LINK-OAM;
    }
    leaf sub-interface-name {
      type xr:Interface-name;
      description "Sub-interface handle";
    }
  }
}
