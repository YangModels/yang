module Cisco-IOS-XR-mpls-vpn-oper {

  /*** NAMESPACE / PREFIX DEFINITION ***/

  namespace "http://cisco.com/ns/yang/Cisco-IOS-XR-mpls-vpn-oper";


  prefix "mpls-vpn-oper";

  /*** LINKAGE (IMPORTS / INCLUDES) ***/

  import Cisco-IOS-XR-types { prefix "xr"; }

  include Cisco-IOS-XR-mpls-vpn-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR mpls-vpn package operational data.

     This module contains definitions
     for the following management objects:
       l3vpn: L3VPN operational data

     Copyright (c) 2013-2016 by Cisco Systems, Inc.
     All rights reserved.";

  revision "2015-11-09" {
    description
      "IOS XR 6.0 revision.";
  }


  container l3vpn {
    config false;
    description "L3VPN operational data";

    container invalid-vrfs {
      description
        "Invalid VRF Table (VRFs that are forward
        referenced)";

      list invalid-vrf {
        key "vrf-name";
        description "Invalid VRF (VRF that is forward referenced)";
        leaf vrf-name {
          type string;
          description "The Name for an invalid VRF";
        }
        uses MPLS-VPN-VRF;
      }
    }

    container vrfs {
      description "VRF Table";

      list vrf {
        key "vrf-name";
        description "VRF";
        leaf vrf-name {
          type string;
          description "The Name for a VRF";
        }
        uses MPLS-VPN-VRF;
      }
    }
  }
}
