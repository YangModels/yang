module Cisco-IOS-XR-lpts-ifib-oper {

  /*** NAMESPACE / PREFIX DEFINITION ***/

  namespace "http://cisco.com/ns/yang/Cisco-IOS-XR-lpts-ifib-oper";


  prefix "lpts-ifib-oper";

  /*** LINKAGE (IMPORTS / INCLUDES) ***/

  import Cisco-IOS-XR-types { prefix "xr"; }

  include Cisco-IOS-XR-lpts-ifib-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR lpts-ifib package operational data.

     This module contains definitions
     for the following management objects:
       lpts-ifib: lpts ifib database

     Copyright (c) 2013-2016 by Cisco Systems, Inc.
     All rights reserved.";

  revision "2015-11-09" {
    description
      "IOS XR 6.0 revision.";
  }


  container lpts-ifib {
    config false;
    description "lpts ifib database";

    container nodes {
      description "Node ifib database";

      list node {
        key "node-name";
        description "Per node slice ";

        container slice-ids {
          description "Slice specific";

          list slice-id {
            key "slice-name";
            description "slice types";
            leaf slice-name {
              type xr:Cisco-ios-xr-string;
              description "Type value";
            }

            list entry {
              key "entry";
              description "Data for single pre-ifib entry";
              leaf entry {
                type int32;
                description "Single Pre-ifib entry";
              }
              uses FM-IFIB-ENTRY;
            }
          }
        }
        leaf node-name {
          type xr:Node-id;
          description "The node name";
        }
      }
    }
  }
}
