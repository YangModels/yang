module openconfig-mpls-rsvp {

  yang-version "1";

  // namespace
  namespace "http://openconfig.net/yang/rsvp";

  prefix "rsvp";

  // import some basic types
  import ietf-inet-types { prefix inet; }
  import openconfig-mpls-types { prefix mplst; }
  import ietf-yang-types { prefix yang; }
  import openconfig-types { prefix oc-types; }
  import openconfig-extensions { prefix oc-ext; }
  import cisco-xr-openconfig-interfaces-types { prefix ocif; }


  // meta
  organization "OpenConfig working group";

  contact
    "OpenConfig working group
     netopenconfig@googlegroups.com";

  description
    "Configuration for RSVP-TE signaling, including global protocol
     parameters and LSP-specific configuration for constrained-path
     LSPs";

  oc-ext:openconfig-version "0.2.1";

  revision "2015-11-05" {
    description
      "Initial public release of MPLS models";
    reference "0.2.1";
  }

  revision "2015-10-14" {
    description
      "Work in progress";
    reference "0.2.0";
  }

  // feature statements

  // identity statements

  // typedef statements

  // grouping statements

  grouping mpls-rsvp-soft-preemption_config {
    description
      "Configuration for MPLS soft preemption";
    leaf enable {
      type boolean;
      default false;
      description
        "Enables soft preemption on a node.";
    }

    leaf soft-preemption-timeout {
      type uint16 {
        range 0..max;
      }
      // The RFC actually recommends 30 seconds as default.
      default 0;
      description
        "Timeout value for soft preemption to revert
         to hard preemption";
      reference "RFC5712 MPLS-TE soft preemption";
    }
  }

  grouping mpls-rsvp-soft-preemption {
    description
      "Top level group for MPLS soft preemption";
    container soft-preemption {
      description
        "Protocol options relating to RSVP
         soft preemption";
      container config {
        description
          "Configuration parameters relating to RSVP
           soft preemption support";
        uses mpls-rsvp-soft-preemption_config;
      }
      container state {
        config false;
        description
          "State parameters relating to RSVP
           soft preemption support";
        uses mpls-rsvp-soft-preemption_config;
      }
    }
  }

  grouping mpls-rsvp-hellos_config {
    description
      "RSVP protocol options configuration.";

    leaf hello-interval {
      type uint16 {
        range 1000..60000;
      }
      units milliseconds;
      default 9000;
      description
        "set the interval in ms between RSVP hello
         messages";
      reference
        "RFC 3209: RSVP-TE: Extensions to RSVP for
         LSP Tunnels.
         RFC 5495: Description of the Resource
         Reservation Protocol - Traffic-Engineered
         (RSVP-TE) Graceful Restart Procedures";
    }

    leaf refresh-reduction {
      type boolean;
      default true;
      description
        "enables all RSVP refresh reduction message
         bundling, RSVP message ID, reliable message delivery
         and summary refresh";
      reference
        "RFC 2961 RSVP Refresh Overhead Reduction
         Extensions";
    }
  }

  grouping mpls-rsvp-hellos {
    description
      "Top level grouping for RSVP hellos parameters";
    // TODO: confirm that the described semantics are supported
    // on various implementations. Finer grain configuration
    // will be vendor-specific

    container hellos {
      description
        "Top level container for RSVP hello parameters";

      container config {
        description
          "Configuration parameters relating to RSVP
           hellos";
        uses mpls-rsvp-hellos_config;
      }
      container state {
        config false;
        description
          "State information associated with RSVP hellos";
        uses mpls-rsvp-hellos_config;
      }
    }
  }

  grouping mpls-rsvp-subscription_config {
    description
      "RSVP subscription configuration";
    leaf subscription {
      type oc-types:percentage;
      description
        "percentage of the interface bandwidth that
         RSVP can reserve";
    }
  }
  grouping mpls-rsvp-subscription {
    description
      "Top level group for RSVP subscription options";

    container subscription {
      description
        "Bandwidth percentage reservable by RSVP
         on an interface";

      container config {
        description
          "Configuration parameters relating to RSVP
          subscription options";
        uses mpls-rsvp-subscription_config;
      }

      container state {
        config false;
        description
          "State parameters relating to RSVP
          subscription options";
        uses mpls-rsvp-subscription_config;
      }
    }
  }

  grouping mpls-rsvp-graceful-restart_config {
    description
      "Configuration parameters relating to RSVP Graceful-Restart";

    leaf enable {
      type boolean;
      default false;
      description
        "Enables graceful restart on the node.";
    }

    leaf restart-time {
      type uint32;
      description
        "Graceful restart time (seconds).";
      reference
        "RFC 5495: Description of the Resource
         Reservation Protocol - Traffic-Engineered
         (RSVP-TE) Graceful Restart Procedures";
    }
    leaf recovery-time {
      type uint32;
      description
        "RSVP state recovery time";
    }
  }

  grouping mpls-rsvp-graceful-restart {
    description
      "Top level group for RSVP graceful-restart
       parameters";

    container graceful-restart {
      description
        "Operational state and configuration parameters relating to
        graceful-restart for RSVP";

      container config {
        description
          "Configuration parameters relating to
           graceful-restart";
        uses mpls-rsvp-graceful-restart_config;
      }

      container state {
        config false;
        description
          "State information associated with
           RSVP graceful-restart";
        uses mpls-rsvp-graceful-restart_config;
      }
    }
  }

  grouping mpls-rsvp-authentication_config {
    description
      "RSVP authentication parameters container.";

    leaf enable {
      type boolean;
      default false;
      description
        "Enables RSVP authentication on the node.";
    }

    leaf authentication-key {
      type string {
        // Juniper supports 1..16 while
        // Cisco has a much bigger range, up to 60.
        length "1..32";
      }
      description
        "authenticate RSVP signaling
         messages";
      reference
        "RFC 2747: RSVP Cryptographic Authentication";
    }
  }

  grouping mpls-rsvp-authentication {
    description
      "Top level group for RSVP authentication,
       as per RFC2747";

    container authentication {
      description
        "Configuration and state parameters relating to RSVP
        authentication as per RFC2747";

      container config {
        description
          "Configuration parameters relating
           to authentication";
        uses mpls-rsvp-authentication_config;
      }

      container state {
        config false;
        description
          "State information associated
           with authentication";
        uses mpls-rsvp-authentication_config;
      }
    }
  }

  grouping mpls-rsvp-protection_config {
    description
      "RSVP facility (link/node) protection configuration";

    leaf link-protection-style-requested {
      type identityref {
        base mplst:protection-type;
      }
      default mplst:link-node-protection-requested;
      description
        "Style of mpls frr protection desired:
        link, link-node, or unprotected";
    }

    leaf bypass-optimize-interval {
      type uint16;
      units seconds;
      description
        "interval between periodic optimization
        of the bypass LSPs";
      // note: this is interface specific on juniper
      // on iox, this is global. need to resolve.
    }
    // to be completed, things like enabling link protection,
    // optimization times, etc.
  }

  grouping mpls-rsvp-link-protection {
    description
      "Top level group for RSVP protection";
    container protection {
      description
        "link-protection (NHOP) related configuration";

      container config {
        description
          "Configuration for link-protection";
        uses mpls-rsvp-protection_config;
      }

      container state {
        config false;
        description
          "State for link-protection";
        uses mpls-rsvp-protection_config;
      }
    }
  }

  grouping mpls-rsvp-error-statistics {
    description
      "RSVP-TE packet statistics";

    container error {
      description
        "RSVP-TE error statistics";

      leaf authentication-failure {
        type yang:counter32;
        description
          "Authentication failure count";
      }

      leaf path-error {
        type yang:counter32;
        description
          "Path error to client count";
      }

      leaf resv-error {
        type yang:counter32;
        description
          "Resv error to client count";
      }

      leaf path-timeout {
        type yang:counter32;
        description
          "Path timeout count";
      }

      leaf resv-timeout {
        type yang:counter32;
        description
          "Resv timeout count";
      }

      leaf rate-limit {
        type yang:counter32;
        description
          "Count of packets that were rate limited";
      }

      // TODO - complete the other error statistics
    }
  }

  grouping mpls-rsvp-protocol-statistics {
    description
      "RSVP protocol statistics";

    container protocol {
      description
        "RSVP-TE protocol statistics";

      leaf hello-sent {
        type yang:counter32;
        description
          "Hello sent count";
      }

      leaf hello-rcvd {
        type yang:counter32;
        description
          "Hello received count";
      }

      leaf path-sent {
        type yang:counter32;
        description
          "Path sent count";
      }

      leaf path-rcvd {
        type yang:counter32;
        description
          "Path received count";
      }

      // TODO - To be completed the other packet statistics
    }
  }

  grouping mpls-rsvp-statistics {
    description
      "Top level grouping for RSVP protocol state";

    uses mpls-rsvp-protocol-state;
  }

  grouping rsvp-global {
    description
      "Global RSVP protocol configuration";
    container rsvp-te {
      description
        "RSVP-TE global signaling protocol configuration";

      container sessions {
        description
          "Configuration and state of RSVP sessions";

        container config {
          description
            "Configuration of RSVP sessions on the device";
        }

        container state {
          config false;
          description
            "State information relating to RSVP sessions
            on the device";
          uses mpls-rsvp-session-state;
        }
      }

      container neighbors {
        description
          "Configuration and state for RSVP neighbors connecting
          to the device";

        container config {
          description
            "Configuration of RSVP neighbor information";
        }

        container state {
          config false;
          description
            "State information relating to RSVP neighbors";
          uses mpls-rsvp-neighbor-state;
        }
      }

      container global {
        description
          "Platform wide RSVP configuration and state";
        uses mpls-rsvp-graceful-restart;
        uses mpls-rsvp-soft-preemption;
       uses mpls-rsvp-hellos;

        container state {
          config false;
          description
            "Platform wide RSVP state, including counters";
          // TODO - reconcile global and per-interface
          // protocol-related statistics

          container counters {
            config false;
            description
              "Platform wide RSVP statistics and counters";
            uses mpls-rsvp-global-protocol-state;
            uses mpls-rsvp-statistics;
          }
        }
      }

      container interface-attributes {
        // interfaces, bw percentages, hello timers, etc goes here";
        description
          "Attributes relating to RSVP-TE enabled interfaces";

        list interface {
          key interface-name;
          description
            "list of per-interface RSVP configurations";

          leaf interface-name {
            type leafref {
              path "../config/interface-name";
              require-instance true;
            }
            description
              "references a configured IP interface";
          }


          container config {
            description
              "Configuration of per-interface RSVP parameters";

            leaf interface-name {
              type ocif:interface-ref;
              description
                "Name of configured IP interface";
            }
          }

          container state {
            config false;
            description
              "Per-interface RSVP protocol and state information";
            uses mpls-rsvp-interfaces-state;

            container counters {
              config false;
              description
                "Interface specific RSVP statistics and counters";
              uses mpls-rsvp-protocol-state;
            }
          }

          uses mpls-rsvp-hellos;
          uses mpls-rsvp-authentication;
          uses mpls-rsvp-subscription;
          uses mpls-rsvp-link-protection;
        }
      }
    }
  }

  grouping rsvp-p2p-tunnel-attributes_config {
    description
      "properties of RSPP point-to-point paths";

    leaf source {
      when "/mpls/lsps/constrained-path/tunnel/config/signaling-protocol = 'RSVP'" {
        description
          "When the signaling protocol is RSVP-TE ";
      }
      type inet:ip-address;
      description
        "RSVP-TE tunnel source address";
    }

    leaf soft-preemption {
      when "/mpls/lsps/constrained-path/tunnel/config/signaling-protocol = 'RSVP'" {
        description
          "When the signaling protocol is RSVP-TE ";
      }
      type boolean;
      default false;
      description
        "Enables RSVP soft-preemption on this LSP";
    }

    uses rsvp-priorities_config;
  }

  grouping rsvp-priorities_config {
    description
      "Configuration paramters related to RSVP-TE priorities";

    leaf setup-priority {
      when "/mpls/lsps/constrained-path/tunnel/config/signaling-protocol = 'RSVP'" {
        description
          "When the signaling protocol is RSVP-TE ";
      }
      type uint8 {
        range 0..7;
      }
      default 7;
      description
        "RSVP-TE preemption priority during LSP setup, lower is
         higher priority; default 7 indicates that LSP will not
         preempt established LSPs during setup";
      reference "RFC 3209 - RSVP-TE: Extensions to RSVP for
         LSP Tunnels";
    }

    leaf hold-priority {
      when "/mpls/lsps/constrained-path/tunnel/config/signaling-protocol = 'RSVP'" {
        description
           "When the signaling protocol is RSVP-TE ";
      }
      type uint8 {
        range 0..7;
      }
      default 0;
      description
        "preemption priority once the LSP is established,
         lower is higher priority; default 0 indicates other LSPs
         will not preempt the LSPs once established";
      reference "RFC 3209 - RSVP-TE: Extensions to RSVP for
        LSP Tunnels";
    }
  }

  grouping rsvp-p2p-path-attributes_config {
    description
      "properties of RSPP point-to-point paths";

    uses rsvp-priorities_config;

    leaf retry-timer {
      when "/mpls/lsps/constrained-path/tunnel/config/signaling-protocol = 'RSVP'" {
        description
        "When the signaling protocol is RSVP-TE ";
      }
      type uint16 {
        range 1..600;
      }
      units seconds;
      description
        "sets the time between attempts to establish the
         LSP";
    }
  }

  grouping mpls-rsvp-neighbor-state {
    description
      "State information for RSVP neighbors";

    list neighbor {
      key "address";
      description
        "List of RSVP neighbors connecting to the device,
        keyed by neighbor address";

      leaf address {
        type inet:ip-address;
        description
          "Address of RSVP neighbor";
      }

      leaf detected-interface {
        type string;
        description
          "Interface where RSVP neighbor was detected";
      }

      leaf neighbor-status {
        type enumeration {
          enum UP {
            description
              "RSVP hello messages are detected from the neighbor";
          }
          enum DOWN {
            description
              "RSVP neighbor not detected as up, due to a
               communication failure or IGP notification
               the neighbor is unavailable";
          }
        }
        description
          "Enumuration of possible RSVP neighbor states";
      }

      leaf refresh-reduction {
        type boolean;
        description
          "Suppport of neighbor for RSVP refresh reduction";
        reference
          "RFC 2961 RSVP Refresh Overhead Reduction
           Extensions";
      }
    }
  }

  grouping mpls-rsvp-session-state {
    description
      "State information for RSVP TE sessions";

    list session {
      key "source-port destination-port
       source-address destination-address";
      description
        "List of RSVP sessions";

      leaf source-address {
        type inet:ip-address;
        description
          "Origin address of RSVP session";
      }

      leaf destination-address {
        type inet:ip-address;
        description
          "Destination address of RSVP session";
      }

      leaf source-port {
        type uint16;
        description
          "RSVP source port";
        reference "RFC 2205";
      }

      leaf destination-port {
        type uint16;
        description
          "RSVP source port";
        reference "RFC 2205";

      }

      leaf status {
        type enumeration {
          enum UP {
            description
              "RSVP session is up";
          }
          enum DOWN {
            description
              "RSVP session is down";
          }
        }
        description
          "Enumeration of RSVP session states";
      }

      leaf type {
        type enumeration {
          enum SOURCE {
            description
              "RSVP session originates on this device";
          }
          enum TRANSIT {
            description
              "RSVP session transits this device only";
          }
          enum DESTINATION {
            description
              "RSVP session terminates on this device";
          }
        }
        description
          "Enumeration of possible RSVP session types";
      }

      leaf tunnel-id {
        type uint16;
        description
          "Unique identifier of RSVP session";
      }

      leaf label-in {
        type mplst:mpls-label;
        description
          "Incoming MPLS label associated with this RSVP session";
      }

      leaf label-out {
        type mplst:mpls-label;
        description
          "Outgoing MPLS label associated with this RSVP session";
      }

      leaf-list associated-lsps {
        type leafref {
          path "../../../../../../lsps/constrained-path/tunnel/" +
          "config/name";
        }
        description
          "List of label switched paths associated with this RSVP
           session";
      }
    }
  } //rsvp-session-state

  grouping mpls-rsvp-interfaces-state {
    description
      "RSVP state information relevant to an interface";

    list bandwidth {
      key priority;
      description
        "Available and reserved bandwidth by priority on
         the interface.";

      leaf priority {
        type uint8 {
          range 0..7;
        }
        description
          "RSVP priority level for LSPs traversing the interface";
      }

      leaf available-bandwidth {
        type mplst:bandwidth-mbps;
        description
          "Bandwidth currently available";
      }

      leaf reserved-bandwidth {
        type mplst:bandwidth-mbps;
        description
          "Bandwidth currently reserved";
      }
    }

    leaf highwater-mark {
      type mplst:bandwidth-mbps;
      description
        "Maximum bandwidth ever reserved";
    }

    leaf active-reservation-count {
      type yang:gauge64;
      description
        "Number of active RSVP reservations";
    }
  }

  grouping mpls-rsvp-global-protocol-state {
    description
      "RSVP protocol statistics which may not apply
      on an interface, but are significant globally.";

    leaf path-timeouts {
      type yang:counter64;
      description
        "TODO";
    }

    leaf reservation-timeouts {
      type yang:counter64;
      description
        "TODO";
    }

    leaf rate-limited-messages {
      type yang:counter64;
      description
        "RSVP messages dropped due to rate limiting";
    }
  }

  grouping mpls-rsvp-protocol-state {
    description
      "RSVP protocol statistics and message counters";

    leaf in-path-messages {
      type yang:counter64;
      description
        "Number of received RSVP Path messages";
    }

    leaf in-path-error-messages {
      type yang:counter64;
      description
        "Number of received RSVP Path Error messages";
    }

    leaf in-path-tear-messages {
      type yang:counter64;
      description
        "Number of received RSVP Path Tear messages";
    }

    leaf in-reservation-messages {
      type yang:counter64;
      description
        "Number of received RSVP Resv messages";
    }

    leaf in-reservation-error-messages {
      type yang:counter64;
      description
        "Number of received RSVP Resv Error messages";
    }

    leaf in-reservation-tear-messages {
      type yang:counter64;
      description
        "Number of received RSVP Resv Tear messages";
    }

    leaf in-hello-messages {
      type yang:counter64;
      description
        "Number of received RSVP hello messages";
    }

    leaf in-srefresh-messages {
      type yang:counter64;
      description
        "Number of received RSVP summary refresh messages";
    }

    leaf in-ack-messages {
      type yang:counter64;
      description
        "Number of received RSVP refresh reduction ack
         messages";
    }

    leaf out-path-messages {
      type yang:counter64;
      description
        "Number of sent RSVP PATH messages";
    }

    leaf out-path-error-messages {
      type yang:counter64;
      description
        "Number of sent RSVP Path Error messages";
    }

    leaf out-path-tear-messages {
      type yang:counter64;
      description
        "Number of sent RSVP Path Tear messages";
    }

    leaf out-reservation-messages {
      type yang:counter64;
      description
        "Number of sent RSVP Resv messages";
    }

    leaf out-reservation-error-messages {
      type yang:counter64;
      description
        "Number of sent RSVP Resv Error messages";
    }

    leaf out-reservation-tear-messages {
      type yang:counter64;
      description
        "Number of sent RSVP Resv Tear messages";
    }

    leaf out-hello-messages {
      type yang:counter64;
      description
        "Number of sent RSVP hello messages";
    }

    leaf out-srefresh-messages {
      type yang:counter64;
      description
        "Number of sent RSVP summary refresh messages";
    }

    leaf out-ack-messages {
      type yang:counter64;
      description
        "Number of sent RSVP refresh reduction ack messages";
    }
  }



  // data definition statements

  // augment statements

  // rpc statements

  // notification statements

}
