module Cisco-IOS-XR-ethernet-lldp-cfg {

  /*** NAMESPACE / PREFIX DEFINITION ***/

  namespace "http://cisco.com/ns"+
    "/yang/Cisco-IOS-XR-ethernet-lldp-cfg";


  prefix "ethernet-lldp-cfg";

  /*** LINKAGE (IMPORTS / INCLUDES) ***/

  import Cisco-IOS-XR-types { prefix "xr"; }

  import Cisco-IOS-XR-ifmgr-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ethernet-lldp package configuration.

     This module contains definitions
     for the following management objects:
       lldp: Enable LLDP, or configure global LLDP subcommands

     This YANG module augments the
       Cisco-IOS-XR-ifmgr-cfg
     module with configuration data.

     Copyright (c) 2013-2016 by Cisco Systems, Inc.
     All rights reserved.";

  revision "2015-11-09" {
    description
      "IOS XR 6.0 revision.";
  }


  container lldp {
    description "Enable LLDP, or configure global LLDP subcommands";

    container tlv-select {
      presence "Indicates a tlv-select node is configured.";
      description "Selection of LLDP TLVs to disable";

      container system-name {
        description "System Name TLV";
        leaf disable {
          type boolean;
          default "false";
          description "disable System Name TLV";
        }
      }

      container port-description {
        description "Port Description TLV";
        leaf disable {
          type boolean;
          default "false";
          description "disable Port Description TLV";
        }
      }

      container system-description {
        description "System Description TLV";
        leaf disable {
          type boolean;
          default "false";
          description "disable System Description TLV";
        }
      }

      container system-capabilities {
        description "System Capabilities TLV";
        leaf disable {
          type boolean;
          default "false";
          description "disable System Capabilities TLV";
        }
      }

      container management-address {
        description "Management Address TLV";
        leaf disable {
          type boolean;
          default "false";
          description "disable Management Address TLV";
        }
      }
      leaf tlv-select-enter {
        type boolean;
        mandatory true;
        description "enter lldp tlv-select submode";
      }
    }
    leaf holdtime {
      type uint32 {
        range "0..65535";
      }
      description
        "Length  of time  (in sec) that receiver must
        keep this packet";
    }
    leaf extended-show-width {
      type boolean;
      default "false";
      description
        "Enable or disable LLDP Show LLDP Neighbor
        Extended Width";
    }
    leaf enable-subintf {
      type boolean;
      default "false";
      description
        "Enable or disable LLDP on Sub-interfaces as well
        globally";
    }
    leaf timer {
      type uint32 {
        range "5..65534";
      }
      default "30";
      description
        "Specify the rate at which LLDP packets are sent
        (in sec)";
    }
    leaf reinit {
      type uint32 {
        range "2..5";
      }
      default "2";
      description
        "Delay (in sec) for LLDP initialization on any
        interface";
    }
    leaf enable {
      type boolean;
      default "false";
      description "Enable or disable LLDP globally";
    }
  }

  augment "/a1:interface-configurations/a1:interface-configuration" {

    container lldp {
      presence "Indicates a lldp node is configured.";
      description "Disable LLDP TX or RX";

      container transmit {
        description "Disable LLDP TX";
        leaf disable {
          type boolean;
          default "false";
          description "disable LLDP TX";
        }
      }

      container receive {
        description "Disable LLDP RX";
        leaf disable {
          type boolean;
          default "false";
          description "disable LLDP RX";
        }
      }
      leaf lldp-intf-enter {
        type boolean;
        mandatory true;
        description "enter LLDP interface submode";
      }
    }
    description
      "This augment extends the configuration data of
      'Cisco-IOS-XR-ifmgr-cfg'";
  }
}
