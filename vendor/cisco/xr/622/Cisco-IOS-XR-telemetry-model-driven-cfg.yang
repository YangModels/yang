module Cisco-IOS-XR-telemetry-model-driven-cfg {

  /*** NAMESPACE / PREFIX DEFINITION ***/

  namespace "http://cisco.com/ns/yang"+
    "/Cisco-IOS-XR-telemetry-model-driven-cfg";


  prefix "telemetry-model-driven-cfg";

  /*** LINKAGE (IMPORTS / INCLUDES) ***/

  import ietf-inet-types { prefix "inet"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR telemetry-model-driven package configuration.

     This module contains definitions
     for the following management objects:
       telemetry-model-driven: Model Driven Telemetry configuration

     Copyright (c) 2013-2016 by Cisco Systems, Inc.
     All rights reserved.";

  revision "2017-01-30" {
    description
      "Updated version for source-interface/vrf";
  }

  revision "2015-11-09" {
    description
      "IOS XR 6.0 revision.";
  }

  typedef Proto-type {
    type enumeration {
      enum grpc {
        value 1;
        description "GRPC";
      }
      enum tcp {
        value 2;
        description "tcp";
      }
    }
    description "Proto type";
  }
  typedef Encode-type {
    type enumeration {
      enum gpb {
        value 2;
        description "GPB";
      }
      enum self-describing-gpb {
        value 3;
        description "SELF DESCRIBING GPB";
      }
    }
    description "Encode type";
  }

  grouping ENCODING {
    description "Common node of ipv6-destination, ipv4-destination";
    leaf encoding {
      type Encode-type;
      description
        "Encoding used to transmit telemetry data to the
        collector";
    }
  }

  grouping PROTOCOL {
    description "Common node of ipv6-destination, ipv4-destination";

    container protocol {
      presence "Indicates a protocol node is configured.";
      description
        "Transport Protocol used to transmit telemetry
        data to the collector";
      leaf protocol {
        type Proto-type;
        mandatory true;
        description "protocol";
      }
      leaf tls-hostname {
        type string;
        description "tls hostname";
      }
      leaf no-tls {
        type int32;
        default "0";
        description "no tls";
      }
      leaf packetsize {
        type uint32 {
          range "484..65507";
        }
        default "1472";
        description "udp packetsize";
      }
    }
  }

  container telemetry-model-driven {
    description "Model Driven Telemetry configuration";

    container sensor-groups {
      description "Sensor group configuration";

      list sensor-group {
        key "sensor-group-identifier";
        description "Sensor group configuration";

        container sensor-paths {
          description "Sensor path configuration";

          list sensor-path {
            key "telemetry-sensor-path";
            description "Sensor path configuration";
            leaf telemetry-sensor-path {
              type string;
              description "Sensor Path";
            }
          }
        }
        leaf sensor-group-identifier {
          type xr:Cisco-ios-xr-string;
          description "The identifier for this group";
        }
      }
    }

    container subscriptions {
      description "Streaming Telemetry Subscription";

      list subscription {
        key "subscription-identifier";
        description "Streaming Telemetry Subscription";

        container sensor-profiles {
          description "Associate Sensor Groups with Subscription";

          list sensor-profile {
            key "sensorgroupid";
            description "Associate Sensor Group with Subscription";
            leaf strict-timer {
              type empty;
              description "use strict timer";
            }
            leaf sample-interval {
              type uint32 {
                range "0..4294967295";
              }
              units "millisecond";
              description "Sample interval in milliseconds";
            }
            leaf sensorgroupid {
              type xr:Cisco-ios-xr-string;
              description
                "Reference to the telemetry sensor group name";
            }
          }
        }

        container destination-profiles {
          description
            "Associate Destination Groups with Subscription";

          list destination-profile {
            key "destination-id";
            description
              "Associate Destination Group with Subscription";
            leaf destination-id {
              type xr:Cisco-ios-xr-string;
              description
                "Destination Id to associate with
                Subscription";
            }
          }
        }
        leaf source-interface {
          type xr:Interface-name;
          description
            "Source address to use for streaming telemetry
            information";
        }
        leaf subscription-identifier {
          type xr:Cisco-ios-xr-string;
          description "Subscription identifier string";
        }
      }
    }

    container destination-groups {
      description "Destination Group configuration";

      list destination-group {
        key "destination-id";
        description "Destination Group";

        container ipv6-destinations {
          description "Destination address configuration";

          list ipv6-destination {
            key "ipv6-address destination-port";
            description "destination IP address";
            leaf ipv6-address {
              type inet:ipv6-address-no-zone;
              description "Destination IPv6 address";
            }
            leaf destination-port {
              type xr:Cisco-ios-xr-port-number;
              description "destination port";
            }
            uses ENCODING;
            uses PROTOCOL;
          }
        }

        container ipv4-destinations {
          description "Destination address configuration";

          list ipv4-destination {
            key "ipv4-address destination-port";
            description "destination IP address";
            leaf ipv4-address {
              type inet:ipv4-address-no-zone;
              description "Destination IPv4 address";
            }
            leaf destination-port {
              type xr:Cisco-ios-xr-port-number;
              description "destination port";
            }
            uses ENCODING;
            uses PROTOCOL;
          }
        }
        leaf vrf {
          type xr:Cisco-ios-xr-string {
            length "1..32";
          }
          description "Vrf for the destination group";
        }
        leaf destination-id {
          type xr:Cisco-ios-xr-string;
          description "destination group id string";
        }
      }
    }
    leaf enable {
      type empty;
      description "Enable Model Driven Telemetry";
    }
  }
}
