submodule Cisco-IOS-XR-infra-statsd-oper-sub1 {

  belongs-to Cisco-IOS-XR-infra-statsd-oper {
    prefix Cisco-IOS-XR-infra-statsd-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR infra-statsd package operational data.

     Copyright (c) 2013-2016 by Cisco Systems, Inc.
     All rights reserved.";

  revision "2015-11-09" {
    description
      "IOS XR 6.0 revision.";
  }


  grouping STATSDBAG-DATARATE {
    description "Datarate information";
    leaf input-data-rate {
      type uint64;
      units "bit/s";
      description "Input data rate in 1000's of bps";
    }
    leaf input-packet-rate {
      type uint64;
      units "packet/s";
      description "Input packets per second";
    }
    leaf output-data-rate {
      type uint64;
      units "bit/s";
      description "Output data rate in 1000's of bps";
    }
    leaf output-packet-rate {
      type uint64;
      units "packet/s";
      description "Output packets per second";
    }
    leaf peak-input-data-rate {
      type uint64;
      description "Peak input data rate";
    }
    leaf peak-input-packet-rate {
      type uint64;
      description "Peak input packet rate";
    }
    leaf peak-output-data-rate {
      type uint64;
      description "Peak output data rate";
    }
    leaf peak-output-packet-rate {
      type uint64;
      description "Peak output packet rate";
    }
    leaf bandwidth {
      type uint32;
      units "kbit/s";
      description "Bandwidth (in kbps)";
    }
    leaf load-interval {
      type uint32;
      description "Number of 30-sec intervals less one";
    }
    leaf output-load {
      type uint8;
      description "Output load as fraction of 255";
    }
    leaf input-load {
      type uint8;
      description "Input load as fraction of 255";
    }
    leaf reliability {
      type uint8;
      description "Reliability coefficient";
    }
  }

  grouping IFSTATSBAG-GENERIC {
    description "Generic set of interface counters";
    leaf packets-received {
      type uint64;
      description "Packets received";
    }
    leaf bytes-received {
      type uint64;
      units "byte";
      description "Bytes received";
    }
    leaf packets-sent {
      type uint64;
      description "Packets sent";
    }
    leaf bytes-sent {
      type uint64;
      units "byte";
      description "Bytes sent";
    }
    leaf multicast-packets-received {
      type uint64;
      description "Multicast packets received";
    }
    leaf broadcast-packets-received {
      type uint64;
      description "Broadcast packets received";
    }
    leaf multicast-packets-sent {
      type uint64;
      description "Multicast packets sent";
    }
    leaf broadcast-packets-sent {
      type uint64;
      description "Broadcast packets sent";
    }
    leaf output-drops {
      type uint32;
      description "Total output drops";
    }
    leaf output-queue-drops {
      type uint32;
      description "Output queue drops";
    }
    leaf input-drops {
      type uint32;
      description "Total input drops";
    }
    leaf input-queue-drops {
      type uint32;
      description "Input queue drops";
    }
    leaf runt-packets-received {
      type uint32;
      description "Received runt packets";
    }
    leaf giant-packets-received {
      type uint32;
      description "Received giant packets";
    }
    leaf throttled-packets-received {
      type uint32;
      description "Received throttled packets";
    }
    leaf parity-packets-received {
      type uint32;
      description "Received parity packets";
    }
    leaf unknown-protocol-packets-received {
      type uint32;
      description "Unknown protocol packets received";
    }
    leaf input-errors {
      type uint32;
      description "Total input errors";
    }
    leaf crc-errors {
      type uint32;
      description "Input CRC errors";
    }
    leaf input-overruns {
      type uint32;
      description "Input overruns";
    }
    leaf framing-errors-received {
      type uint32;
      description "Framing-errors received";
    }
    leaf input-ignored-packets {
      type uint32;
      description "Input ignored packets";
    }
    leaf input-aborts {
      type uint32;
      description "Input aborts";
    }
    leaf output-errors {
      type uint32;
      description "Total output errors";
    }
    leaf output-underruns {
      type uint32;
      description "Output underruns";
    }
    leaf output-buffer-failures {
      type uint32;
      description "Output buffer failures";
    }
    leaf output-buffers-swapped-out {
      type uint32;
      description "Output buffers swapped out";
    }
    leaf applique {
      type uint32;
      description "Applique";
    }
    leaf resets {
      type uint32;
      description "Number of board resets";
    }
    leaf carrier-transitions {
      type uint32;
      description "Carrier transitions";
    }
    leaf availability-flag {
      type uint32;
      description "Availability bit mask";
    }
    leaf last-data-time {
      type uint32;
      units "second";
      description
        "Time when counters were last written (in
        seconds)";
    }
    leaf seconds-since-last-clear-counters {
      type uint32;
      units "second";
      description "Number of seconds since last clear counters";
    }
    leaf last-discontinuity-time {
      type uint32;
      units "second";
      description
        "SysUpTime when counters were last reset (in
        seconds)";
    }
    leaf seconds-since-packet-received {
      type uint32;
      units "second";
      description "Seconds since packet received";
    }
    leaf seconds-since-packet-sent {
      type uint32;
      units "second";
      description "Seconds since packet sent";
    }
  }

  grouping IFSTATSBAG-PROTO {
    description "Interface counters per protocol";
    leaf bytes-received {
      type uint64;
      units "byte";
      description "Bytes received";
    }
    leaf packets-received {
      type uint64;
      description "Packets received";
    }
    leaf bytes-sent {
      type uint64;
      units "byte";
      description "Bytes sent";
    }
    leaf packets-sent {
      type uint64;
      description "Packets sent";
    }
    leaf protocol {
      type uint32;
      description "Protocol number";
    }
    leaf last-data-time {
      type uint32;
      units "second";
      description
        "Time when counters were last written (in
        seconds)";
    }
    leaf input-data-rate {
      type uint64;
      units "bit/s";
      description "Input data rate in 1000's of bps";
    }
    leaf input-packet-rate {
      type uint64;
      units "packet/s";
      description "Input packets per second";
    }
    leaf output-data-rate {
      type uint64;
      units "bit/s";
      description "Output data rate in 1000's of bps";
    }
    leaf output-packet-rate {
      type uint64;
      units "packet/s";
      description "Output packets per second";
    }
  }
}
