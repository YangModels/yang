module Cisco-IOS-XR-aaa-aaacore-cfg {

  /*** NAMESPACE / PREFIX DEFINITION ***/

  namespace "http://cisco.com/ns/yang/Cisco-IOS-XR-aaa-aaacore-cfg";


  prefix "aaa-aaacore-cfg";

  /*** LINKAGE (IMPORTS / INCLUDES) ***/

  import Cisco-IOS-XR-types { prefix "xr"; }

  import Cisco-IOS-XR-aaa-lib-datatypes { prefix "dt1"; }

  import Cisco-IOS-XR-aaa-lib-cfg { prefix "a1"; }

  import Cisco-IOS-XR-ifmgr-cfg { prefix "a2"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR aaa-aaacore package configuration.

     This YANG module augments the
       Cisco-IOS-XR-aaa-lib-cfg,
       Cisco-IOS-XR-ifmgr-cfg
     modules with configuration data.

     Copyright (c) 2013-2016 by Cisco Systems, Inc.
     All rights reserved.";

  revision "2015-11-09" {
    description
      "IOS XR 6.0 revision.";
  }

  typedef Nas-port-value {
    type enumeration {
      enum async {
        value 0;
        description "Async(0)";
      }
      enum sync {
        value 1;
        description "Sync(1)";
      }
      enum isdn {
        value 2;
        description "ISDN(2)";
      }
      enum isdn-async-v120 {
        value 3;
        description "ISDN Async V120(3)";
      }
      enum isdn-async-v110 {
        value 4;
        description "ISDN Async V110(4)";
      }
      enum virtual {
        value 5;
        description "Virtual(5)";
      }
      enum isdn-async-piafs {
        value 6;
        description "ISDN Async PIAFS(6)";
      }
      enum x75 {
        value 9;
        description "X75(9)";
      }
      enum ethernet {
        value 15;
        description "Ethernet(15)";
      }
      enum pppoa {
        value 30;
        description "PPPoA(30)";
      }
      enum pppoeoa {
        value 31;
        description "PPPoEoA(31)";
      }
      enum pppoeoe {
        value 32;
        description "PPPoEoE(32)";
      }
      enum pppoeovlan {
        value 33;
        description "PPPoEoVLAN(33)";
      }
      enum pppoeoqinq {
        value 34;
        description "PPPoEoQinQ(34)";
      }
      enum virtual-pppoeoe {
        value 35;
        description "Virtual PPPoEoE(35)";
      }
      enum virtual-pppoeovlan {
        value 36;
        description "Virtual PPPoEoVLAN(36)";
      }
      enum virtual-pppoeoqinaq {
        value 37;
        description "Virtual PPPoEoQinQ(37)";
      }
      enum ipsec {
        value 38;
        description "IPSEC(38)";
      }
      enum ipoeoe {
        value 39;
        description "IPOEOE(39)";
      }
      enum ipoeovlan {
        value 40;
        description "IPOEOVLAN(40)";
      }
      enum ipoeoqinq {
        value 41;
        description "IPOEOQINQ(41)";
      }
      enum virtual-ipoeoe {
        value 42;
        description "VIRTUAL IPOEOE(42)";
      }
      enum virtual-ipoeovlan {
        value 43;
        description "VIRTUAL IPOEOVLAN(43)";
      }
      enum virtual-ipoeoqinq {
        value 44;
        description "VIRTUAL IPOEOQINQ(44)";
      }
    }
    description "Nas port value";
  }
  typedef Aaa-list {
    type string {
      pattern "(subscriber)|(service)|(policy-if)|(prepaid)|(dot1x)";
    }
    description
      "subscriber:Set AAA lists for Subscriber, service
      :Set AAA lists for Service, policy-if:Set
      policy-if, prepaid:Set prepaid, dot1x:Set dot1x
      method list";
  }
  typedef Aaa-service-accounting {
    type enumeration {
      enum none {
        value 0;
        description "None";
      }
      enum extended {
        value 1;
        description "Extended";
      }
      enum brief {
        value 2;
        description "Brief";
      }
    }
    description "Aaa service accounting";
  }

  grouping FORMAT-TABLE {
    description
      "Common node of nas-port-id, calling-station,
      called-station";

    container formats {
      description "AAA nas-port-id attribute format";

      list format {
        key "type";
        description "nas-port-id attribute format";
        leaf type {
          type uint32 {
            range "0..45";
          }
          description "Nas-Port-Type value to apply format name on";
        }
        leaf format-name {
          type string;
          mandatory true;
          description "AAA nas-port attribute format";
        }
      }
    }
  }

  augment "/a2:interface-configurations/a2:interface-configuration" {

    container aaa-table {
      description "AAA configuration";

      container radius {
        description "AAA radius configuration";

        container attribute {
          description "AAA radius attribute";
          leaf nas-port-type {
            type Nas-port-value;
            description "AAA nas-port-type attribute";
          }
        }
      }
    }
    description
      "This augment extends the configuration data of
      'Cisco-IOS-XR-ifmgr-cfg'";
  }

  augment "/a1:aaa" {

    container aaa-subscriber {
      description "AAA subscriber";

      container policy-if-authors {
        description "AAA authorization policy";

        list policy-if-author {
          key "type listname";
          description "Configurations related to authorization";
          leaf type {
            type Aaa-list;
            description "Set authorization lists";
          }
          leaf listname {
            type xr:Cisco-ios-xr-string;
            description "Named authorization list";
          }
          leaf-list method {
            type dt1:Aaa-method;
            min-elements "1";
            max-elements "4";
            description "Method Types";
          }
          leaf-list server-group-name {
            type string;
            max-elements "4";
            description "Server group names";
          }
        }
      }

      container accountings {
        description "AAA accounting";

        list accounting {
          key "type listname";
          description "Configurations related to accounting";
          leaf type {
            type Aaa-list;
            description "Set accounting lists";
          }
          leaf listname {
            type xr:Cisco-ios-xr-string;
            description "Named accounting list";
          }
          leaf broadcast {
            type dt1:Aaa-accounting-broadcast;
            mandatory true;
            description "Broadcast";
          }
          leaf-list method {
            type dt1:Aaa-method;
            max-elements "4";
            description "Method Types";
          }
          leaf-list server-group-name {
            type string;
            max-elements "4";
            description "Server group names";
          }
        }
      }

      container service-accounting {
        description "Set accounting parameters for Service";
        leaf type {
          type Aaa-service-accounting;
          description
            "Send extended/brief service accounting records";
        }
      }

      container prepaid-authors {
        description "AAA authorization prepaid";

        list prepaid-author {
          key "type listname";
          description "Configurations related to authorization";
          leaf type {
            type Aaa-list;
            description "Set authorization lists";
          }
          leaf listname {
            type xr:Cisco-ios-xr-string;
            description "Named authorization list";
          }
          leaf-list method {
            type dt1:Aaa-method;
            min-elements "1";
            max-elements "4";
            description "Method Types";
          }
          leaf-list server-group-name {
            type string;
            max-elements "4";
            description "Server group names";
          }
        }
      }

      container authorizations {
        description "AAA authorization";

        list authorization {
          key "type listname";
          description "Configurations related to authorization";
          leaf type {
            type Aaa-list;
            description "Set authorization lists";
          }
          leaf listname {
            type xr:Cisco-ios-xr-string;
            description "Named authorization list";
          }
          leaf-list method {
            type dt1:Aaa-method;
            min-elements "1";
            max-elements "4";
            description "Method Types";
          }
          leaf-list server-group-name {
            type string;
            max-elements "4";
            description "Server group names";
          }
        }
      }

      container authentications {
        description "AAA authentication";

        list authentication {
          key "type listname";
          description "Configurations related to authentication";
          leaf type {
            type Aaa-list;
            description "Set authentication lists";
          }
          leaf listname {
            type xr:Cisco-ios-xr-string;
            description "Named authentication list";
          }
          leaf-list method {
            type dt1:Aaa-method;
            min-elements "1";
            max-elements "4";
            description "Method Types";
          }
          leaf-list server-group-name {
            type string;
            max-elements "4";
            description "Server group names";
          }
        }
      }
    }
    description
      "This augment extends the configuration data of
      'Cisco-IOS-XR-aaa-lib-cfg'";
  }

  augment "/a1:aaa" {

    container aaa-mobile {
      description "AAA Mobile";

      container mobiles {
        description "AAA Mobile Accounting";

        list mobile {
          key "listname";
          description "Configurations related to accounting";
          leaf listname {
            type xr:Cisco-ios-xr-string;
            description "Named accounting list";
          }
          leaf broadcast {
            type dt1:Aaa-accounting-broadcast;
            mandatory true;
            description "Broadcast";
          }
          leaf-list method {
            type dt1:Aaa-method;
            max-elements "4";
            description "Method Types";
          }
          leaf-list server-group-name {
            type string;
            max-elements "4";
            description "Server group names";
          }
        }
      }
    }
    description
      "This augment extends the configuration data of
      'Cisco-IOS-XR-aaa-lib-cfg'";
  }

  augment "/a1:aaa" {

    container aaa-dot1x {
      description "AAA Dot1x";

      container authentications {
        description "AAA authentication";

        list authentication {
          key "type listname";
          description "Configurations related to authentication";
          leaf type {
            type Aaa-list;
            description "Set authentication lists";
          }
          leaf listname {
            type xr:Cisco-ios-xr-string;
            description "Named authentication list";
          }
          leaf-list method {
            type dt1:Aaa-method;
            min-elements "1";
            max-elements "4";
            description "Method Types";
          }
          leaf-list server-group-name {
            type string;
            max-elements "4";
            description "Server group names";
          }
        }
      }
    }
    description
      "This augment extends the configuration data of
      'Cisco-IOS-XR-aaa-lib-cfg'";
  }

  augment "/a1:aaa" {

    container radius-attribute {
      description "AAA RADIUS attribute configurations";

      container nas-port-id {
        description "AAA nas-port-id attribute";
        uses FORMAT-TABLE;
      }

      container calling-station {
        description "AAA calling station id attribute";
        uses FORMAT-TABLE;
      }

      container called-station {
        description "AAA called station id attribute";
        uses FORMAT-TABLE;
      }

      container nas-port {
        description "AAA nas-port-id attribute";

        container format-extendeds {
          description "AAA nas-port-id attribute format";

          list format-extended {
            key "value type";
            description "nas-port-id extended attribute";
            leaf format-identifier {
              type xr:Cisco-ios-xr-string {
                length "1..32";
              }
              description
                "A 32 character string representing the
                format to be used";
            }
            leaf value {
              type xr:Cisco-ios-xr-string;
              description "format type";
            }
            leaf type {
              type uint32 {
                range "0..45";
              }
              description "AAA nas-port attribute format";
            }
          }
        }
      }

      container format-others {
        description "AAA nas-port-id attribute format";

        list format-other {
          key "nas-port-type-name";
          description "Other configs";
          leaf nas-port-type-name {
            type xr:Cisco-ios-xr-string;
            description
              "Nas-Port-Type value to apply format name on";
          }
          leaf attribute-config1 {
            type string;
            description "Argument1";
          }
          leaf attribute-config2 {
            type string;
            description "Argument2";
          }
          leaf attribute-config3 {
            type string;
            description "Argument3";
          }
          leaf attribute-config4 {
            type string;
            description "Argument4";
          }
          leaf attribute-config5 {
            type string;
            description "Argument5";
          }
          leaf attribute-config6 {
            type string;
            description "Argument6";
          }
          leaf attribute-config7 {
            type string;
            description "Argument7";
          }
          leaf attribute-config8 {
            type string;
            description "Argument8";
          }
          leaf attribute-config9 {
            type string;
            description "Argument9";
          }
          leaf attribute-config10 {
            type string;
            description "Argument10";
          }
          leaf attribute-config11 {
            type string;
            description "Argument11";
          }
          leaf attribute-config12 {
            type string;
            description "Argument12";
          }
          leaf attribute-config13 {
            type string;
            description "Argument13";
          }
          leaf attribute-config14 {
            type string;
            description "Argument14";
          }
          leaf attribute-config15 {
            type string;
            description "Argument15";
          }
          leaf attribute-config16 {
            type string;
            description "Argument16";
          }
          leaf attribute-config17 {
            type string;
            description "Argument17";
          }
          leaf attribute-config18 {
            type string;
            description "Argument18";
          }
          leaf attribute-config19 {
            type uint32 {
              range "1..253";
            }
            description "Argument19";
          }
        }
      }
    }
    description
      "This augment extends the configuration data of
      'Cisco-IOS-XR-aaa-lib-cfg'";
  }
}
