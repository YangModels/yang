module Cisco-IOS-XR-kim-tpa-cfg {

  /*** NAMESPACE / PREFIX DEFINITION ***/

  namespace "http://cisco.com/ns/yang/Cisco-IOS-XR-kim-tpa-cfg";


  prefix "kim-tpa-cfg";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR kim-tpa package configuration.

     This module contains definitions
     for the following management objects:
       tpa: tpa configuration commands

     Copyright (c) 2013-2016 by Cisco Systems, Inc.
     All rights reserved.";

  revision "2015-11-09" {
    description
      "IOS XR 6.0 revision.";
  }


  grouping UPDATE-SOURCE {
    description "Common node of ipv4, ipv6";
    leaf update-source {
      type xr:Interface-name;
      description "Interface name for source address";
    }
  }

  grouping DEFAULT-ROUTE {
    description "Common node of ipv4, ipv6";
    leaf default-route {
      type string;
      description "Default interface used for routing";
    }
  }

  container tpa {
    description "tpa configuration commands";

    container vrf-names {
      description "VRF container";

      list vrf-name {
        key "vrf-name";
        description "VRF name";

        container east-west-names {
          description "EastWest container";

          list east-west-name {
            key "east-west-name";
            description "East West interface";
            leaf east-west-name {
              type xr:Cisco-ios-xr-string;
              description "Interface";
            }
            leaf vrf {
              type string;
              description "VRF name";
            }
            leaf interface {
              type string;
              description "Interface";
            }
          }
        }

        container address-family {
          description "Address family";

          container ipv6 {
            description "IPv6 configuration";
            uses DEFAULT-ROUTE;
            uses UPDATE-SOURCE;
          }

          container ipv4 {
            description "IPv4 configuration";
            uses DEFAULT-ROUTE;
            uses UPDATE-SOURCE;
          }
        }
        leaf vrf-name {
          type xr:Cisco-ios-xr-string {
            length "1..32";
          }
          description "VRF name";
        }
      }
    }

    container statistics {
      description "Statistics";
      leaf statistics-update-frequency {
        type int32;
        units "second";
        description "Statistics update frequency into Linux";
      }
    }
  }
}
