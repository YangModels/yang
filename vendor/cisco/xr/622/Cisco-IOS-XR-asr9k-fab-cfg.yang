module Cisco-IOS-XR-asr9k-fab-cfg {

  /*** NAMESPACE / PREFIX DEFINITION ***/

  namespace "http://cisco.com/ns/yang/Cisco-IOS-XR-asr9k-fab-cfg";


  prefix "asr9k-fab-cfg";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR asr9k-fab package configuration.

     This module contains definitions
     for the following management objects:
       fab-vqi-config: Configure Fabric

     Copyright (c) 2013-2016 by Cisco Systems, Inc.
     All rights reserved.";

  revision "2015-11-09" {
    description
      "IOS XR 6.0 revision.";
  }


  container fab-vqi-config {
    description "Configure Fabric";

    container operates {
      description "none";

      list operate {
        key "id1";
        description "none";
        leaf id1 {
          type xr:Cisco-ios-xr-string;
          description "none";
        }
        leaf id1-xr {
          type int32;
          description "none";
        }
        leaf id2 {
          type int32;
          description "none";
        }
      }
    }
  }
}
