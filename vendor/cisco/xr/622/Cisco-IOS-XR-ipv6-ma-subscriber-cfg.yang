module Cisco-IOS-XR-ipv6-ma-subscriber-cfg {

  /*** NAMESPACE / PREFIX DEFINITION ***/

  namespace "http://cisco.com/ns/yang"+
    "/Cisco-IOS-XR-ipv6-ma-subscriber-cfg";


  prefix "ipv6-ma-subscriber-cfg";

  /*** LINKAGE (IMPORTS / INCLUDES) ***/

  import Cisco-IOS-XR-types { prefix "xr"; }

  import Cisco-IOS-XR-subscriber-infra-tmplmgr-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ipv6-ma-subscriber package configuration.

     This YANG module augments the
       Cisco-IOS-XR-subscriber-infra-tmplmgr-cfg
     module with configuration data.

     Copyright (c) 2013-2016 by Cisco Systems, Inc.
     All rights reserved.";

  revision "2017-01-11" {
    description
      "Descriptions updated.";
  }

  revision "2015-01-07" {
    description
      "IOS XR 5.3.1 revision.";
  }


  grouping IPV6-NETWORK {
    description
      "Common node of ip-subscriber, ppp,
      subscriber-service";

    container ipv6-network {
      description "Interface IPv6 Network configuration data";

      container addresses {
        description "Set the IPv6 address of an interface";

        container auto-configuration {
          description "Auto IPv6 Interface Configuration";
          leaf enable {
            type empty;
            description
              "The flag to enable auto ipv6 interface
              configuration";
          }
        }
      }
      leaf mtu {
        type uint32 {
          range "1280..65535";
        }
        units "byte";
        description "MTU Setting of Interface";
      }
      leaf rpf {
        type boolean;
        description "TRUE if enabled, FALSE if disabled";
      }
      leaf unreachables {
        type empty;
        description "Override Sending of ICMP Unreachable Messages";
      }
    }
  }

  augment "/a1:dynamic-template/a1:subscriber-services"+
    "/a1:subscriber-service" {
    description
      "This augment extends the configuration data of
      'Cisco-IOS-XR-subscriber-infra-tmplmgr-cfg'";
    uses IPV6-NETWORK;
  }

  augment "/a1:dynamic-template/a1:ppps/a1:ppp" {
    description
      "This augment extends the configuration data of
      'Cisco-IOS-XR-subscriber-infra-tmplmgr-cfg'";
    uses IPV6-NETWORK;
  }

  augment "/a1:dynamic-template/a1:ip-subscribers/a1:ip-subscriber" {
    description
      "This augment extends the configuration data of
      'Cisco-IOS-XR-subscriber-infra-tmplmgr-cfg'";
    uses IPV6-NETWORK;
  }
}
