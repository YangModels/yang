module Cisco-IOS-XR-subscriber-pppoe-ma-oper {

  /*** NAMESPACE / PREFIX DEFINITION ***/

  namespace "http://cisco.com/ns/yang"+
    "/Cisco-IOS-XR-subscriber-pppoe-ma-oper";


  prefix "subscriber-pppoe-ma-oper";

  /*** LINKAGE (IMPORTS / INCLUDES) ***/

  import ietf-yang-types { prefix "yang"; }

  import Cisco-IOS-XR-types { prefix "xr"; }

  include Cisco-IOS-XR-subscriber-pppoe-ma-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR subscriber-pppoe-ma package operational data.

     This module contains definitions
     for the following management objects:
       pppoe: PPPoE operational data

     Copyright (c) 2013-2016 by Cisco Systems, Inc.
     All rights reserved.";

  revision "2015-11-09" {
    description
      "IOS XR 6.0 revision.";
  }


  container pppoe {
    config false;
    description "PPPoE operational data";

    container access-interface-statistics {
      description "PPPoE access interface statistics information";

      list access-interface-statistic {
        key "interface-name";
        description
          "Statistics information for a PPPoE-enabled
          access interface";
        leaf interface-name {
          type xr:Interface-name;
          description "PPPoE Access Interface";
        }
        uses PPPOE-MA-ACCESS-INTERFACE-STATS-INFO;
      }
    }

    container nodes {
      description "Per-node PPPoE operational data";

      list node {
        key "node-name";
        description "PPPoE operational data for a particular node";

        container statistics {
          description "PPPoE statistics for a given node";
          uses PPPOE-MA-TOTAL-STATS-INFO;
        }

        container access-interface {
          description "PPPoE access interface information";

          container summaries {
            description
              "PPPoE access interface summary information";

            list summary {
              key "interface-name";
              description
                "Summary information for a PPPoE-enabled
                access interface";
              leaf interface-name {
                type xr:Interface-name;
                description "PPPoE Access Interface";
              }
              uses PPPOE-MA-ACCESS-INTERFACE-INFO;
            }
          }
        }

        container interfaces {
          description "Per interface PPPoE operational data";

          list interface {
            key "interface-name";
            description "Data for a PPPoE interface";
            leaf interface-name {
              type xr:Interface-name;
              description "PPPoE Interface";
            }
            uses PPPOE-MA-INTERFACE-INFO;
          }
        }

        container bba-groups {
          description "PPPoE BBA-Group information";

          list bba-group {
            key "bba-group-name";
            description "PPPoE BBA-Group information";

            container limit-config {
              description
                "BBA-Group limit configuration information";
              uses PPPOE-MA-LIMIT-CONFIG-INFO;
            }

            container limits {
              description "PPPoE session limit information";

              list limit {
                description "PPPoE session limit state";
                leaf interface-name {
                  type xr:Interface-name;
                  description "Access Interface";
                }
                leaf mac-address {
                  type yang:mac-address;
                  description "MAC address";
                }
                leaf iwf {
                  type boolean;
                  description "IWF flag";
                }
                leaf circuit-id {
                  type xr:Cisco-ios-xr-string;
                  description "Circuit ID";
                }
                leaf remote-id {
                  type xr:Cisco-ios-xr-string;
                  description "Remote ID";
                }
                leaf outer-vlan-id {
                  type uint32 {
                    range "0..4095";
                  }
                  description "Outer VLAN ID";
                }
                leaf inner-vlan-id {
                  type uint32 {
                    range "0..4095";
                  }
                  description "Inner VLAN ID";
                }
                uses PPPOE-MA-LIMIT-INFO;
              }
            }

            container throttles {
              description "PPPoE throttle information";

              list throttle {
                description "PPPoE session throttle state";
                leaf interface-name {
                  type xr:Interface-name;
                  description "Access Interface";
                }
                leaf mac-address {
                  type yang:mac-address;
                  description "MAC address";
                }
                leaf iwf {
                  type boolean;
                  description "IWF flag";
                }
                leaf circuit-id {
                  type xr:Cisco-ios-xr-string;
                  description "Circuit ID";
                }
                leaf remote-id {
                  type xr:Cisco-ios-xr-string;
                  description "Remote ID";
                }
                leaf outer-vlan-id {
                  type uint32 {
                    range "0..4095";
                  }
                  description "Outer VLAN ID";
                }
                leaf inner-vlan-id {
                  type uint32 {
                    range "0..4095";
                  }
                  description "Inner VLAN ID";
                }
                uses PPPOE-MA-THROTTLE-INFO;
              }
            }

            container throttle-config {
              description
                "BBA-Group throttle configuration information";
              uses PPPOE-MA-THROTTLE-CONFIG-INFO;
            }
            leaf bba-group-name {
              type xr:Cisco-ios-xr-string;
              description "BBA Group";
            }
          }
        }

        container summary-total {
          description "PPPoE statistics for a given node";
          uses PPPOE-MA-SUMMARY-TOTAL-INFO;
        }
        leaf node-name {
          type xr:Node-id;
          description "Node";
        }
      }
    }
  }
}
