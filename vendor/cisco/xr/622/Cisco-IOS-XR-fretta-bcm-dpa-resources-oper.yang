module Cisco-IOS-XR-fretta-bcm-dpa-resources-oper {

  /*** NAMESPACE / PREFIX DEFINITION ***/

  namespace "http://cisco.com/ns/yang"+
    "/Cisco-IOS-XR-fretta-bcm-dpa-resources-oper";


  prefix "fretta-bcm-dpa-resources-oper";

  /*** LINKAGE (IMPORTS / INCLUDES) ***/

  import Cisco-IOS-XR-types { prefix "xr"; }

  include Cisco-IOS-XR-fretta-bcm-dpa-resources-oper-sub2 {
    revision-date 2015-11-09;
  }

  include Cisco-IOS-XR-fretta-bcm-dpa-resources-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR fretta-bcm-dpa-resources package operational data.

     This module contains definitions
     for the following management objects:
       dpa: Stats Data

     Copyright (c) 2013-2016 by Cisco Systems, Inc.
     All rights reserved.";

  revision "2015-11-09" {
    description
      "IOS XR 6.0 revision.";
  }

  typedef Max-trap-s {
    type uint32 {
      range "0..4294967295";
    }
    description "Max trap s";
  }
  typedef Max-lc-intf-hand-les {
    type uint32 {
      range "0..4294967295";
    }
    description "Max lc intf hand les";
  }
  typedef Max-re-source-s-table {
    type uint32 {
      range "0..109";
    }
    description "Max re source s table";
  }

  container dpa {
    config false;
    description "Stats Data";

    container resources {
      description "DPA Resources Data";

      container nodes {
        description "DPA data for available nodes";

        list node {
          key "node-name";
          description "DPA operational data for a particular node";

          container table-datas {
            description "DPA Resources table";

            list table-data {
              key "resource";
              description "Resources table";
              leaf resource {
                type Max-re-source-s-table;
                description "Resource type";
              }
              uses DPA-SYSDB-TABLE-RESOURCE;
            }
          }
          leaf node-name {
            type xr:Node-id;
            description "Node ID";
          }
        }
      }
    }

    container stats {
      description "Voq or Trap Data";

      container nodes {
        description "DPA data for available nodes";

        list node {
          key "node-name";
          description "DPA operational data for a particular node";

          container asic-statistics {
            description "ASIC statistics table";

            container asic-statistics-for-npu-ids {
              description "ASIC statistics";

              list asic-statistics-for-npu-id {
                key "npu-id";
                description "ASIC statistics for a particular NPU";
                leaf npu-id {
                  type int32;
                  description "NPU number";
                }
                uses FIA-EDM-STATS-BRIEF-INFO;
              }
            }

            container asic-statistics-detail-for-npu-ids {
              description "Detailed ASIC statistics";

              list asic-statistics-detail-for-npu-id {
                key "npu-id";
                description
                  "Detailed ASIC statistics for a particular
                  NPU";
                leaf npu-id {
                  type int32;
                  description "NPU number";
                }
                uses FIA-EDM-STATS-INFO;
              }
            }
          }

          container npu-numbers {
            description "Ingress Stats";

            list npu-number {
              key "npu-id";
              description "Stats for a particular npu";

              container display {
                description "show npu specific voq or trap stats";

                container base-numbers {
                  description
                    "Voq stats grouped by voq base numbers";

                  list base-number {
                    key "base-number";
                    description
                      "Voq Base Number for a particular voq";
                    leaf base-number {
                      type Max-lc-intf-hand-les;
                      description "Interface handle";
                    }
                    uses DPA-VOQ-INTF-PORT;
                  }
                }

                container trap-ids {
                  description "Trap stats for a particular npu";

                  list trap-id {
                    key "trap-id";
                    description "Filter by specific trap id";
                    leaf trap-id {
                      type Max-trap-s;
                      description "Trap ID";
                    }
                    uses DPA-TRAP-STATS;
                  }
                }

                container interface-handles {
                  description
                    "Voq stats grouped by interface handle";

                  list interface-handle {
                    key "interface-handle";
                    description
                      "Voq stats for a particular interface
                      handle";
                    leaf interface-handle {
                      type Max-lc-intf-hand-les;
                      description "Interface Handle";
                    }
                    uses DPA-VOQ-INTF-PORT;
                  }
                }
              }
              leaf npu-id {
                type int32;
                description "Npu number";
              }
            }
          }
          leaf node-name {
            type xr:Node-id;
            description "Node ID";
          }
        }
      }
    }
  }
}
