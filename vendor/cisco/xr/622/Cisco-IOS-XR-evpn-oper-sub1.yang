submodule Cisco-IOS-XR-evpn-oper-sub1 {

  belongs-to Cisco-IOS-XR-evpn-oper {
    prefix Cisco-IOS-XR-evpn-oper;
  }

  /*** LINKAGE (IMPORTS / INCLUDES) ***/

  import ietf-inet-types { prefix "inet"; }

  import ietf-yang-types { prefix "yang"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR evpn package operational data.

     Copyright (c) 2013-2016 by Cisco Systems, Inc.
     All rights reserved.";

  revision "2015-11-09" {
    description
      "IOS XR 6.0 revision.";
  }

  typedef L2vpn-evpn-sc {
    type enumeration {
      enum not-applicable {
        description "Service Carving does not apply";
      }
      enum evi {
        description "Service Carving by EVI";
      }
      enum isid {
        description "Service Carving by ISID";
      }
      enum evpn-bag-sc-type-max {
        description "evpn bag sc type max";
      }
    }
    description "EVPN Ethernet-Segment service carving type";
  }
  typedef L2vpn-evpn-sc-mode {
    type enumeration {
      enum invalid {
        description "Invalid service carving mode";
      }
      enum auto {
        description "Auto service carving mode";
      }
      enum manual {
        description "Manual service carving";
      }
    }
    description "EVPN Ethernet-Segment service carving mode";
  }
  typedef L2vpn-evpn-smac-src {
    type enumeration {
      enum invalid {
        description "Incomplete Configuration";
      }
      enum not-applicable {
        description "Source MAC Not Applicable (EVPN)";
      }
      enum local {
        description "Local";
      }
      enum pbb-bsa {
        description "PBB BSA";
      }
      enum esi {
        description "From ESI";
      }
      enum esi-invalid {
        description "From ESI, Error";
      }
      enum pbb-bsa-overrride {
        description "PBB BSA, no ESI";
      }
    }
    description "L2vpn evpn smac src";
  }
  typedef L2vpn-evpn-lb-mode {
    type enumeration {
      enum invalid-load-balancing {
        description "Invalid load balancing";
      }
      enum single-homed {
        description "Single-homed site or network";
      }
      enum multi-homed-aa-per-flow {
        description
          "Multi-homed access network active/active per
          flow";
      }
      enum multi-homed-aa-per-service {
        description
          "Multi-homed access network active/active per
          service";
      }
    }
    description "L2VPN EVPN load balancing mode";
  }
  typedef L2vpn-evpn-mf-mode {
    type enumeration {
      enum invalid {
        description "Invalid MAC Flushing mode";
      }
      enum tcn-stp {
        description "TCN STP MAC Flushing mode";
      }
      enum mvrp {
        description "MVRP MAC Flushing mode";
      }
    }
    description "L2VPN EVPN MAC flushing mode";
  }
  typedef L2vpn-evpn-rt-origin {
    type enumeration {
      enum invalid {
        description "Incomplete Configuration";
      }
      enum extracted {
        description "From ESI";
      }
      enum configured {
        description "Locally configured";
      }
    }
    description "L2vpn evpn rt origin";
  }
  typedef L2vpn-rg-state {
    type enumeration {
      enum unknown {
        description "Not defined";
      }
      enum active {
        description "Active";
      }
      enum standby {
        description "Standby";
      }
    }
    description "L2vpn rg state";
  }
  typedef L2vpn-evpn-esi {
    type enumeration {
      enum esi-type0 {
        value 0;
        description "ESI type zero";
      }
      enum esi-type1 {
        value 1;
        description "ESI type one";
      }
      enum esi-type2 {
        value 2;
        description "ESI type two";
      }
      enum esi-type3 {
        value 3;
        description "ESI type three";
      }
      enum esi-type4 {
        value 4;
        description "ESI type four";
      }
      enum esi-type5 {
        value 5;
        description "ESI type five";
      }
      enum l2vpn-evpn-esi-type-legacy {
        value 128;
        description "ESI type legacy";
      }
      enum l2vpn-evpn-esi-type-override {
        value 129;
        description "ESI type override (10-octet value)";
      }
      enum esi-type-invalid {
        value 255;
        description "ESI type invalid";
      }
    }
    description "EVPN ESI types";
  }
  typedef L2vpn-ad-rt-role {
    type enumeration {
      enum both {
        value 0;
        description "Both";
      }
      enum import {
        value 1;
        description "Import";
      }
      enum export {
        value 2;
        description "Export";
      }
    }
    description "L2vpn ad rt role";
  }
  typedef L2vpn-ad-rt {
    type enumeration {
      enum l2vpn-ad-rt-none {
        value 0;
        description "Route target not set";
      }
      enum l2vpn-ad-rt-as {
        value 1;
        description "Route Target with 2 Byte AS number";
      }
      enum l2vpn-ad-rt-4byte-as {
        value 2;
        description "Route Target with 4 Byte AS number";
      }
      enum l2vpn-ad-rt-v4-addr {
        value 3;
        description "Route Target with IPv4 Address";
      }
      enum es-import {
        value 1538;
        description "Ethernet Segment Route Target from BGP";
      }
    }
    description "L2vpn ad rt";
  }
  typedef L2vpn-ad-rd {
    type enumeration {
      enum l2vpn-ad-rd-none {
        value 0;
        description "Route Distinguisher not set";
      }
      enum l2vpn-ad-rd-auto {
        value 1;
        description "Route Distinguisher auto-generated";
      }
      enum l2vpn-ad-rd-as {
        value 2;
        description "Route Distinguisher with 2 Byte AS number";
      }
      enum l2vpn-ad-rd-4byte-as {
        value 3;
        description "Route Distinguisher with 4 Byte AS number";
      }
      enum l2vpn-ad-rd-v4-addr {
        value 4;
        description "Route Distinguisher with IPv4 Address";
      }
    }
    description "L2vpn ad rd";
  }
  typedef L2vpn-evpn {
    type enumeration {
      enum evpn-type-invalid {
        description "Unspecify type for that EVI entry";
      }
      enum evpn-type-evpn {
        description "EVPN service type";
      }
      enum evpn-type-pbb-evpn {
        description "PBB EVPN service type";
      }
      enum evpn-type-evpn-vpws-vlan-unaware {
        description "EVPN VPWS vlan-unaware service type";
      }
      enum evpn-type-evpn-vpws-vlan-aware {
        description "EVPN VPWS vlan-aware service type";
      }
      enum evpn-type-max {
        description "Max EVPN type";
      }
    }
    description "L2vpn evpn";
  }

  grouping L2VPN-EVPN-REMOTE-SHG-INFO {
    description "L2VPN EVPN remote split horizon group labels";
    leaf next-hop {
      type inet:ipv6-address;
      description "Next-hop IP address (v6 format)";
    }
    leaf label {
      type uint32;
      description
        "Split horizon label associated with next-hop
        address";
    }
  }

  grouping L2VPN-EVPN-ES-NH-BUFFER {
    description
      "L2VPN EVPN Ethernet Segment (ES) nexthops
      information";
    leaf next-hop {
      type inet:ipv6-address;
      description "Next-hop IP address (v6 format)";
    }
  }

  grouping L2VPN-EVPN-ES {
    description "EVPN Ethernet Segment (ES) database information";
    leaf esi-type {
      type L2vpn-evpn-esi;
      description "ESI Type";
    }
    leaf ethernet-segment-name {
      type string;
      description "Ethernet Segment Name";
    }
    leaf ethernet-segment-state {
      type uint32;
      description "State of the ethernet segment";
    }
    leaf if-handle {
      type xr:Interface-name;
      description "Main port ifhandle";
    }
    leaf main-port-role {
      type L2vpn-rg-state;
      description "Main port redundancy group role";
    }
    leaf main-port-mac {
      type yang:mac-address;
      description "Main Port MAC Address";
    }
    leaf num-up-p-ws {
      type uint32;
      description "Number of PWs in Up state";
    }
    leaf route-target {
      type yang:mac-address;
      description "ES-Import Route Target";
    }
    leaf rt-origin {
      type L2vpn-evpn-rt-origin;
      description "Origin of operational ES-Import RT";
    }
    leaf es-bgp-gates {
      type string;
      description "ES BGP Gates";
    }
    leaf es-l2fib-gates {
      type string;
      description "ES L2FIB Gates";
    }
    leaf mac-flushing-mode-config {
      type L2vpn-evpn-mf-mode;
      description "Configured MAC Flushing mode";
    }
    leaf load-balance-mode-config {
      type L2vpn-evpn-lb-mode;
      description "Configured load balancing mode";
    }
    leaf load-balance-mode-is-default {
      type boolean;
      description "Load balancing mode is default";
    }
    leaf load-balance-mode-oper {
      type L2vpn-evpn-lb-mode;
      description "Operational load balancing mode";
    }
    leaf force-single-home {
      type boolean;
      description "Ethernet-Segment forced to single home";
    }
    leaf source-mac-oper {
      type yang:mac-address;
      description "Operational Source MAC address";
    }
    leaf source-mac-origin {
      type L2vpn-evpn-smac-src;
      description "Origin of operational source MAC address";
    }
    leaf peering-timer {
      type uint32;
      units "second";
      description
        "Configured timer for triggering DF election
        (seconds)";
    }
    leaf peering-timer-left {
      type uint32;
      units "millisecond";
      description "Milliseconds left on DF election timer";
    }
    leaf recovery-timer {
      type uint32;
      units "second";
      description "Configured timer for (STP) recovery (seconds)";
    }
    leaf recovery-timer-left {
      type uint32;
      units "millisecond";
      description "Milliseconds left on (STP) recovery timer";
    }
    leaf service-carving-mode {
      type L2vpn-evpn-sc-mode;
      description "Service carving mode";
    }
    leaf primary-services-input {
      type string;
      description "Input string of Primary services ESI/I-SIDs";
    }
    leaf secondary-services-input {
      type string;
      description "Input string of Secondary services ESI/I-SIDs";
    }
    leaf forwarder-ports {
      type uint32;
      description "Count of Forwarders (AC, AC PW, VFI PW)";
    }
    leaf mp-protected {
      type boolean;
      description "MP is protected and not under EVPN control";
    }
    leaf service-carving-type {
      type L2vpn-evpn-sc;
      description "Service Carving Type";
    }
    leaf elected-d-fs {
      type uint32;
      description "Count of service carving results - elected";
    }
    leaf not-elected-d-fs {
      type uint32;
      description "Count of service carving results - not elected";
    }
    leaf not-config-d-fs {
      type uint32;
      description
        "Count of service carving results - missing
        config detected";
    }
    leaf local-split-horizon-group-label {
      type uint32;
      description "Local split horizon group label";
    }
    leaf-list ethernet-segment-identifier {
      type uint8;
      description "Ethernet Segment id";
    }
    leaf-list primary-service {
      type uint32;
      description "List of Primary services ESI/I-SIDs";
    }
    leaf-list secondary-service {
      type uint32;
      description "List of Secondary services ESI/I-SIDs";
    }
    leaf-list service-carving-result {
      type uint32;
      description "Service carving results";
    }

    list next-hop {
      description "List of nexthop IPv6 addresses";
      uses L2VPN-EVPN-ES-NH-BUFFER;
    }

    list remote-split-horizon-group-label {
      description "Remote split horizon group labels";
      uses L2VPN-EVPN-REMOTE-SHG-INFO;
    }
  }

  grouping L2VPN-EVPN-MAC {
    description "L2VPN EVPN MAC database information";
    leaf ethernet-tag-xr {
      type uint32;
      description "Ethernet Tag";
    }
    leaf mac-address-xr {
      type yang:mac-address;
      description "MAC address";
    }
    leaf ip-address-xr {
      type inet:ipv6-address;
      description "IP address (v6 format)";
    }
    leaf local-label {
      type uint32;
      description "Associated local label";
    }
    leaf num-paths {
      type uint32;
      description " Number of items in path list buffer";
    }
    leaf is-local-mac {
      type boolean;
      description "Indication of MAC being locally generated";
    }
    leaf is-proxy-entry {
      type boolean;
      description "Proxy entry";
    }
    leaf is-remote-mac {
      type boolean;
      description "Indication of MAC being remotely generated";
    }
    leaf soo-nexthop {
      type inet:ipv6-address;
      description "SOO nexthop (v6 format)";
    }
    leaf ipnh-address {
      type inet:ipv6-address;
      description "IP nexthop address (v6 format)";
    }
    leaf esi-port-key {
      type uint16;
      description "ESI port key";
    }
    leaf local-encap-type {
      type uint8;
      description "Encap type of local MAC";
    }
    leaf remote-encap-type {
      type uint8;
      description "Encap type of remote MAC";
    }
    leaf learned-bridge-port-name {
      type string;
      description "Port the MAC was learned on";
    }
    leaf local-seq-id {
      type uint32;
      description "local seq id";
    }
    leaf remote-seq-id {
      type uint32;
      description "remote seq id";
    }
    leaf local-l3-label {
      type uint32;
      description "local l3 label";
    }
    leaf router-mac-address {
      type yang:mac-address;
      description "Router MAC address";
    }
    leaf mac-flush-requested {
      type uint16;
      description "Number of flushes requested ";
    }
    leaf mac-flush-received {
      type uint16;
      description "Number of flushes received ";
    }
    leaf internal-label {
      type uint32;
      description "MPLS Internal Label";
    }
    leaf resolved {
      type boolean;
      description
        "Internal Label has resolved per-ES EAD and
        per-EVI EAD or MAC routes";
    }
    leaf is-static {
      type boolean;
      description "Indication if MAC is statically configured";
    }
    leaf-list local-ethernet-segment-identifier {
      type uint8;
      description "Local Ethernet Segment id";
    }
    leaf-list remote-ethernet-segment-identifier {
      type uint8;
      description "Remote Ethernet Segment id";
    }

    list path-buffer {
      description "Path List Buffer";
      uses L2VPN-LABEL-PATH-BUFFER;
    }
  }

  grouping L2VPN-EVPN-EVI-BGP-RT {
    description "EVPN E-VPN ID Route Target information";

    container route-target {
      description "Route Target";
      uses L2VPN-RT;
    }
    leaf bd-name {
      type string;
      description "Bridge Domain Name";
    }
    leaf evi-xr {
      type uint32;
      description "VPN ID";
    }
    leaf route-target-role {
      type L2vpn-ad-rt-role;
      description "RT Role";
    }
    leaf route-target-stitching {
      type boolean;
      description "RT Stitching";
    }
  }

  grouping L2VPN-EVPN-IMCAST {
    description
      "L2VPN EVPN Inclusive Multicast database
      information";
    leaf evi-xr {
      type uint32;
      description "E-VPN id";
    }
    leaf ethernet-tag-xr {
      type uint32;
      description "Ethernet Tag";
    }
    leaf originating-ip-xr {
      type inet:ipv6-address;
      description "Originating IP";
    }
    leaf next-hop {
      type inet:ipv6-address;
      description "IP of nexthop";
    }
    leaf output-label {
      type uint32;
      description "Output label";
    }
    leaf is-local-entry {
      type boolean;
      description "Local entry";
    }
    leaf is-proxy-entry {
      type boolean;
      description "Proxy entry";
    }
    leaf encap-type {
      type uint8;
      description "Encap type of IMCAST";
    }
  }

  grouping L2VPN-LABEL-PATH-BUFFER {
    description "L2VPN LABEL PATH BUFFER";
    leaf next-hop {
      type inet:ipv6-address;
      description "Next-hop IP address (v6 format)";
    }
    leaf output-label {
      type uint32;
      description "Output Label";
    }
  }

  grouping L2VPN-EVPN-EAD {
    description "L2VPN EVPN EAD database information";
    leaf ethernet-vpnid {
      type uint32;
      description "E-VPN id";
    }
    leaf type {
      type L2vpn-evpn;
      description "Service Type";
    }
    leaf ethernet-tag-xr {
      type uint32;
      description "Ethernet Tag";
    }
    leaf local-next-hop {
      type inet:ipv6-address;
      description "Local nexthop IP";
    }
    leaf local-label {
      type uint32;
      description "Associated local label";
    }
    leaf is-local-ead {
      type boolean;
      description
        "Indication of EthernetAutoDiscovery Route is
        local";
    }
    leaf encap {
      type uint8;
      description "Encap type of local or remote EAD";
    }
    leaf redundancy-single-active {
      type boolean;
      description
        "Single-active redundancy configured at remote
        EAD";
    }
    leaf num-paths {
      type uint32;
      description " Number of items in path list buffer";
    }
    leaf-list ethernet-segment-identifier {
      type uint8;
      description "Ethernet Segment id";
    }

    list path-buffer {
      description "Path List Buffer";
      uses L2VPN-LABEL-PATH-BUFFER;
    }
  }

  grouping L2VPN-EVPN-NEIGHBOR {
    description "L2VPN EVPN Neighbor database information";
    leaf evi-xr {
      type uint32;
      description "E-VPN id";
    }
    leaf neighbor {
      type inet:ipv6-address;
      description "Neighbor IP";
    }
  }

  grouping L2VPN-RT-ES-IMPORT {
    description "L2VPN RT ES IMPORT";
    leaf high-bytes {
      type uint32;
      description "Top 4 bytes of ES Import";
    }
    leaf low-bytes {
      type uint16;
      description "Low 2 bytes of ES Import";
    }
  }

  grouping L2VPN-RT-V4ADDR {
    description "L2VPN RT V4ADDR";
    leaf ipv4-address {
      type inet:ipv4-address;
      description "IPv4 Address";
    }
    leaf two-byte-index {
      type uint16;
      description "2 Byte Index";
    }
  }

  grouping L2VPN-RT-4BYTE-AS {
    description "L2VPN RT 4BYTE AS";
    leaf four-byte-as {
      type uint32;
      description "4 Byte AS Number";
    }
    leaf two-byte-index {
      type uint16;
      description "2 Byte Index";
    }
  }

  grouping L2VPN-RT-2BYTE-AS {
    description "L2VPN RT 2BYTE AS";
    leaf two-byte-as {
      type uint16;
      description "2 Byte AS Number";
    }
    leaf four-byte-index {
      type uint32;
      description "4 Byte Index";
    }
  }

  grouping L2VPN-RT {
    description "L2VPN RT";

    container two-byte-as {
      when "../rt = 'l2vpn-ad-rt-as'" {
        description "../RT = 'L2VPN_AD_RT_AS'";
      }
      description "two byte as";
      uses L2VPN-RT-2BYTE-AS;
    }

    container four-byte-as {
      when "../rt = 'l2vpn-ad-rt-4byte-as'" {
        description "../RT = 'L2VPN_AD_RT_4BYTE_AS'";
      }
      description "four byte as";
      uses L2VPN-RT-4BYTE-AS;
    }

    container v4-addr {
      when "../rt = 'l2vpn-ad-rt-v4-addr'" {
        description "../RT = 'L2VPN_AD_RT_V4ADDR'";
      }
      description "v4 addr";
      uses L2VPN-RT-V4ADDR;
    }

    container es-import {
      when "../rt = 'es-import'" {
        description "../RT = 'ES_Import'";
      }
      description "es import";
      uses L2VPN-RT-ES-IMPORT;
    }
    leaf rt {
      type L2vpn-ad-rt;
      description "RT";
    }
  }

  grouping L2VPN-RD-V4ADDR {
    description "L2VPN RD V4ADDR";
    leaf ipv4-address {
      type inet:ipv4-address;
      description "IPv4 Address";
    }
    leaf two-byte-index {
      type uint16;
      description "2 Byte Index";
    }
  }

  grouping L2VPN-RD-4BYTE-AS {
    description "L2VPN RD 4BYTE AS";
    leaf four-byte-as {
      type uint32;
      description "4 Byte AS Number";
    }
    leaf two-byte-index {
      type uint16;
      description "2 Byte Index";
    }
  }

  grouping L2VPN-RD-2BYTE-AS {
    description "L2VPN RD 2BYTE AS";
    leaf two-byte-as {
      type uint16;
      description "2 Byte AS Number";
    }
    leaf four-byte-index {
      type uint32;
      description "4 Byte Index";
    }
  }

  grouping L2VPN-RD-AUTO {
    description "L2VPN RD AUTO";
    leaf router-id {
      type inet:ipv4-address;
      description "BGP Router ID";
    }
    leaf auto-index {
      type uint16;
      description "Auto-generated Index";
    }
  }

  grouping L2VPN-RD {
    description "L2VPN RD";

    container auto {
      when "../rd = 'l2vpn-ad-rd-auto'" {
        description "../RD = 'L2VPN_AD_RD_AUTO'";
      }
      description "auto";
      uses L2VPN-RD-AUTO;
    }

    container two-byte-as {
      when "../rd = 'l2vpn-ad-rd-as'" {
        description "../RD = 'L2VPN_AD_RD_AS'";
      }
      description "two byte as";
      uses L2VPN-RD-2BYTE-AS;
    }

    container four-byte-as {
      when "../rd = 'l2vpn-ad-rd-4byte-as'" {
        description "../RD = 'L2VPN_AD_RD_4BYTE_AS'";
      }
      description "four byte as";
      uses L2VPN-RD-4BYTE-AS;
    }

    container v4-addr {
      when "../rd = 'l2vpn-ad-rd-v4-addr'" {
        description "../RD = 'L2VPN_AD_RD_V4ADDR'";
      }
      description "v4 addr";
      uses L2VPN-RD-V4ADDR;
    }
    leaf rd {
      type L2vpn-ad-rd;
      description "RD";
    }
  }

  grouping L2VPN-EVPN-FLOW-LABEL {
    description "L2VPN EVPN FLOW LABEL";
    leaf static-flow-label {
      type boolean;
      description "Static flow label";
    }
    leaf global-flow-label {
      type boolean;
      description "Globally configured flow label";
    }
  }

  grouping L2VPN-EVPN-EVI-DETAIL {
    description "EVPN E-VPN ID database detail information";

    container flow-label {
      description "Flow Label Information";
      uses L2VPN-EVPN-FLOW-LABEL;
    }

    container rd-auto {
      description "Automatic Route Distingtuisher";
      uses L2VPN-RD;
    }

    container rd-configured {
      description "Configured Route Distinguisher";
      uses L2VPN-RD;
    }

    container rt-auto {
      description "Automatic Route Target";
      uses L2VPN-RT;
    }

    container rt-auto-stitching {
      description "Automatic Route Target Stitching";
      uses L2VPN-RT;
    }
    leaf evi-xr {
      type uint32;
      description "E-VPN id";
    }
    leaf description {
      type string;
      description "EVI description";
    }
    leaf bd-name {
      type string;
      description "Bridge domain name";
    }
    leaf type {
      type L2vpn-evpn;
      description "Service Type";
    }
    leaf unicast-label {
      type uint32;
      description "Unicast Label";
    }
    leaf multicast-label {
      type uint32;
      description "Multicast Label";
    }
    leaf cw-disable {
      type boolean;
      description "Control-Word Disable";
    }
    leaf table-policy-name {
      type string;
      description "Table-policy Name";
    }
    leaf forward-class {
      type uint8;
      description "Forward Class attribute";
    }
    leaf rt-import-block-set {
      type boolean;
      description "Is Import RT None set";
    }
    leaf rt-export-block-set {
      type boolean;
      description "Is Export RT None set";
    }
    leaf advertise-mac {
      type boolean;
      description "Advertise MAC-only routes on this EVI";
    }
    leaf advertise-bvi-mac {
      type boolean;
      description "Advertise BVI MACs routes on this EVI";
    }
    leaf aliasing-disabled {
      type boolean;
      description "Route Aliasing is disabled";
    }
    leaf unknown-unicast-flooding-disabled {
      type boolean;
      description "Unknown-unicast flooding is disabled";
    }
    leaf reoriginate-disabled {
      type boolean;
      description "Route Re-origination is disabled";
    }
    leaf stitching {
      type uint8;
      description "EVPN Instance is Regular/Stitching side";
    }
    leaf encapsulation {
      type uint8;
      description "EVPN Instance encapsulation";
    }
  }

  grouping L2VPN-EVPN-SUMMARY {
    description "EVPN Information Summary";
    leaf router-id {
      type inet:ipv6-address;
      description "EVPN Router ID";
    }
    leaf as {
      type uint32;
      description "BGP AS number";
    }
    leaf ev-is {
      type uint32;
      description "Number of EVI DB Entries";
    }
    leaf local-mac-routes {
      type uint32;
      description "Number of Local MAC Routes";
    }
    leaf local-ipv4-mac-routes {
      type uint32;
      description "Number of Local IPv4 MAC-IP Routes";
    }
    leaf local-ipv6-mac-routes {
      type uint32;
      description "Number of Local IPv6 MAC-IP Routes";
    }
    leaf es-global-mac-routes {
      type uint32;
      description "Number of ES:Global MAC Routes";
    }
    leaf remote-mac-routes {
      type uint32;
      description "Number of Remote MAC Routes";
    }
    leaf remote-soo-mac-routes {
      type uint32;
      description "Number of Remote Soo MAC Routes";
    }
    leaf remote-ipv4-mac-routes {
      type uint32;
      description "Number of Remote IPv4 MAC-IP Routes";
    }
    leaf remote-ipv6-mac-routes {
      type uint32;
      description "Number of Remote IPv6 MAC-IP Routes";
    }
    leaf local-imcast-routes {
      type uint32;
      description "Number of Local IMCAST Routes";
    }
    leaf remote-imcast-routes {
      type uint32;
      description "Number of Remote IMCAST Routes";
    }
    leaf labels {
      type uint32;
      description "Number of Internal Labels";
    }
    leaf es-entries {
      type uint32;
      description "Number of ES Entries in DB";
    }
    leaf neighbor-entries {
      type uint32;
      description "Number of neighbor Entries in DB";
    }
    leaf local-ead-routes {
      type uint32;
      description "Number of Local EAD Entries in DB";
    }
    leaf remote-ead-routes {
      type uint32;
      description "Number of Remote EAD Entries in DB";
    }
    leaf global-source-mac {
      type yang:mac-address;
      description "Global Source MAC Address";
    }
    leaf peering-time {
      type uint32;
      units "second";
      description "EVPN ES Peering Time (seconds)";
    }
    leaf recovery-time {
      type uint32;
      units "second";
      description "EVPN ES Recovery Time (seconds)";
    }
    leaf l2rib-throttle {
      type boolean;
      description "Send to L2RIB Throttled";
    }
    leaf logging-df-election-enabled {
      type boolean;
      description
        "Logging EVPN Designated Forwarder changes
        enabled";
    }
  }

  grouping L2VPN-EVPN-EVI-SUMMARY {
    description "EVPN E-VPN ID database summary information";
    leaf evi-xr {
      type uint32;
      description "E-VPN id";
    }
    leaf bd-name {
      type string;
      description "Bridge domain name";
    }
    leaf type {
      type L2vpn-evpn;
      description "Service Type";
    }
  }
}
