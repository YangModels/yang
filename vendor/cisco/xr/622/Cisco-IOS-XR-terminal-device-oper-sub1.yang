submodule Cisco-IOS-XR-terminal-device-oper-sub1 {

  belongs-to Cisco-IOS-XR-terminal-device-oper {
    prefix Cisco-IOS-XR-terminal-device-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR terminal-device package operational data.

     Copyright (c) 2013-2016 by Cisco Systems, Inc.
     All rights reserved.";

  revision "2015-11-09" {
    description
      "IOS XR 6.0 revision.";
  }

  typedef Logical-protocol {
    type enumeration {
      enum proto-type-unknown {
        value 0;
        description "Unknown protocol framing";
      }
      enum proto-type-ethernet {
        value 1;
        description "Ethernet protocol framing";
      }
      enum proto-type-otn {
        value 2;
        description "OTN protocol framing";
      }
    }
    description "Logical protocol";
  }
  typedef Trib-protocol {
    type enumeration {
      enum trib-proto-type-unknown {
        value 0;
        description "Unknown protocol";
      }
      enum trib-proto-type1ge {
        value 1;
        description "1G Ethernet protocol";
      }
      enum trib-proto-type-oc48 {
        value 2;
        description "OC48 protocol";
      }
      enum trib-proto-type-stm16 {
        value 3;
        description "STM 16 protocol";
      }
      enum trib-proto-type10gelan {
        value 4;
        description "10G Ethernet LAN protocol";
      }
      enum trib-proto-type10gewan {
        value 5;
        description "10G Ethernet WAN protocol";
      }
      enum trib-proto-type-oc192 {
        value 6;
        description "OC 192 (9.6GB) port protocol";
      }
      enum trib-proto-type-stm64 {
        value 7;
        description "STM 64 protocol";
      }
      enum trib-proto-type-otu2 {
        value 8;
        description "OTU 2 protocol";
      }
      enum trib-proto-type-otu2e {
        value 9;
        description "OTU 2e protocol";
      }
      enum trib-proto-type-otu1e {
        value 10;
        description "OTU 1e protocol";
      }
      enum trib-proto-type-odu2 {
        value 11;
        description "ODU 2 protocol";
      }
      enum trib-proto-type-odu2e {
        value 12;
        description "ODU 2e protocol";
      }
      enum trib-proto-type40ge {
        value 13;
        description "40G Ethernet port protocol";
      }
      enum trib-proto-type-oc768 {
        value 14;
        description "OC 768 protocol";
      }
      enum trib-proto-type-stm256 {
        value 15;
        description "STM 256 protocol";
      }
      enum trib-proto-type-otu3 {
        value 16;
        description "OTU 3 protocol";
      }
      enum trib-proto-type-odu3 {
        value 17;
        description "ODU 3 protocol";
      }
      enum trib-proto-type100ge {
        value 18;
        description "100G Ethernet protocol";
      }
      enum trib-proto-type100g-mlg {
        value 19;
        description "100G MLG protocol";
      }
      enum trib-proto-type-otu4 {
        value 20;
        description
          "OTU4 signal protocol (112G) for transporting
          100GE signal";
      }
      enum trib-proto-type-otu-cn {
        value 21;
        description "OTU Cn protocol";
      }
      enum trib-proto-type-odu4 {
        value 22;
        description "ODU 4 protocol";
      }
    }
    description "Trib protocol";
  }
  typedef Trib-rate-class {
    type enumeration {
      enum trib-rate-unknown {
        value 0;
        description "Unknown tributary signal rate";
      }
      enum trib-rate1g {
        value 1;
        description "1G tributary signal rate";
      }
      enum trib-rate25g {
        value 2;
        description "2.5G tributary signal rate";
      }
      enum trib-rate10g {
        value 3;
        description "10G tributary signal rate";
      }
      enum trib-rate40g {
        value 4;
        description "40G tributary signal rate";
      }
      enum trib-rate100g {
        value 5;
        description "100G tributary signal rate";
      }
    }
    description "Trib rate class";
  }

  grouping LOGICAL-CHANNEL-ASSIGNMENT {
    description "LOGICAL CHANNEL ASSIGNMENT";
    leaf index {
      type uint32;
      description "Index";
    }
    leaf name {
      type string {
        length "0..128";
      }
      description "Name";
    }
    leaf is-logical-link {
      type boolean;
      description "IsLogicalLink";
    }
    leaf logical-channel {
      type uint32;
      description "LogicalChannel";
    }
    leaf optical-channel {
      type string {
        length "0..128";
      }
      description "OpticalChannel";
    }
    leaf allocation {
      type uint32;
      description "Allocation";
    }
    leaf assignment-type {
      type uint32;
      description "AssignmentType";
    }
  }

  grouping LOGICAL-CHANNEL-ATTRIBUTES {
    description "LOGICAL CHANNEL ATTRIBUTES";
    leaf logical-channel-index {
      type uint32;
      description "LogicalChannelIndex";
    }
    leaf logical-channel-ifname {
      type string {
        length "0..128";
      }
      description "LogicalChannelIfname";
    }
    leaf type {
      type string {
        length "0..32";
      }
      description "Type";
    }
    leaf trib-rate-class {
      type Trib-rate-class;
      description "TribRateClass";
    }
    leaf trib-protocol {
      type Trib-protocol;
      description "TribProtocol";
    }
    leaf protocol-type {
      type Logical-protocol;
      description "ProtocolType";
    }
    leaf admin-state {
      type uint32;
      description "AdminState";
    }
    leaf loopback-mode {
      type uint32;
      description "LoopbackMode";
    }
    leaf ingress-client-port {
      type string {
        length "0..128";
      }
      description "IngressClientPort";
    }
    leaf ingress-physical-channel {
      type uint32;
      description "IngressPhysicalChannel";
    }
    leaf tti-transmit {
      type string {
        length "0..256";
      }
      description "TtiTransmit";
    }
    leaf tti-expected {
      type string {
        length "0..256";
      }
      description "TtiExpected";
    }
  }

  grouping OPERATIONAL-MODE-ATTRIBUTES {
    description "OPERATIONAL MODE ATTRIBUTES";
    leaf description {
      type string {
        length "0..128";
      }
      description "Description";
    }
    leaf vendor-id {
      type string {
        length "0..64";
      }
      description "VendorId";
    }
  }

  grouping GRAPH-STRUCTURE-PATH {
    description "GRAPH STRUCTURE PATH";
    leaf path {
      type string {
        length "0..256";
      }
      description "Path";
    }
  }

  grouping ADJACENCY-LIST-PATH {
    description "ADJACENCY LIST PATH";
    leaf path {
      type string {
        length "0..256";
      }
      description "Path";
    }
  }

  grouping OPTICAL-CHANNEL-ATTRIBUTES {
    description "OPTICAL CHANNEL ATTRIBUTES";
    leaf name {
      type string {
        length "0..128";
      }
      description "Name";
    }
    leaf index {
      type uint32;
      description "Index";
    }
    leaf frequency {
      type uint64;
      description "Frequency";
    }
    leaf power {
      type uint64;
      description "Power";
    }
    leaf oper-mode {
      type uint32;
      description "OperMode";
    }
    leaf line-port {
      type string {
        length "0..128";
      }
      description "LinePort";
    }
  }

  grouping SLICE-CONFIG-STATUS-ATTRIBUTES {
    description "SLICE CONFIG STATUS ATTRIBUTES";
    leaf slice {
      type uint8;
      description "Slice";
    }
    leaf prov-status {
      type string {
        length "0..32";
      }
      description "ProvStatus";
    }
    leaf present-config {
      type string {
        length "0..32";
      }
      description "PresentConfig";
    }
    leaf present-timestamp {
      type string {
        length "0..32";
      }
      description "PresentTimestamp";
    }
    leaf past-config {
      type string {
        length "0..32";
      }
      description "PastConfig";
    }
    leaf past-timestamp {
      type string {
        length "0..32";
      }
      description "PastTimestamp";
    }
    leaf err-str {
      type string {
        length "0..1024";
      }
      description "ErrStr";
    }
    leaf err-timestamp {
      type string {
        length "0..32";
      }
      description "ErrTimestamp";
    }
  }

  grouping PARTIAL-CONFIG-STATUS {
    description "PARTIAL CONFIG STATUS";
    leaf partial-config {
      type uint8;
      description "PartialConfig";
    }
  }
}
