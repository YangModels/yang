submodule Cisco-IOS-XR-icpe-infra-oper-sub8 {

  belongs-to Cisco-IOS-XR-icpe-infra-oper {
    prefix Cisco-IOS-XR-icpe-infra-oper;
  }

  /*** LINKAGE (IMPORTS / INCLUDES) ***/

  import Cisco-IOS-XR-types { prefix "xr"; }

  include Cisco-IOS-XR-icpe-infra-oper-sub3 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR icpe-infra package operational data.

     Copyright (c) 2013-2016 by Cisco Systems, Inc.
     All rights reserved.";

  revision "2015-11-09" {
    description
      "IOS XR 6.0 revision.";
  }


  grouping ICPE-GCO-PRIORITY-OPER-TYPE {
    description "Satellite priority information";
    leaf satellite-id-xr {
      type uint32;
      description "Satellite ID";
    }
    leaf rgid {
      type uint32;
      description "RG ID";
    }
    leaf best-path-hops {
      type uint32;
      description "Best path hops";
    }
    leaf configured-priority {
      type uint8;
      description "Configured priority";
    }
    leaf host-priority {
      type uint64;
      description "Host priority";
    }
    leaf partner-priority {
      type uint64;
      description "Partner priority";
    }
    leaf multichassis-redundancy {
      type Icpe-oper-multichassis-redundancy;
      description "Multichassis redundancy";
    }
  }
}
