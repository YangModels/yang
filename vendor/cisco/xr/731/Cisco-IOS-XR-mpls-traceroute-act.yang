module Cisco-IOS-XR-mpls-traceroute-act {
  namespace "http://cisco.com/ns/yang/Cisco-IOS-XR-mpls-traceroute-act";
  prefix mpls-traceroute-act;

  import ietf-inet-types {
    prefix inet;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR mpls traceroute action package configuration
     
     Copyright (c) 2020-2021 by Cisco Systems, Inc.
     All rights reserved.";

  revision 2020-06-05 {
    description
      "Initial revision.";
    reference "MPLS traceroute reference.";
    semver:module-version "1.0.0";
  }

  typedef mpls-fec-type {
    type enumeration {
      enum "bgp" {
        description
          "MPLS BGP FEC";
      }
      enum "generic" {
        description
          "MPLS Generic FEC";
      }
      enum "ldp" {
        description
          "MPLS LDP FEC";
      }
    }
  }

  typedef sr-fec-type {
    type enumeration {
      enum "bgp" {
        description
          "SR IGP BGP FEC";
      }
      enum "ospf" {
        description
          "SR IGP OSPF FEC";
      }
      enum "isis" {
        description
          "SR IGP ISIS FEC";
      }
    }
  }

  typedef request-reply-mode {
    type enumeration {
      enum "ipv4" {
        description
          "Reply Mode IPv4";
      }
      enum "router-alert" {
        description
          "Reply Mode Router Alert";
      }
    }
  }

  rpc mpls-traceroute {
    description
      "Send echo messages";
    input {
      choice traceroute-type {
        mandatory true;
        case type-mpls {
          container mpls {
            description
              "MPLS traceroute";
            choice mpls-subtype {
              mandatory true;
              case subtype-ipv4 {
                container ipv4 {
                  leaf ipv4-prefix {
                    type inet:ipv4-prefix;
                    mandatory true;
                    description
                      "destination of mpls traceroute";
                  }
                  leaf fec-type {
                    type mpls-fec-type;
                    mandatory false;
                    description
                      "TLV FEC type to use in request";
                  }
                }
              }
              case subtype-traffic-eng {
                container traffic-eng {
                  description
                    "MPLS-TE traceroute";
                  choice tunnel-identifier {
                    mandatory true;
                    case subtype-tunnel-name {
                      leaf tunnel-name {
                        type string;
                        description
                          "Next hop tunnel lsp name";
                      }
                    }
                    case subtype-tunnel-interface {
                      leaf tunnel-interface {
                        type string;
                        description
                          "Next hop Interface with form tunnel-te<number>";
                      }
                    }
                  }
                  choice te-lsp-option {
                    case te-lsp-option-active {
                      leaf active-lsp {
                        type boolean;
                        description
                          "Enforce active LSP selection for tunnel";
                      }
                    }
                    case te-lsp-option-id {
                      leaf lsp-id {
                        type uint32 {
                          range "16..10000";
                        }
                        default "16";
                        description
                          "Tunnel Label Switched Path Identifier";
                      }
                    }
                    case te-lsp-option-path-protected {
                      leaf path-protected {
                        type boolean;
                        description
                          "Test path protected LSP for tunnel";
                      }
                    }
                    case te-lsp-option-reoptimized {
                      leaf reoptimized {
                        type boolean;
                        description
                          "Test reoptimized LSP for tunnel";
                      }
                    }
                  }
                }
              }
            }
          }
        }
        case type-sr {
          container sr-mpls {
            choice sr-target {
              case target_ipv4_prefix {
                container ipv4 {
                  leaf ipv4-prefix {
                    type inet:ipv4-prefix;
                    mandatory true;
                    description
                      "SR LSP Egress IPv4 Identifier";
                  }
                  leaf fec-type {
                    type sr-fec-type;
                    description
                      "SR OAM IGP FEC TLV type to use in request";
                  }
                }
              }
              case target_labels {
                container labels {
                  list label {
                    key "index";
                    leaf index {
                      type uint32 {
                        range "0..9";
                      }
                      mandatory true;
                    }
                    leaf label {
                      type uint32 {
                        range "16..1048575";
                      }
                      mandatory true;
                    }
                  }
                  leaf nil-fec {
                    type boolean;
                    mandatory false;
                    description
                      "Use Nil-FEC TLV and Append Explicit Null";
                  }
                  leaf lsp-endpoint {
                    type inet:ipv4-address;
                    mandatory false;
                    description
                      "Specify the IP of the LSP endpoint";
                  }
                }
              }
              case target_policy {
                container policy {
                  choice sr-policy-id {
                    mandatory true;
                    case sr-policy-id-bsid {
                      leaf bsid {
                        type uint32 {
                          range "16..1048575";
                        }
                        default "16";
                        description
                          "SR Policy Binding SID";
                      }
                    }
                    case sr-policy-id-name {
                      leaf name {
                        type string;
                        description
                          "SR Policy Name";
                      }
                    }
                  }
                  leaf fec-type {
                    type sr-fec-type;
                    description
                      "SR OAM IGP FEC TLV type to use in request";
                  }
                  leaf nil-fec {
                    type boolean;
                    mandatory false;
                    description
                      "Use Nil-FEC TLV and Append Explicit Null";
                  }
                  leaf lsp-endpoint {
                    type inet:ipv4-address;
                    description
                      "Specify the IP of the LSP endpoint";
                  }
                }
              }
            }
          }
        }
      }
      container request-options-parameters {
        leaf exp {
          type uint8;
          mandatory false;
          description
            "EXP Bits To Set";
        }
        leaf fec {
          type boolean;
          mandatory false;
          description
            "Force FEC TLV Checks";
        }
        leaf ddmap {
          type boolean;
          mandatory false;
          description
            "Use DDMAP (Default is DSMAP)";
        }
        leaf force-explicit-null {
          type boolean;
          mandatory false;
          description
            "Force explicit null to be added";
        }
        container packet-output {
          leaf interface-name {
            type string;
            description
              "Outgoing interface for echo packet";
          }
          leaf next-hop {
            type inet:ipv4-address;
            description
              "Outgoing next hop IP for echo packet";
          }
        }
        container reply {
          leaf dscp {
            type uint8 {
              range "0..63";
            }
            description
              "Enable DSCP in reply";
          }
          leaf reply-mode {
            type request-reply-mode;
            mandatory false;
            description
              "Echo Reply Mode";
          }
        }
        leaf source {
          type inet:ipv4-address;
          description
            "Source IP address to use in the IP header (used as the return address for the reply)";
        }
        leaf destination {
          type inet:ipv4-address;
          description
            "Destination IP address (127.x.y.z)";
        }
        leaf brief {
          type boolean;
          description
            "Brief mode. Does not include statistical data in result";
        }
        leaf timeout {
          type uint32 {
            range "0..3600";
          }
          description
            "Time in seconds before the lack of a reply invalidates a request";
        }
        leaf ttl {
          type uint32 {
            range "1..255";
          }
          description
            "Time to live (hops to until forced punt)";
        }
      }
    }
    output {
      container mpls-traceroute-response {
        description
          "MPLS traceroute Response";
        container request-options-parameters {
          leaf exp {
            type uint8;
            mandatory false;
            description
              "EXP Bits To Set";
          }
          leaf fec {
            type boolean;
            mandatory false;
            description
              "Force FEC TLV Checks";
          }
          leaf ddmap {
            type boolean;
            mandatory false;
            description
              "Use DDMAP (Default is DSMAP)";
          }
          leaf force-explicit-null {
            type boolean;
            mandatory false;
            description
              "Force an explicit null label to be added";
          }
          container packet-output {
            leaf interface-name {
              type string;
              description
                "Outgoing interface for echo packet";
            }
            leaf next-hop {
              type inet:ipv4-address;
              description
                "Outgoing next hop IP for echo packet";
            }
          }
          container reply {
            leaf dscp {
              type uint8 {
                range "0..63";
              }
              description
                "Enable DSCP in reply";
            }
            leaf reply-mode {
              type request-reply-mode;
              mandatory false;
              description
                "Echo Reply Mode";
            }
          }
          leaf source {
            type inet:ipv4-address;
            description
              "Source IP address to use in the IP header (used as the return address for the reply)";
          }
          leaf destination {
            type inet:ipv4-address;
            description
              "Destination IP address (127.x.y.z)";
          }
          leaf brief {
            type boolean;
            description
              "Brief mode. Does not include statistical data in result";
          }
          leaf timeout {
            type uint32 {
              range "0..3600";
            }
            description
              "Time in seconds before the lack of a reply invalidates a request";
          }
          leaf ttl {
            type uint32 {
              range "1..255";
            }
            description
              "Time to live (hops to until forced punt)";
          }
        }
        container hops {
          list hop {
            key "hop-index";
            leaf hop-index {
              type uint64 {
                range "1..2147483647";
              }
              description
                "Index of the hop list";
            }
            leaf hop-origin-ip {
              type string;
              description
                "Hop origin interface ip";
            }
            leaf hop-destination-ip {
              type string;
              description
                "Hop destination interface ip";
            }
            leaf mtu {
              type string;
              description
                "Maximum Transmission Unit";
            }
            container dsmap-label-stack {
              list dsmap-label {
                key "label";
                description
                  "Label Stack from the DSMAP received
                   in the Echo Response Payload.";
                leaf label {
                  type uint32 {
                    range "16..1048575";
                  }
                }
              }
            }
            leaf return-code {
              type uint8;
              description
                "Return Code of the echo request";
            }
            leaf return-char {
              type string;
              description
                "Return Char of the echo request";
            }
            leaf duration {
              type uint32;
              description
                "Trip duration (msec)";
            }
            container ddmaps {
              list ddmap {
                key "ddmap-index";
                leaf ddmap-index {
                  type uint64 {
                    range "1..2147483647";
                  }
                  description
                    "Index of the hop list";
                }
                leaf ddmap-mtu {
                  type int16;
                  description
                    "MTU from the DDMAP received in
                     the Echo Response Payload";
                }
                leaf ddmap-downstream-address {
                  type inet:ipv4-address;
                  description
                    "Downstream Address from the DDMAP
                     received in the Echo Response Payload";
                }
                leaf ddmap-downstream-intf-index {
                  type int32 {
                    range "1..2147483647";
                  }
                  description
                    "Downstream Interface Address from the DDMAP
                     received in the Echo Response Payload.";
                }
                leaf ddmap-return-code {
                  type uint8;
                  description
                    "Return Code from the DDMAP received
                     in the Echo Response Payload.";
                }
                leaf ddmap-return-subcode {
                  type int16;
                  description
                    "Return Sub Code from the DDMAP
                     received in the Echo Response Payload.";
                }
                container ddmap-label-stack {
                  list ddmap-label {
                    key "label";
                    description
                      "Label Stack from the DDMAP received
                       in the Echo Response Payload.";
                    leaf label {
                      type uint32 {
                        range "16..1048575";
                      }
                    }
                  }
                }
              }
            }
          }
        }
      }
    }
  }
}
