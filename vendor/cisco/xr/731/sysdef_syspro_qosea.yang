/******************************************************************
*
* sysdef_syspro_qosea.yang
*
* Copyright (c) 2020-2021 by cisco Systems, Inc.
* All rights reserved.
*******************************************************************/

module sysdef_syspro_qosea {
  namespace "http://www.cisco.com/ns/yang/plat_sys_profile/sysdef_syspro_qosea";
  prefix sysdef_syspro_qosea;

  import sysdef_ext {
    prefix sysdef_ext;
  }

  organization
    "Cisco Systems Inc.";

  contact
    "Cisco Systems, Inc.
    170 West Tasman Drive
    San Jose, CA  95134-1706
    US";

  description
    "syspro_qosea model";

  revision "2020-05-01" {
    description "Initial revision";
  }


  typedef SYSDEF_CHAR_ATTRB_LEN {
    type uint32 {
      sysdef_ext:const "32";
    }
  }

  grouping sysdef_syspro_qosea {
    description
      "Syspro QoS EA System Profile";

    leaf max_depth_supported {
      type uint32;
      description "Maximum policymap level supported";
    }

    leaf max_queues_per_policy {
      type uint32;
      description "Maximum queues per policymap";
    }

    leaf max_queue_limit {
      type uint32;
      description "Maximum queue limit (in bytes)";
    }

    leaf max_layer3_intfs_per_lc {
      type uint32;
      description "Maximum layer 3 interfaces per LC";
    }

    leaf max_layer3_intfs_per_npu {
      type uint32;
      description "Maximum layer 3 interfaces per NPU";
    }

    leaf max_classes_per_policy {
      type uint32;
      description "Maximum classes per policymap";
    }

    leaf max_classes_per_lc {
      type uint32;
      description "Maximum classes per LC";
    }

    leaf subif_unsupp {
      type uint32;
      description "Flag to indicate if subif is not supported";
    }

    leaf match_vlan_unsupp {
      type uint32;
      description "Flag to indicate if match-vlan is not supported";
    }

    leaf max_leaf_policers_per_policy {
      type uint32;
      description "Max policers per policymap at leaf level";
    }

    leaf max_rate_profile_per_npu {
      type uint32;
      description "Max rate profile per npu";
    }

    leaf max_burst {
      type uint32;
      description "Max burst in bytes";
    }

    leaf min_burst {
      type uint32;
      description "MIN burst in bytes";
    }

    leaf inlif_based {
      type uint32;
      description "inlif based computation";
    }

    leaf max_cir {
      type uint32;
      description "Maximum CIR in kbps";
    }

    leaf min_cir {
      type uint32;
      description "Minimum CIR in kbps";
    }

    leaf ingress_voq_packet_len_adjust {
      type int32;
      description "Ingress Voq Packet Lenght Adjust";
    }

    leaf tcam_based_classification {
      type uint32;
      description "TCAM based classification";
    }

    leaf policer_stats_rm_enabled {
      type uint32;
      description "Uses RM to allocate Policer and Stats";
    }

    leaf dynamic_policer_allocation {
      type uint32;
      description "Policer allocation with Policy Map";
    }

    leaf is_subif_egress_qos_supported {
      type uint32;
      description "Subinterface Egress QOS supported";
    }

    leaf is_dual_policy_supported {
      type uint32;
      description "Dual Policy Support";
    }

    leaf is_timestamp_supported {
      type uint32;
      description "Time Stamp Support";
    }

    leaf is_parent_oversubscription_supported {
      type uint32;
      description "Child policy min is more than parent shape";
    }

    leaf hybrid_classification {
      type uint32;
      description "use tcam or map for classification";
    }

    leaf classification_verify {
      type uint32;
      description "qos class format verification";
    }

    leaf is_sub_with_priority_without_policer_supported {
      type uint32;
      description "Subinterface with priority without policer action";
    }

    leaf num_policer_stat_resources_default_qos_mode {
      type uint32;
      description "Number of policer stats resources in default qos mode";
    }

    leaf num_policer_stat_resources_enhan_qos_mode {
      type uint32;
      description "Number of policer stats resources in enhanced qos mode";
    }

    leaf is_rm_in_sdk {
      type uint32;
      description "Resource Management (most of) in SDK";
    }

    leaf is_weight_inverted_in_ea {
      type uint32;
      description "NPU requires inverse weight EA converts weight to an inverse value";
    }

    leaf is_8pq_hqos_supported {
      type uint32;
      description "Up to 8 priorities hqos supported";
    }

    leaf is_subinterface_sys_port_needed {
      type uint32;
      description "Does Sub Interface need a unique System Port";
    }

    leaf is_slot_num_derived_from_npu {
      type uint32;
      description "Does the slot number needs to be derived from NPU";
    }

    leaf default_queue_len_ms {
      type uint32;
      description "Platform specific default queue size in ms";
    }

    leaf prio_default_queue_len_ms {
      type uint32;
      description "Platform specific priority default queue size in ms";
    }

    leaf default_min_queue_len_ms {
      type uint32;
      description "Platform specific minimum queue size in ms";
    }

    leaf is_policer_marking_supported {
      type uint32;
      description "Policer marking actions supported";
    }

    leaf asic_partition_levels {
      type uint32;
      description "the number of partition levels in an asic";
    }

    leaf asic_partition_level_1_name {
      type string {
        sysdef_ext:max-length "SYSDEF_CHAR_ATTRB_LEN";
      }
      description "the number of partition levels in an asic";
    }

    leaf asic_partition_level_2_name {
      type string {
        sysdef_ext:max-length "SYSDEF_CHAR_ATTRB_LEN";
      }
      description "the name of asic partition level 2";
    }

    leaf only_monotonic_priority_supported {
      type uint32;
      description "Only policy with monotonically increasing priority is supported";
    }

    leaf is_subif_bw_over_supported {
      type uint32;
      description "The sum of sub intfs' priority and min bw can exceed main intf bw";
    }

    leaf mainif_max_wt {
      type uint32;
      description "The sum of sub intfs' priority and min bw can exceed main intf bw";
    }

    leaf subif_max_wt {
      type uint32;
      description "The sum of sub intfs' priority and min bw can exceed main intf bw";
    }

    leaf is_mainif_subif_max_wt_different {
      type uint32;
      description "The sum of sub intfs' priority and min bw can exceed main intf bw";
    }

    leaf is_voq_grid_alloc {
      type uint32;
      description "Is VoQ allocated by GRID";
    }

    leaf is_subif_queue_shape_supported {
      type uint32;
      description "Are shapers allowed for queues on sub-interfaces";
    }

    leaf is_parent_ipm_brr_for_subif_supported {
      type uint32;
      description "Is IPM of BRR supported for parent policy on subif";
    }

    leaf is_parent_brr_for_mainif_supported {
      type uint32;
      description "Is BRR supported for parent policy on mainif";
    }

    leaf is_parent_bw_br_supported {
      type uint32;
      description "Is BW BW remaining supported for parent policy";
    }

    leaf is_mainif_subif_policy_allowed {
      type uint32;
      description "Is similar type of policy allowed on main & sub-intf in either direction";
    }

    leaf create_unique_tc7_cgm_profile {
      type uint32;
      description "Create unique CGM profile for TC7";
    }

    leaf return_error_on_exceed_ql_max {
      type uint32;
      description "return error when user tries to exceed MAX QL for RED";
    }

    leaf fixed_tail_drop_thresh_for_red {
      type uint32;
      description "fixed tail drop threshold for queue with RED 0 if platform has no fixed tail drop for RED";
    }

    leaf min_queue_limit {
      type uint32;
      description "Minimum queue limit (in bytes)";
    }
  }
}
