module Cisco-IOS-XR-sysadmin-fabric-qsfpdd {
  namespace "http://www.cisco.com/ns/yang/Cisco-IOS-XR-sysadmin-fabric-qsfpdd";
  prefix fabric_qsfpdd;

  import Cisco-IOS-XR-sysadmin-fabric-types {
    prefix fabric-types;
  }
  import tailf-xsd-types {
    prefix xs;
  }
  import Cisco-IOS-XR-sysadmin-show-trace {
    prefix show_trace;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains definitions
     for the Calvados model objects.
     
     Copyright (c) 2012-2020 by Cisco Systems, Inc.
     All rights reserved.";

  revision 2015-08-30 {
    description
      "Initial version.";
    semver:module-version "1.0.0";
  }

  grouping fc_qsfpdd {
    container qsfpdd {
      container dom {
        list location {
          key "loc_str";
          leaf loc_str {
            type string;
          }
          leaf description {
            type string;
            default "location (R/S)";
          }
          list qsfpdd_port {
            key "qsfpdd_port_num";
            config false;
            leaf qsfpdd_port_num {
              type uint32;
              description
                "Front Port Num";
            }
            list qsfpdd_port_dom_data {
              leaf qsfpdd_dom_data {
                type string;
              }
            }
          }
        }
      }
      container summary {
        list rack {
          key "rack_str";
          config false;
          leaf rack_str {
            type string;
          }
          leaf description {
            type string;
            default "Rack No.";
          }
          list qsfpdd_rack_summary_data {
            leaf qsfpdd_rack_data {
              type string;
            }
          }
        }
      }
    }
  }
}
