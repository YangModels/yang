/********************************************************************
 *
 *      File:  sysdef_datapath.yang
 *
 *      Description:
 *         System Definition Yang model for Datapath
 *
 *
 * Copyright (c) 2020-2021 by Cisco Systems, Inc.
 * All rights reserved.
 *
 *
 **********************************************************************/
module sysdef_datapath{
  namespace "http://www.cisco.com/ns/yang/cpa/sysdef_datapath";
  prefix sysdef_datapath;

  import sysdef_ext {
    prefix sysdef_ext;
  }

  organization
    "Cisco Systems Inc.";

  contact
    "Cisco Systems, Inc.
    170 West Tasman Drive
    San Jose, CA  95134-1706
    US";

  description
    "System Definition Datapath Model";

  revision "2020-06-23" {
    description "Initial revision";
  }

  /*
   * Please maintain this enumeration in sync with
   * the duplicate definition dn_port_speed_e
   */
  typedef port_speed_type {
    description
      "Port Type";

    type enumeration {

      enum PORT_SPEED_INVALID {
        value 0;
      }

      enum PORT_SPEED_1G {
        value 1;
      }

      enum PORT_SPEED_10G {
        value 2;
      }

      enum PORT_SPEED_25G {
        value 3;
      }

      enum PORT_SPEED_40G {
        value 4;
      }

      enum PORT_SPEED_50G {
        value 5;
      }

      enum PORT_SPEED_100G {
        value 6;
      }

      enum PORT_SPEED_400G {
        value 7;
      }

      enum PORT_SPEED_800G {
        value 8;
      }
    }
  }

/*
 * Please maintain this enumeration in sync with optics_breakout_t
 */
  typedef breakout_type {
    description
      "Port Breakout Type";

    type enumeration {

      enum BREAKOUT_NONE {
        value 0;
      }

      enum BREAKOUT_UNSUPPORTED {
        value 1;
      }

      enum BREAKOUT_UNSUPPORTED_REJECT_CONFIG {
        value 2;
      }

      enum BREAKOUT_4x10G {
        value 3;
      }

      enum BREAKOUT_10x10G {
        value 4;
      }

      enum BREAKOUT_4x25G {
        value 5;
      }

      enum BREAKOUT_2x50G {
        value 6;
      }

      enum BREAKOUT_GAUI_2x100G {
        value 7;
      }

      enum BREAKOUT_2x100G {
        value 8;
      }

      enum  BREAKOUT_4x100G {
        value 9;
      }

      enum  BREAKOUT_8x50G {
        value 10;
      }

      enum  BREAKOUT_1x100G {
        value 11;
      }

      enum  BREAKOUT_3x100G {
        value 12;
      }

      enum BREAKOUT_INVALID {
        value 255;
      }
    }
  }

 /*
  * Please maintain this enumeration in sync with
  * thee duplicate definition dn_pic_type_e
  */
  typedef pic_type {
    description
      "PIC Type";

    type enumeration {

      enum  PIC_TYPE_INVALID {
        value 0; /* reserve 0 as invalid */
      }

      enum  PIC_TYPE_PHY {
        value 1; /* for physical main interfaces */
      }

      enum  PIC_TYPE_MGMT {
        value 2; /* for RP Interfaces */
      }

      enum  PIC_TYPE_LB {
        value 3; /* for bundle main interfaces */
      }

      enum  PIC_TYPE_PHY_SUB {
        value 4; /* for physical vlan interfaces */
      }

      enum  PIC_TYPE_LB_SUB {
        value 5; /* for bundle vlan interfaces */
      }

      enum  PIC_TYPE_MAX {
        value 6;
      }
    }
  }

  /* NPU family id used for a Spitfire platform */
  typedef npu_family {
    description "NPU Family Types";

    type enumeration {
      enum NPU_FAMILY_BASE {
        value 0;
      }

      enum NPU_FAMILY_PACIFIC {
        value 1;
      }

      enum NPU_FAMILY_GIBRALTAR {
        value 2;
      }

      enum NPU_FAMILY_GRAPHENE {
        value 3;
      }

      enum NPU_FAMILY_PALLADIUM {
        value 4;
      }

      enum NPU_FAMILY_MAX {
        value 5;
      }
    }
  }

/***************************************
 Datapath Profile and related Structures
****************************************/

  grouping datapath_subport_info {
    description
      "Breakout Port Infromation";

    leaf breakout_type {
      type breakout_type;
      description "Port breakout type";
    }

    leaf min_subport_index {
      type uint32;
      description "Minimum subport index for this breakout type";
    }

    leaf max_subport_index {
      type uint32;
      description "Maximum subport index for this breakout type";
    }
  }

  grouping datapath_port_breakout_info {
    description
      "Port Infromation";

    leaf port_speed {
      type port_speed_type;
      description "Port speed";
    }

    leaf num_ports {
      type uint32;
      description "Total Number of ports at this port speed";
    }

    list subport_info {
      uses datapath_subport_info;
      description "List of breakout ports possible and its details";
    }
  }

  grouping id_field_extraction_attribs {
    description "ID's Subfield extraction attributes";

    leaf mask {
      type uint64;
    }

    leaf shift {
      type uint32;
    }
  }

  grouping port_id_composition {
    description "Port ID Composition";

    container subport_id {
      uses id_field_extraction_attribs;
    }

    container nif_id {
      uses id_field_extraction_attribs;
    }

    container pp_port_id {
      uses id_field_extraction_attribs;
    }

    container unit_id {
      uses id_field_extraction_attribs;
    }
  }

  grouping pic_id_composition {
    description "PIC ID Composition";

    container pic_type {
      uses id_field_extraction_attribs;
    }

    container pic_speed {
      uses id_field_extraction_attribs;
    }

    container pic_spa {
      uses id_field_extraction_attribs;
    }

    container pic_lb_npu {
      uses id_field_extraction_attribs;
    }

    container pic_system_port {
      uses id_field_extraction_attribs;
    }

    container pic_pp_port {
      uses id_field_extraction_attribs;
    }

    container pic_unit {
      uses id_field_extraction_attribs;
    }

    container pic_voq_base {
      uses id_field_extraction_attribs;
    }

    container pic_connector_base {
      uses id_field_extraction_attribs;
    }

    container pic_nife_base {
      uses id_field_extraction_attribs;
    }

    container pic_core {
      uses id_field_extraction_attribs;
    }
  }

  grouping sysdef_datapath {
    description
      "Datapath Profile";

    leaf npu_family {
      type npu_family;
    }

    leaf max_physical_front_panel_ports {
      type uint32;
    }

    leaf cfm_dm_sw_ts_is_req { /* Need to name this better */
      type uint32;
    }

    leaf lc_trap_npu_mask { /* Need to name this better */
      type uint64;
    }

    leaf max_ports_per_npu {
      type uint32;
      description "Maximum number of physical ports supported on this NPU";
    }

    leaf num_min_voq_per_port { /* Need more information on what this represents */
      type uint32;
      description "Minimum number of voq per port";
    }

    leaf port_speed_min {
      type port_speed_type;
      description "Minimum port speed type";
    }

    leaf port_speed_max {
      type port_speed_type;
      description "Maximum port speed type";
    }

    leaf max_breakout_ports {
      type uint32;
      description "Maximum number of breakout ports possible";
    }

    container port_id_composition {
      uses port_id_composition;
    }

    container pic_id_composition {
      uses pic_id_composition;
    }

    list port_breakout_info {
      uses datapath_port_breakout_info;
      description "Number of maximum and minimum breakout ports per port speed and breakout types";
    }
  }
}
