/******************************************************************
*
* sysdef_syspro_oam.yang
*
* Copyright (c) 2020-2021 by cisco Systems, Inc.
* All rights reserved.
*******************************************************************/

module sysdef_syspro_oam {
  namespace "http://www.cisco.com/ns/yang/plat_sys_profile/sysdef_syspro_oam";
  prefix sysdef_syspro_oam;

  organization
    "Cisco Systems Inc.";

  contact
    "Cisco Systems, Inc.
    170 West Tasman Drive
    San Jose, CA  95134-1706
    US";

  description
    "syspro_oam model";

  revision "2020-05-01" {
    description "Initial revision";
  }

  grouping sysdef_syspro_oam {
    description
      "Syspro OAM System Profile";

    leaf oam_enable {
      type uint32;
      description "Feature OAM Enable";
    }

    leaf bfd_enable {
      type uint32;
      description "Feature BFD enable";
    }

    leaf max_1sec_timer {
      type uint32;
      description "Feature BFD enable";
    }

    leaf oam_mlc_bundle {
      type uint32;
      description "multi line card bundle support";
    }

    leaf oam_init_wa {
      type uint32;
      description "oam_init WorkAround for QAX Platform enable";
    }

    leaf flexible_timer_range_support {
      type uint32;
      description "flexible_timer_range_support";
    }

    leaf oam_edpl_support {
      type uint32;
      description "oam_edpl_support";
    }

    leaf cfm_hw_lmep_id_min {
      type uint32;
      description "cfm local id alloc min value";
    }

    leaf cfm_hw_lmep_id_max {
      type uint32;
      description "cfm local id alloc max value";
    }

    leaf cfm_hw_lmep_id_default {
      type uint32;
      description "cfm local id alloc default value";
    }

    leaf cfm_hw_lmep_icc_id_min {
      type uint32;
      description "cfm local icc id alloc min value";
    }

    leaf cfm_hw_lmep_icc_id_max {
      type uint32;
      description "cfm local icc id alloc max value";
    }
  }
}
