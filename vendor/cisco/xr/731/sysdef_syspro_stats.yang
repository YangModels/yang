/******************************************************************
*
* sysdef_syspro_stats.yang
*
* Copyright (c) 2020-2021 by cisco Systems, Inc.
* All rights reserved.
*******************************************************************/

module sysdef_syspro_stats {
  namespace "http://www.cisco.com/ns/yang/plat_sys_profile/sysdef_syspro_stats";
  prefix sysdef_syspro_stats;

  organization
    "Cisco Systems Inc.";

  contact
    "Cisco Systems, Inc.
    170 West Tasman Drive
    San Jose, CA  95134-1706
    US";

  description
    "syspro_stats model";

  revision "2020-05-01" {
    description "Initial revision";
  }

  typedef syspro_stats_core {
    description "Platform Family Types";

    type enumeration {
      enum SYSPRO_STATS_CORE_0 {
        value 0;
      }

      enum SYSPRO_STATS_CORE_1 {
        value 1;
      }

      enum SYSPRO_STATS_CORE_BOTH {
        value 2;
      }

      enum SYSPRO_STATS_CORE_ID_MAX {
        value 3;
      }
    }
  }

  grouping sysdef_syspro_stats {
    description
      "Syspro Stats System Profile";

    leaf stats_max {
      type uint32;
      description "Maximum number of stats";
    }

    leaf stats_max_template {
      type uint32;
      description "max template";
    }

    leaf pseudo_intfs_stats_core {
      type syspro_stats_core;
      description "pseudo interfaces statistics core";
    }

    leaf external_rmon_stats_supported  {
      type uint32;
      description "Is external rmon stats supported";
    }
  }
}
