/******************************************************************
*
* sysdef_syspro_grid.yang
*
* Copyright (c) 2020-2021 by cisco Systems, Inc.
* All rights reserved.
*******************************************************************/

module sysdef_syspro_grid {
  namespace "http://www.cisco.com/ns/yang/plat_sys_profile/sysdef_syspro_grid";
  prefix sysdef_syspro_grid;

  organization
    "Cisco Systems Inc.";

  contact
    "Cisco Systems, Inc.
    170 West Tasman Drive
    San Jose, CA  95134-1706
    US";

  description
    "syspro_grid model";

  revision "2020-05-01" {
    description "Initial revision";
  }

  grouping sysdef_syspro_grid {
    description
      "Syspro Grid System Profile";

    leaf rif_vsi_pool_start {
      type uint32;
      description "Start of the VSI/RIF pool";
    }

    leaf rif_vsi_pool_end {
      type uint32;
      description "End of the VSI/RIF pool";
    }

    leaf inlif_pool_start {
      type uint32;
      description "Start of the INLIF pool";
    }

    leaf inlif_pool_end {
      type uint32;
      description "End of the INLIF pool";
    }

    leaf glif_pool_start {
      type uint32;
      description "Start of the GLIF/OUTLIF/encap_id pool end";
    }

    leaf glif_pool_end {
      type uint32;
      description "End of the GLIF/OUTLIF/encap_id pool end";
    }

    leaf is_lag_id_grid_allocated {
      type uint32;
      description "is lag id allocated from grid or not";
    }

    leaf is_rif_grid_allocated {
      type uint32;
      description "is rif allocated from grid or not";
    }

    leaf is_mrid_grid_allocated {
      type uint32;
      description "is MRID allocated from grid or not";
    }

    leaf port_class_id_base {
      type uint32;
      description "vlan domain for bundle intfs";
    }

    leaf is_glif_grid_allocated {
      type uint32;
      description "is glif allocated from grid or not";
    }

    leaf is_lif_id_grid_allocated {
      type uint32;
      description "is lif id allocated from grid or not";
    }

    leaf is_local_port_grid_allocated {
      type uint32;
      description "is local port id allocated from grid or not";
    }

    leaf is_bfd_remote_id_grid_allocated {
      type uint32;
      description "is bfd remote id allocated from grid or not";
    }

    leaf is_cfm_hw_lmep_id_grid_allocated {
      type uint32;
      description "is cfm local id allocated from grid or not";
    }

    leaf is_cfm_hw_rmep_id_grid_allocated {
      type uint32;
      description "is cfm remote id allocated from grid or not";
    }

    leaf is_voq_grid_allocated {
      type uint32;
      description "is voq allocated from grid or not";
    }

    leaf is_evpn_peer_id_grid_allocated {
      type uint32;
      description "is evpn peer id allocated from grid or not";
    }

    leaf is_swoff_mc_id_grid_allocated {
      type uint32;
      description "is swoff mc id allocated from grid or not";
    }

    leaf bvi_rif_bank {
      type uint32;
      description "bvi rif bank";
    }

    leaf mrib4_mrid_bank {
      type uint32;
      description "mrib4_mrid_bank";
    }

    leaf mrib6_mrid_bank {
      type uint32;
      description "mrib6_mrid_bank";
    }

    leaf is_sysport_grid_allocated {
      type uint32;
      description "is system-port allocated from grid or not";
    }

    leaf is_vrf_id_grid_allocated {
      type uint32;
      description "is vrf id allocated from grid or not";
    }

    leaf is_switch_id_grid_allocated {
      type uint32;
      description "is switch id allocated from grid or not";
    }

    leaf lag_id_res_pool_num_banks {
      type uint32;
      description "lag id resource pool number of banks";
    }

    leaf rif_res_pool_num_banks {
      type uint32;
      description "rif id resource pool number of banks";
    }

    leaf mrid_res_pool_num_banks {
      type uint32;
      description "mrid id resource pool number of banks";
    }

    leaf glif_res_pool_num_banks {
      type uint32;
      description "glif resource pool number of banks";
    }

    leaf inlif_res_pool_num_banks {
      type uint32;
      description "inlif resource pool number of banks";
    }

    leaf voq_res_pool_num_banks {
      type uint32;
      description "voq resource pool number of banks";
    }

    leaf local_port_res_pool_num_banks {
      type uint32;
      description "local_port resource pool number of banks";
    }

    leaf bfd_remote_id_res_pool_num_banks {
      type uint32;
      description "bfd remote id resource pool number of banks";
    }

    leaf cfm_hw_lmep_id_res_pool_num_banks {
      type uint32;
      description "cfm local id resource pool number of banks";
    }

    leaf cfm_hw_rmep_id_res_pool_num_banks {
      type uint32;
      description "cfm remote id resource pool number of banks";
    }

    leaf evpn_peer_id_res_pool_num_banks {
      type uint32;
      description "evpn peer id resource pool number of banks";
    }

    leaf swoff_mc_id_res_pool_num_banks {
      type uint32;
      description "swoff mc id resource pool number of banks";
    }

    leaf sysport_res_pool_num_banks {
      type uint32;
      description "system-port resource pool number of banks";
    }

    leaf vrf_id_res_pool_num_banks {
      type uint32;
      description "vrf id resource pool number of banks";
    }

    leaf switch_id_res_pool_num_banks {
      type uint32;
      description "switch id resource pool number of banks";
    }

    leaf span_res_pool_num_banks {
      type uint32;
      description "SPAN resource pool number of banks";
    }

    leaf lag_id_res_pool_bank_0_min {
      type uint32;
      description "lag id resource pool bank 0 min";
    }

    leaf lag_id_res_pool_bank_0_max {
      type uint32;
      description "lag id resource pool bank 0 max";
    }

    leaf lag_id_res_pool_bank_1_min {
      type uint32;
      description "lag id resource pool bank 1 min";
    }

    leaf lag_id_res_pool_bank_1_max {
      type uint32;
      description "lag id resource pool bank 1 max";
    }

    leaf lag_id_res_pool_bank_2_min {
      type uint32;
      description "lag id resource pool bank 2 min";
    }

    leaf lag_id_res_pool_bank_2_max {
      type uint32;
      description "lag id resource pool bank 2 max";
    }

    leaf rif_reserved_for_tpa {
      type uint32;
      description "rif reserved resource for tpa";
    }

    leaf mrid_reserved_for_mrib4 {
      type uint32;
      description "mrid reserved resource for mrib4";
    }

    leaf mrid_reserved_for_mrib6 {
      type uint32;
      description "mrid reserved resource for mrib6";
    }

    leaf rif_res_pool_bank_0_min {
      type uint32;
      description "rif resource pool phy intf bank 0 min";
    }

    leaf rif_res_pool_bank_0_max {
      type uint32;
      description "rif resource pool intf bank 0 max";
    }

    leaf rif_res_pool_bank_1_min {
      type uint32;
      description "rif resource pool bank 1 min";
    }

    leaf rif_res_pool_bank_1_max {
      type uint32;
      description "rif resource pool bank 1 max";
    }

    leaf rif_res_pool_bank_2_min {
      type uint32;
      description "rif resource pool bank 2 min - VRF/TUNNEL interfaces";
    }

    leaf rif_res_pool_bank_2_max {
      type uint32;
      description "rif resource pool bank 2 max - VRF/TUNNEL interfaces";
    }

    leaf rif_res_pool_bank_3_min {
      type uint32;
      description "rif resource pool bank 3 min - BVI";
    }

    leaf rif_res_pool_bank_3_max {
      type uint32;
      description "rif resource pool bank 3 max - BVI";
    }

    leaf mrid_res_pool_bank_0_min {
      type uint32;
      description "mrid resource pool phy intf bank 0 min";
    }

    leaf mrid_res_pool_bank_0_max {
      type uint32;
      description "mrid resource pool intf bank 0 max 0-0x7FFFffff";
    }

    leaf mrid_res_pool_bank_1_min {
      type uint32;
      description "mrid resource pool bank 1 min 01 are reserved Start from 2";
    }

    leaf mrid_res_pool_bank_1_max {
      type uint32;
      description "mrid resource pool bank 1 max 1024 GRE and 512 BVI";
    }

    leaf glif_res_pool_bank_0_min {
      type uint32;
      description "glif resource pool bank 0 min";
    }

    leaf glif_res_pool_bank_0_max {
      type uint32;
      description "glif resource pool bank 0 max";
    }

    leaf glif_res_pool_bank_1_min {
      type uint32;
      description "glif resource pool bank 1 min";
    }

    leaf glif_res_pool_bank_1_max {
      type uint32;
      description "glif resource pool bank 1 max";
    }

    leaf glif_res_pool_bank_2_min {
      type uint32;
      description "glif resource pool bank 2 min - mplsmdtbud - will be removing/merging with bank 1";
    }

    leaf glif_res_pool_bank_2_max {
      type uint32;
      description "glif resource pool bank 2 max - mplsmdtbud - will be removing/merging with bank 1";
    }

    leaf glif_res_pool_bank_3_min {
      type uint32;
      description "glif resource pool bank 3 min";
    }

    leaf glif_res_pool_bank_3_max {
      type uint32;
      description "glif resource pool bank 3 max";
    }

    leaf glif_res_pool_bank_4_min {
      type uint32;
      description "glif resource pool bank 4 min";
    }

    leaf glif_res_pool_bank_4_max {
      type uint32;
      description "glif resource pool bank 4 max";
    }

    leaf glif_res_pool_bank_5_min {
      type uint32;
      description "glif resource pool bank 5 min";
    }

    leaf glif_res_pool_bank_5_max {
      type uint32;
      description "glif resource pool bank 5 max";
    }

    leaf glif_res_pool_bank_6_min {
      type uint32;
      description "glif resource pool bank 6 min";
    }

    leaf glif_res_pool_bank_6_max {
      type uint32;
      description "glif resource pool bank 6 max";
    }

    leaf glif_res_pool_bank_7_min {
      type uint32;
      description "glif resource pool bank 7 min - MLDP encap id";
    }

    leaf glif_res_pool_bank_7_max {
      type uint32;
      description "glif resource pool bank 7 max - MLDP encap id";
    }

    leaf inlif_res_pool_bank_0_min {
      type uint32;
      description "inlif resource pool bank 0 min";
    }

    leaf inlif_res_pool_bank_0_max {
      type uint32;
      description "inlif resource pool bank 0 max : max_inlif_l2";
    }

    leaf inlif_res_pool_bank_17_min {
      type uint32;
      description "inlif resource pool bank 17 min";
    }

    leaf inlif_res_pool_bank_17_max {
      type uint32;
      description "inlif resource pool bank 17 max";
    }

    leaf inlif_res_pool_bank_18_min {
      type uint32;
      description "MH-PWE-PORT IN-LIF";
    }

    leaf inlif_res_pool_bank_18_max {
      type uint32;
      description "MH-PWE-PORT IN-LIF";
    }

    leaf inlif_res_pool_bank_19_min {
      type uint32;
      description "inlif resource pool bank 19 min";
    }

    leaf inlif_res_pool_bank_19_max {
      type uint32;
      description "inlif resource pool bank 19 max";
    }

    leaf inlif_res_pool_bank_20_min {
      type uint32;
      description "SRv6 INLIF min";
    }

    leaf inlif_res_pool_bank_20_max {
      type uint32;
      description "SRv6 INLIF max";
    }

    leaf inlif_res_pool_bank_21_min {
      type uint32;
      description "inlif resource pool bank 21 min";
    }

    leaf inlif_res_pool_bank_21_max {
      type uint32;
      description "inlif resource pool bank 21 max";
    }

    leaf inlif_res_pool_bank_22_min {
      type uint32;
      description "inlif resource pool bank 22 min";
    }

    leaf inlif_res_pool_bank_22_max {
      type uint32;
      description "inlif resource pool bank 22 max";
    }

    leaf inlif_res_pool_bank_24_min {
      type uint32;
      description "Resources allocated at init time - dnsdk_prealloc_ids_t";
    }

    leaf inlif_res_pool_bank_24_max {
      type uint32;
      description "Resources allocated at init time";
    }

    leaf inlif_res_pool_bank_25_min {
      type uint32;
      description "Reserved for IP-tunnel InLIF direct-extraction";
    }

    leaf inlif_res_pool_bank_25_max {
      type uint32;
      description "Reserved for IP-tunnel InLIF direct-extraction";
    }

    leaf inlif_res_pool_bank_32_min {
      type uint32;
      description "EVPN IML LABEL INLIF";
    }

    leaf inlif_res_pool_bank_32_max {
      type uint32;
      description "EVPN IML LABEL LIF - 2K EVIs we need 4K tunnel_in_lifs";
    }

    leaf local_port_res_pool_bank_0_min {
      type uint32;
      description "local_port resource pool bank 0 min";
    }

    leaf local_port_res_pool_bank_0_max {
      type uint32;
      description "local_port resource pool bank 0 max";
    }

    leaf bfd_remote_id_res_pool_bank_0_min {
      type uint32;
      description "bfd remote id resource pool bank 0 min";
    }

    leaf bfd_remote_id_res_pool_bank_0_max {
      type uint32;
      description "bfd remote id resource pool bank 0 max";
    }

    leaf cfm_hw_lmep_id_res_pool_bank_0_min {
      type uint32;
      description "cfm local id resource pool bank 0 min";
    }

    leaf cfm_hw_lmep_id_res_pool_bank_0_max {
      type uint32;
      description "cfm local id resource pool bank 0 max";
    }

    leaf cfm_hw_rmep_id_res_pool_bank_0_min {
      type uint32;
      description "cfm remote id resource pool bank 0 min";
    }

    leaf cfm_hw_rmep_id_res_pool_bank_0_max {
      type uint32;
      description "cfm remote id resource pool bank 0 max";
    }

    leaf voq_res_pool_bank_0_min {
      type uint32;
      description "voq resource pool bank 0 min VOQ/8 allocation ";
    }

    leaf cfm_hw_lmep_id_res_pool_bank_1_min {
      type uint32;
      description "cfm local id resource pool bank 1 min";
    }

    leaf voq_res_pool_bank_0_max {
      type uint32;
      description "voq resource pool bank 0 max VOQ/8 allocation";
    }

    leaf evpn_peer_id_res_pool_bank_0_min {
      type uint32;
      description "evpn peer id resource pool bank 0 min";
    }

    leaf evpn_peer_id_res_pool_bank_0_max {
      type uint32;
      description "evpn peer id resource pool bank 0 max";
    }

    leaf swoff_mc_id_res_pool_bank_0_min {
      type uint32;
      description "swoff mc id resource pool bank 0 min";
    }

    leaf cfm_hw_lmep_id_res_pool_bank_1_max {
      type uint32;
      description "cfm local id resource pool bank 1 max";
    }

    leaf swoff_mc_id_res_pool_bank_0_max {
      type uint32;
      description "swoff mc id resource pool bank 0 max";
    }

    leaf sysport_res_pool_bank_0_min {
      type uint32;
      description "system-port resource pool bank 0 min";
    }

    leaf sysport_res_pool_bank_0_max {
      type uint32;
      description "system-port resource pool bank 0 max";
    }

    leaf vrf_id_res_pool_bank_0_min {
      type uint32;
      description "vrf id resource pool bank 0 min";
    }

    leaf vrf_id_res_pool_bank_0_max {
      type uint32;
      description "vrf id resource pool bank 0 max";
    }

    leaf span_res_pool_bank_0_min {
      type uint32;
      description "SPAN resource pool bank 0 min";
    }

    leaf span_res_pool_bank_0_max {
      type uint32;
      description "SPAN resource pool bank 0 max";
    }

    leaf span_res_pool_bank_1_min {
      type uint32;
      description "SPAN resource pool bank 1 min";
    }

    leaf span_res_pool_bank_1_max {
      type uint32;
      description "SPAN resource pool bank 1 max";
    }

    leaf switch_id_res_pool_bank_0_min {
      type uint32;
      description "switch id resource pool bank 0 min";
    }

    leaf switch_id_res_pool_bank_0_max {
      type uint32;
      description "switch id resource pool bank 0 max";
    }

    leaf physical_lif_offset {
      type uint32;
      description "Physical LIF offset";
    }

    leaf slot_lif_offset {
      type uint32;
      description "Slot LIF offset";
    }

    leaf bdl_lif_rid_level {
      type uint32;
      description "Lif level";
    }

    leaf l2_lif_rid_level {
      type uint32;
      description "L2 Lif level";
    }

    leaf l3a_intf_id_rid_level {
      type uint32;
      description "VSI interface's rid level";
    }

    leaf l2_intf_subintf_lif_rid_level {
      type uint32;
      description "L2 interface and sub interface lif level";
    }

    leaf vrf_rif_rid_level {
      type uint32;
      description "VRF Rif level";
    }

    leaf bvi_rif_min {
      type uint32;
      description "BVI Rif minimum value";
    }

    leaf bvi_rif_max {
      type uint32;
      description "BVI Rif max value";
    }

    leaf mrib4_mrid_min {
      type uint32;
      description "MRIB MRID minimum value";
    }

    leaf mrib4_mrid_max {
      type uint32;
      description "MRIB MRID max value";
    }

    leaf mrib6_mrid_min {
      type uint32;
      description "MRIB6 MRID minimum value";
    }

    leaf mrib6_mrid_max {
      type uint32;
      description "MRIB6 MRID max value";
    }

    leaf bfd_remote_id_rid_level {
      type uint32;
      description "rid level for bfd remote_id";
    }

    leaf is_rx_inj_port_check_needed {
      type uint32;
      description "flag to check if rx inject port check is needed in port-mapper";
    }

    leaf tunnel_encapid_rid_level {
      type uint32;
      description "rid level for bfd tunnel encap";
    }

    leaf bfd_pmdb_slot {
      type int32;
      description "bfd pmdb slot";
    }

    leaf is_bvi_rif_check_needed {
      type uint32;
      description "flag to check if BVI rif check is needed in port-mapper";
    }

    leaf max_ecmp_path_num {
      type uint32;
      description "maximum number of ecmp paths";
    }

    leaf bundle_l3_lif_offset {
      type uint32;
      description "lif offset for bundle and l3 sub intfs";
    }
  }
}
