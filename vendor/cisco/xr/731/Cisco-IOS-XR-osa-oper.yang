module Cisco-IOS-XR-osa-oper {
  namespace "http://cisco.com/ns/yang/Cisco-IOS-XR-osa-oper";
  prefix osa-oper;

  import Cisco-IOS-XR-types {
    prefix xr;
  }
  import cisco-semver {
    prefix semver;
  }
  include Cisco-IOS-XR-osa-oper-sub1 {
    revision-date 2020-06-01;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR osa package operational data.
     
     This module contains definitions
     for the following management objects:
       osa: Show hw-module location
     
     Copyright (c) 2013-2020 by Cisco Systems, Inc.
     All rights reserved.";

  revision 2020-06-01 {
    description
      "Enhancement to support LC startup config complete";
    semver:module-version "1.3.0";
  }
  revision 2019-10-11 {
    description
      "Enhancement in CLI for 50G trunk-rate";
    semver:module-version "1.2.0";
  }
  revision 2019-08-13 {
    description
      "Aligning modifications to 7.1.1.";
    semver:module-version "1.1.0";
  }
  revision 2019-04-05 {
    description
      "Establish semantic version baseline.";
    semver:module-version "1.0.0";
  }
  revision 2018-05-23 {
    description
      "Initial Revision.";
  }
  revision 2015-11-09 {
    description
      "IOS XR 6.0 revision.";
  }

  container osa {
    config false;
    description
      "Show hw-module location";
    container node-ids {
      description
        "Per-node OSA operational data";
      list node-id {
        key "node-name";
        description
          "Node ID of LC";
        container startup-config-complete {
          description
            "Display LC startup config complete";
          uses OSA-HWMOD-LC-STARTUP-CFG-B;
        }
        container mxponder-slices {
          description
            "Display Muxponder Slice Information";
          list mxponder-slice {
            key "slice-id";
            description
              "Per slice num data";
            leaf slice-id {
              type uint32;
              description
                "Slice Id";
            }
            uses HW-MODULE-SLICE-INFO-B;
          }
        }
        container regen {
          description
            "Display Regeneration Module Information";
          uses OSA-HWMOD-REGEN-OP;
        }
        container xponder-capabilities {
          description
            "HW capability container";
          container mxponder-slice-hw-capabilities {
            description
              "MXP/TXP slice HW capabilities";
            list mxponder-slice-hw-capability {
              key "slice-id";
              description
                "Per slice HW capabilities";
              leaf slice-id {
                type uint32;
                description
                  "Slice Id";
              }
              uses OSA-HWMOD-XPONDER-SLICE-CAPAB-INFO-B;
            }
          }
          container mxponder-hw-capabilities {
            description
              "MXP/TXP bundle HW capabilities";
            uses OSA-HWMOD-XPONDER-SLICE-CAPAB-INFO-B;
          }
        }
        container mxponder {
          description
            "Display Muxponder Information";
          uses OSA-HWMOD-MXPONDER-OP;
        }
        leaf node-name {
          type xr:Node-id;
          description
            "The identifier for the node";
        }
      }
    }
  }
}
