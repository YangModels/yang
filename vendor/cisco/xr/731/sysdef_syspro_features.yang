/******************************************************************
*
* sysdef_syspro_features.yang
*
* Copyright (c) 2020-2021 by cisco Systems, Inc.
* All rights reserved.
*******************************************************************/

module sysdef_syspro_features {
  namespace "http://www.cisco.com/ns/yang/plat_sys_profile/sysdef_syspro_features";
  prefix sysdef_syspro_features;

  organization
    "Cisco Systems Inc.";

  contact
    "Cisco Systems, Inc.
    170 West Tasman Drive
    San Jose, CA  95134-1706
    US";

  description
    "syspro_features model";

  revision "2020-05-01" {
    description "Initial revision";
  }

  grouping sysdef_syspro_features {
    description
      "Syspro System features Profile";

    leaf is_snoop_simple {
      type uint32;
      description "Is snoop simple enabled";
    }

    leaf is_olp_enabled {
      type uint32;
      description "Is OLP enabled";
    }

    leaf is_routing_prof_granular {
      type uint32;
      description "Routing profile granularity";
    }

    leaf is_mpls_ttl_exp_inheritance_supported {
      type uint32;
      description "MPLS TTL EXP enheritance model";
    }

    leaf is_ovelay_ll_supported {
      type uint32;
      description "Overlay LL entries support";
    }

    leaf acl_nf_snoop_size_supported {
      type int32;
      description "SNOOP packet size";
    }

    leaf is_pkt_prio_supported {
      type uint32;
      description "Packet priority support";
    }

    leaf max_number_of_mirror_gids {
      type uint32;
      description "Maximum number of GID's available per chip";
    }

    leaf is_ingress_p2p_delay_supported {
      type uint32;
      description "Is INGRESS_P2P_DELAY supported";
    }
  }
}
