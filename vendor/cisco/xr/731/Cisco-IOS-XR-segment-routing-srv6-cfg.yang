module Cisco-IOS-XR-segment-routing-srv6-cfg {
  namespace "http://cisco.com/ns/yang/Cisco-IOS-XR-segment-routing-srv6-cfg";
  prefix segment-routing-srv6-cfg;

  import ietf-inet-types {
    prefix inet;
  }
  import cisco-semver {
    prefix semver;
  }
  import Cisco-IOS-XR-segment-routing-srv6-datatypes {
    prefix dt1;
  }
  import Cisco-IOS-XR-segment-routing-ms-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR segment-routing-srv6 package configuration.
     
     This YANG module augments the
       Cisco-IOS-XR-segment-routing-ms-cfg
     module with configuration data.
     
     Copyright (c) 2013-2019 by Cisco Systems, Inc.
     All rights reserved.";

  revision 2019-11-21 {
    description
      "Support for anycast locator flag";
    semver:module-version "1.2.0";
  }
  revision 2019-04-05 {
    description
      "Establish semantic version baseline.";
    semver:module-version "1.0.1";
  }
  revision 2015-11-09 {
    description
      "IOS XR 6.0 revision.";
  }

  augment "/a1:sr" {
    description
      "This augment extends the configuration data of
       'Cisco-IOS-XR-segment-routing-ms-cfg'";
    container srv6 {
      description
        "Segment Routing with IPv6 dataplane";
      container logging {
        description
          "Enable logging";
        leaf locator-status {
          type empty;
          description
            "Enable logging for locator status changes";
        }
      }
      container micro-segment-global-params {
        description
          "Configure micro-segment related parameters";
        leaf merge-overlay-underlay-sids {
          type empty;
          description
            "Enable merge mode for SIDs from overlay and
             underlay";
        }
      }
      container locators {
        description
          "Configure SRv6 locators parameters";
        container locators {
          description
            "Configure SRv6 table of locators";
          list locator {
            key "name";
            description
              "Configure a SRv6 locator";
            container micro-segment {
              description
                "Configure micro-segments (uSID) related
                 parameters";
              leaf behavior {
                type dt1:Srv6u-behavior;
                description
                  "Specify Locator's behavior";
              }
            }
            container prefix {
              description
                "Specify locator prefix value";
              leaf prefix {
                type inet:ip-address-no-zone;
                description
                  "IPv6 Prefix";
              }
              leaf prefix-length {
                type dt1:Srv6-locator-len;
                description
                  "Prefix length";
              }
            }
            leaf locator-enable {
              type empty;
              description
                "Enable a SRv6 locator";
            }
            leaf anycast {
              type empty;
              description
                "Specify locator to be anycast type";
            }
            leaf algorithm {
              type dt1:Srv6-algo-value;
              description
                "Specify locator algorithm";
            }
            leaf name {
              type dt1:Srv6-locator-name;
              description
                "Locator name";
            }
          }
        }
      }
      container encapsulation {
        description
          "Configure encapsulation related parameters";
        container traffic-class {
          description
            "Configure IPv6 header traffic-class";
          leaf option {
            type dt1:Srv6-encapsulation-tc-option;
            description
              "Config option";
          }
          leaf value {
            when "../option = 'value'" {
              description
                "../Option = Value";
            }
            type dt1:Srv6-encapsulation-tc-value;
            default "0";
            description
              "Field Value";
          }
        }
        container hop-limit {
          description
            "Configure IPv6 Hop-Limit options";
          leaf option {
            type dt1:Srv6-encapsulation-hop-limit-option;
            description
              "Hop-Limit config option";
          }
          leaf value {
            when "../option = 'count'" {
              description
                "../Option = Count";
            }
            type dt1:Srv6-encapsulation-hop-limit-value;
            default "0";
            description
              "Count for Hop-limit";
          }
        }
        leaf source-address {
          type inet:ip-address-no-zone;
          description
            "Configure a source address";
        }
      }
      leaf enable {
        type empty;
        description
          "Enable SRv6";
      }
      leaf sid-holdtime {
        type dt1:Srv6sid-holdtime;
        description
          "Configure SID holdtime for a stale/freed SID";
      }
    }
  }
}
