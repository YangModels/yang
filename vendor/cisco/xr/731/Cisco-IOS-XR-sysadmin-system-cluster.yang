module Cisco-IOS-XR-sysadmin-system-cluster {
  namespace "http://www.cisco.com/ns/yang/Cisco-IOS-XR-sysadmin-system-cluster";
  prefix calvados_system_cluster;

  import Cisco-IOS-XR-sysadmin-sm-system-cluster {
    prefix shelf_mgr;
  }
  import Cisco-IOS-XR-sysadmin-ethsw-esdma-mlap-connectivity-info-iosxrwbd {
    prefix cluster_connectivity;
  }
  import Cisco-IOS-XR-sysadmin-fabric-mgr-fsdb-aggregator-iosxrwbd {
    prefix cluster-fabric;
  }
  import cisco-semver {
    prefix semver;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains a collection of YANG
     definitions for Cisco IOS-XR SysAdmin configuration.
     
     This module defines the top level container for
     all 'system cluster' commands for Sysadmin.
     
     Copyright(c) 2020 by Cisco Systems, Inc.
     All rights reserved.
     
     Copyright (c) 2012-2020 by Cisco Systems, Inc.
     All rights reserved.";

  revision 2020-09-01 {
    description
      "Added support for cluster oper command";
    semver:module-version "1.0.0";
  }
  revision 2020-08-15 {
    description
      "Support 'system mac-address-pool' cli";
  }
  revision 2020-07-07 {
    description
      "Removed the config support";
  }
  revision 2020-06-10 {
    description
      "Created initial 'system cluster' refactorization";
  }

  grouping cluster-oper-group {
    container cluster {
      config false;
      uses shelf_mgr:system-cluster-layout-oper-group;
      uses cluster_connectivity:cluster-connectivity-iosxrwbd;
      uses cluster_fabric_group;
    }
  }

  grouping cluster_fabric_group {
    container fabric {
      description
        "Fabric resource commands";
      uses cluster-fabric:fsdb_cluster_aggr_bundle;
    }
  }

  uses cluster-oper-group;
  container system {
    config false;
    container cluster {
      config false;
      container actions {
        config false;
        uses shelf_mgr:system-cluster-action-group;
      }
    }
    container macpool {
      config false;
      container actions {
        config false;
        uses shelf_mgr:system-macpool-action-group;
      }
    }
  }
}
