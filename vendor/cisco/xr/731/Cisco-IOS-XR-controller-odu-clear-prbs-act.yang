module Cisco-IOS-XR-controller-odu-clear-prbs-act {
  namespace "http://cisco.com/ns/yang/Cisco-IOS-XR-controller-odu-clear-prbs-act";
  prefix controller-odu-clear-prbs-act;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR clear prbs bit-errrs statistics for controller-odu module.
     
     Copyright (c) 2018-2020 by Cisco Systems, Inc.
     All rights reserved.";

  revision 2020-10-27 {
    description
      "Clear prbs bit-errors support for odu controllers";
  }

  rpc clear-controller-prbsdetails {
    description
      "Clear prbs bit-errors statistics";
    input {
      leaf controller {
        type string;
        description
          "Controller name in R/S/I/P format";
      }
      leaf prbsdetails {
        type empty;
        description
          "clear prbs bit-errors counter";
      }
    }
  }
}
