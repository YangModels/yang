module Cisco-IOS-XR-controller-cpri-oper {
  namespace "http://cisco.com/ns/yang/Cisco-IOS-XR-controller-cpri-oper";
  prefix controller-cpri-oper;

  import Cisco-IOS-XR-types {
    prefix xr;
  }
  import cisco-semver {
    prefix semver;
  }
  include Cisco-IOS-XR-controller-cpri-oper-sub1 {
    revision-date 2020-08-03;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR controller-cpri package operational data.
     
     This module contains definitions
     for the following management objects:
       cpri: CPRI operational data
     
     Copyright (c) 2013-2020 by Cisco Systems, Inc.
     All rights reserved.";

  revision 2020-08-03 {
    description
      "Changed leaf packet-len type to uint16. Renamed leaf errored-packets to errored-length-packets. Added leaves receive-good-packets and receive-roe-lcv-count.";
    semver:module-version "2.0.0";
  }
  revision 2019-12-02 {
    description
      "Show command subtype added for CPRI controller";
    semver:module-version "1.1.0";
  }
  revision 2019-04-05 {
    description
      "Establish semantic version baseline.";
    semver:module-version "1.0.0";
  }
  revision 2015-11-09 {
    description
      "IOS XR 6.0 revision.";
  }

  container cpri {
    config false;
    description
      "CPRI operational data";
    container controllers {
      description
        "All CPRI controller operational data";
      list controller {
        key "controller-name";
        description
          "CPRI controller operational data";
        container detail {
          description
            "CPRI controller detailed data including ROE
             stats";
          uses CPRI-PORT-DETAIL;
        }
        container stats {
          description
            "CPRI controller operational data statistics";
          uses CPRI-PORT-STATS;
        }
        container info {
          description
            "CPRI controller operational data";
          uses CPRI-PORT-INFO;
        }
        container roe-stats {
          description
            "ROE statistics w.r.t CPRI controller";
          uses CPRI-PORT-ROE-STATS;
        }
        container roe-profile {
          description
            "ROE profile params associated with CPRI
             controller";
          uses CPRI-PORT-ROE-PROFILE;
        }
        leaf controller-name {
          type xr:Interface-name;
          description
            "Interface name";
        }
      }
    }
  }
}
