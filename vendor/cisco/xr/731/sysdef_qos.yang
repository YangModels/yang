/******************************************************************************
 *
 * File: sysdef_qos.yang
 *
 * Description:
 * System Definition Yang model for QoS
 *
 * Copyright (c) 2020 by Cisco Systems, Inc.
 * All rights reserved.
 *
 *****************************************************************************/
module sysdef_qos {
  namespace "http://www.cisco.com/ns/yang/sysdef/sysdef_qos";
  prefix sysdef_qos;

  import sysdef_ext {
    prefix sysdef_ext;
  }

  organization
    "Cisco Systems Inc.";

  contact
    "Cisco Systems, Inc.
    170 West Tasman Drive
    San Jose, CA  95134-1706
    US";

  description
    "System Definition Platform Information";

  revision "2020-10-13" {
    description "Initial revision";
  }

  grouping sysdef_qos {
    description
      "Platform QoS System Definition";

  }
}
