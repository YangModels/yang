/******************************************************************
*
* sysdef_syspro_trap.yang
*
* Copyright (c) 2020-2021 by cisco Systems, Inc.
* All rights reserved.
*******************************************************************/

module sysdef_syspro_trap {
  namespace "http://www.cisco.com/ns/yang/plat_sys_profile/sysdef_syspro_trap";
  prefix sysdef_syspro_trap;

  organization
    "Cisco Systems Inc.";

  contact
    "Cisco Systems, Inc.
    170 West Tasman Drive
    San Jose, CA  95134-1706
    US";

  description
    "syspro_trap model";

  revision "2020-05-01" {
    description "Initial revision";
  }

  grouping sysdef_syspro_trap {
    description
      "Syspro Trap System Profile";

    leaf ovld_oam_to_rp {
      type uint32;
      description "OVLD OAM Trap To RP";
    }

    leaf ovld_l2_to_rp {
      type uint32;
      description "OVLD L2 TRAP DST to RP";
    }
  }
}
