/******************************************************************************
 *
 * File: sysdef_platform.yang
 *
 * Description:
 * System Definition Yang model
 *
 * Copyright (c) 2020 by Cisco Systems, Inc.
 * All rights reserved.
 *
 *****************************************************************************/
module sysdef_platform_info {
  namespace "http://www.cisco.com/ns/yang/sysdef/sysdef_platform_info";
  prefix sysdef_platform_info;

  import sysdef_ext {
    prefix sysdef_ext;
  }

  organization
    "Cisco Systems Inc.";

  contact
    "Cisco Systems, Inc.
    170 West Tasman Drive
    San Jose, CA  95134-1706
    US";

  description
    "System Definition Platform Information";

  revision "2020-03-24" {
    description "Initial revision";
  }

/******************************************************************************
Section for Macros
******************************************************************************/
  typedef PLATFORM_NAME_LEN {
    type uint32 {
      sysdef_ext:const "64";
    }
  }

  typedef PLATFORM_DESCRIPTION_LEN {
    type uint32 {
      sysdef_ext:const "256";
    }
  }

  typedef PLATFORM_ABBREV_LEN {
    type uint32 {
      sysdef_ext:const "16";
    }
  }

/******************************************************************************
Section for Enumerations
******************************************************************************/
  typedef platform_family {
    description "Platform Family Types";

    type enumeration {
      enum PLATFORM_FAMILY_BASE {
        value 0;
      }

      enum PLATFORM_FAMILY_SPITFIRE {
        value 1;
      }

      enum PLATFORM_FAMILY_FRETTA {
        value 2;
      }

      enum PLATFORM_FAMILY_SCAPA {
        value 3;
      }

      enum PLATFORM_FAMILY_ENXR {
        value 4;
      }

      enum PLATFORM_FAMILY_UEA {
        value 5;
      }

      enum PLATFORM_FAMILY_SKYWARP {
        value 6;
      }

      enum PLATFORM_FAMILY_PANINI {
        value 7;
      }

      enum PLATFORM_FAMILY_ZERMATT {
        value 8;
      }

      enum PLATFORM_FAMILY_BIGBEND {
        value 9;
      }

      enum PLATFORM_FAMILY_DARWIN {
        value 10;
      }

      enum PLATFORM_FAMILY_NCS5700 {
        value 11;
      }

      enum PLATFORM_FAMILY_WBD {
        value 12;
      }

      enum PLATFORM_FAMILY_OTHER {
        value 13;
      }

      enum PLATFORM_FAMILY_MAX {
        value 14;
      }
    }
  }

  typedef form_factor {
    description
      "Platform Form Factor";

    type enumeration {

      enum BASE_PLATFORM {
        value 0;
      }

      enum FIXED_PLATFORM {
        value 1;
      }

      enum DISTRIBUTED_PLATFORM {
        value 2;
      }

      enum CENTRALIZED_PLATFORM {
        value 3;
      }

      enum UNKNOWN_PLATFORM {
        value 4;
      }
    }
  }

  /* Not using the same values from platform_cardtypes.h  */
  typedef board_pi_type {
    description "Board PI Types";

    type enumeration {
      enum  BOARD_TYPE_UNKNOWN {
        value 0;
      }
      enum  BOARD_TYPE_RP {
        value 1;
      }

      enum  BOARD_TYPE_LC {
        value 2;
      }

      enum  BOARD_TYPE_FC {
        value 3;
      }

      enum  BOARD_TYPE_FT {
        value 4;
      }

      enum  BOARD_TYPE_PM {
        value 5;
      }
    }
  }

/******************************************************************************
Platform Profile Info related Structures
******************************************************************************/
  grouping nif_port_config {
    description "Network Interface Port configuration";

    leaf port_number {
      type uint32;
      description "Front panel port number";
    }

    leaf asic_num {
      type uint32;
      description "Asic num used for this Port";
    }

    leaf is_sfp_port {
      type uint32;
      description "Is this port an SFP port";
    }

    /*
     * Unlike QSFP port, each SFP port uses one lane(subport) from a given NIF
     * This represent that lane/subport for a sfp port
     */
    leaf sfp_subport {
      type uint32;
      description "Subport in an SFP port used from a NIF";
    }
  }

  grouping board_slice_attributes {
    description
      "Board Slice Attributes";

    leaf max_slice_per_npu {
      type uint32;
      description "Maximum number of slices per npu";
    }

    leaf max_network_slices {
      type uint32;
      description "Maximum number of Network slices";
    }

    leaf max_fabric_slices {
      type uint32;
      description "Maximum number of Fabric slices";
    }

    leaf slice_mode_bitmap {
      type uint32;
      description "Slice Mode Bitmap. Each bit represents a slice. 0 represents slice in network mode and 1 represents slice in fabric mode.";
    }
  }

  grouping board_attributes {
    description
      "Board Attributes";

    leaf pi_type {
      type board_pi_type;
    }

    leaf form_factor {
      type form_factor;
    }

    leaf max_npu {
      type uint32;
      description "Maximum number of npu";
    }

    container slice_attributes {
      uses board_slice_attributes;
    }

    list nif_port_config {
      uses nif_port_config;
      description "Port configuration";
    }
  }

  grouping sysdef_platform_info {
    description
      "Platform System Definition";

    leaf pid {
      type string {
        sysdef_ext:max-length "PLATFORM_NAME_LEN";
      }
    }

    leaf platform_description {
      type string {
        sysdef_ext:max-length "PLATFORM_DESCRIPTION_LEN";
      }
    }

    leaf platform_abbreviation {
      type string {
        sysdef_ext:max-length "PLATFORM_ABBREV_LEN";
      }
    }

    leaf platform_family {
      type platform_family;
    }

    container board_attributes {
      uses board_attributes;
    }
  }
}
