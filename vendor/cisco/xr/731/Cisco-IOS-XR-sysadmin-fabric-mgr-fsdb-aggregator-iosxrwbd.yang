module Cisco-IOS-XR-sysadmin-fabric-mgr-fsdb-aggregator-iosxrwbd {
  namespace "http://www.cisco.com/ns/yang/Cisco-IOS-XR-sysadmin-fabric-mgr-fsdb-aggregator-iosxrwbd";
  prefix fabric_fsdb_aggr;

  import tailf-common {
    prefix tailf;
  }
  import Cisco-IOS-XR-sysadmin-fabric-types {
    prefix fabric-types;
  }
  import Cisco-IOS-XR-sysadmin-show-trace {
    prefix show-trace;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains definitions
     for the Calvados model objects.
     
     Copyright (c) 2012-2020 by Cisco Systems, Inc.
     All rights reserved.";

  revision 2020-10-06 {
    description
      "Removed admin plane config.";
    semver:module-version "1.0.0";
  }
  revision 2020-07-22 {
    description
      "Implemented single fabric-type model for all platform.";
  }
  revision 2019-05-24 {
    description
      "Support for show controller fabric health CLI.";
  }
  revision 2019-04-15 {
    description
      "Establish semantic version baseline.";
  }
  revision 2018-04-09 {
    description
      "Required changes for ConfD 6.4.5";
  }
  revision 2017-06-07 {
    description
      "Updated the relative path for instance_folded config";
  }
  revision 2017-05-22 {
    description
      "Support added to place fabric link ports in maintenance.";
  }
  revision 2017-05-01 {
    description
      "Namespace change to comply with Cisco guidelines on namespace";
  }
  revision 2016-10-12 {
    description
      "Unhide commands and configs. Moved to advanced-grp";
  }

  typedef node_location_type_iosxrwbd {
    type string;
  }

  grouping plane_show {
    list plane {
      key "planeid";
      max-elements "1024";
      leaf planeid {
        type fabric-types:plane_type_iosxrwbd;
      }
      leaf admin-state {
        type string;
      }
      leaf ucast_oper_state {
        type string;
      }
      leaf mcast_oper_state {
        type string;
      }
      leaf plane_mode {
        type string;
      }
      leaf ucast_cnt_up {
        type int32;
      }
      leaf ucast_cnt_some_up {
        type int32;
      }
      leaf ucast_cnt_dn {
        type int32;
      }
      leaf mcast_cnt_up {
        type int32;
      }
      leaf mcast_cnt_some_up {
        type int32;
      }
      leaf mcast_cnt_dn {
        type int32;
      }
      leaf total_bundles {
        type int32;
      }
      leaf down_bundles {
        type int32;
      }
      leaf rx_data_cells {
        type uint64;
      }
      leaf tx_data_cells {
        type uint64;
      }
      leaf rx_ce_cells_is_overflow {
        type boolean;
      }
      leaf rx_ce_cells {
        type uint64;
      }
      leaf rx_uce_cells_is_overflow {
        type boolean;
      }
      leaf rx_uce_cells {
        type uint64;
      }
      leaf rx_pe_cells_is_overflow {
        type boolean;
      }
      leaf rx_pe_cells {
        type uint64;
      }
      leaf ucast_lost_cells {
        type uint32;
      }
      leaf mcast_lost_cells {
        type uint32;
      }
      leaf last_clear_ts {
        type string;
      }
      leaf last_clear_reason {
        type string;
      }
      leaf last_clear_req_ts {
        type string;
      }
      leaf last_clear_status {
        type string;
      }
      leaf is_asic_internal_error {
        type boolean;
      }
      leaf asic_internal_drops {
        type uint64;
      }
      leaf asic_location_drops {
        type string;
      }
      leaf ppu_state {
        type string;
      }
      list asic_internal_error {
        key "asic_number";
        leaf asic_number {
          type int64;
        }
        leaf asic_location {
          type string;
        }
        leaf link_crc_error {
          type boolean;
        }
        leaf link_size_error {
          type boolean;
        }
        leaf link_mis_align_error {
          type boolean;
        }
        leaf link_code_group_error {
          type boolean;
        }
        leaf link_no_sig_lock_error {
          type boolean;
        }
        leaf link_no_sign_accept_error {
          type boolean;
        }
        leaf link_token_error {
          type boolean;
        }
        leaf error_token_count {
          type boolean;
        }
        leaf last_asic_internal_error_ts {
          type string;
        }
      }
    }
  }

  grouping fsdb_agg_conf_plane {
    list plane {
      key "plane_id";
      description
        "Set state of fabric plane";
      leaf plane_id {
        type fabric-types:conf_plane_type_iosxrwbd;
      }
      leaf shutdown {
        type empty;
        description
          "Shut down state.";
      }
    }
    container link {
      description
        "Link configuration commands";
      container port {
        description
          "Set admin state of a fabric link port";
        list location {
          key "loc_str";
          leaf loc_str {
            type fabric-types:link_port_location_type_iosxrwbd;
          }
          leaf shutdown {
            type empty;
            description
              "Shut down state.";
          }
          leaf maintenance {
            type empty;
            description
              "maintenance state.";
          }
        }
      }
    }
  }

  grouping fabric_sys_plane_health {
    list sys_plane_info_list {
      key "plane_id";
      leaf plane_id {
        type int32;
      }
      leaf admin-state {
        type string;
      }
      leaf plane_state {
        type string;
      }
      leaf plane_mode {
        type string;
      }
      leaf ucast_cnt_dn {
        type int32;
      }
      leaf ucast_cnt_some_up {
        type int32;
      }
      leaf total_bundles {
        type int32;
      }
      leaf down_bundles {
        type int32;
      }
      leaf ppu_state {
        type string;
      }
      leaf racks_w_plane_fault {
        type int32;
      }
      leaf is_data_drop {
        type boolean;
      }
    }
  }

  grouping fsdb_process_status {
    list fsdb_status {
      key "rack_id";
      leaf rack_id {
        type int32;
      }
      leaf status {
        type boolean;
      }
    }
  }

  grouping sfe_process_status {
    list sfe_status {
      key "rack_id";
      leaf rack_id {
        type int32;
      }
      leaf status {
        type boolean;
      }
    }
    list sfe_drvr_loc {
      key "loc_str";
      leaf loc_str {
        type string;
      }
    }
    list sfe_fm_sep {
      key "loc_str";
      leaf loc_str {
        type string;
      }
    }
  }

  grouping rack_plane_num_amba_reachable {
    list reachable_amba {
      key "idx";
      leaf idx {
        type int32;
      }
      leaf num_reachable {
        type int32;
      }
    }
  }

  grouping fabric_rack_plane_health {
    list rack_plane_info_list {
      key "plane_id";
      leaf plane_id {
        type int32;
      }
      leaf plane_state {
        type string;
      }
      leaf plane_mode {
        type string;
      }
      leaf asics_total {
        type int32;
      }
      leaf asics_up {
        type int32;
      }
      leaf asics_dn {
        type int32;
      }
      uses rack_plane_num_amba_reachable;
    }
  }

  grouping fabric_rack_health {
    list rack_info_list {
      key "rack_id";
      leaf rack_id {
        type int32;
      }
      leaf rack_name {
        type string;
      }
      leaf rack_type {
        type string;
      }
      leaf plane_num {
        type int32;
      }
      leaf sfe_asics_total {
        type int32;
      }
      leaf sfe_asics_up {
        type int32;
      }
      leaf sfe_asics_dn {
        type int32;
      }
      leaf fia_asics_total {
        type int32;
      }
      leaf fia_asics_up {
        type int32;
      }
      leaf fia_asics_dn {
        type int32;
      }
      leaf plane_up {
        type uint32;
      }
      leaf plane_dn {
        type uint32;
      }
      leaf plane_mcast_dn {
        type uint32;
      }
      leaf plane_admin_dn {
        type uint32;
      }
      leaf show_rack_plane_detail {
        type boolean;
        default "false";
      }
      leaf amba_valid {
        type int32;
      }
    }
  }

  grouping fabric_health {
    container fab_health {
      list sys_info_list {
        key "index_key";
        leaf index_key {
          type int32;
        }
        leaf aggr_status {
          type boolean;
        }
        leaf available_rack_ids {
          type string;
        }
        leaf rack_id_separator {
          type string;
        }
        leaf available_fm_loc {
          type string;
        }
        leaf fm_loc_separator {
          type string;
        }
        leaf rack_total {
          type uint32;
        }
        leaf rack_lcc {
          type uint32;
        }
        leaf rack_fcc {
          type uint32;
        }
        leaf plane_up {
          type uint32;
        }
        leaf plane_dn {
          type uint32;
        }
        leaf plane_mcast_dn {
          type uint32;
        }
        leaf plane_admin_dn {
          type uint32;
        }
        leaf show_sys_plane_detail {
          type boolean;
          default "false";
        }
        leaf sfe_asics_total {
          type uint32;
        }
        leaf sfe_asics_up {
          type uint32;
        }
        leaf sfe_asics_dn {
          type uint32;
        }
        leaf fia_asics_total {
          type uint32;
        }
        leaf fia_asics_up {
          type uint32;
        }
        leaf fia_asics_dn {
          type uint32;
        }
        uses fabric_sys_plane_health;
        uses fabric_rack_health;
        uses fsdb_process_status;
        uses sfe_process_status;
      }
    }
  }

  grouping fsdb_agg_plane_clear {
    list plane {
      key "planeid";
      leaf planeid {
        type fabric-types:plane_type_iosxrwbd;
      }
      tailf:action "clear_counter" {
        input;
        output;
      }
      tailf:action "clear_stats" {
        input;
        output;
      }
    }
  }

  grouping fsdb_aggr_trace {
    container fsdb-aggregator {
      description
        "FSDB Aggregator information";
      container fsdbagg {
        uses show-trace:traceable;
      }
    }
  }

  grouping fsdb_aggr_ppu {
    container ppu {
      description
        "Plane by plane upgrade.";
      tailf:action "start" {
        description
          "Start PPU.";
        input;
        output {
          leaf PPU {
            type string;
          }
        }
      }
      tailf:action "force" {
        description
          "Force PPU.";
        input;
        output {
          leaf PPU {
            type string;
          }
        }
      }
    }
  }

  grouping bundle_summary_show {
    list bundle_summary_list {
      key "idx";
      leaf idx {
        type int32;
      }
      leaf total_bundles {
        type uint32;
      }
      leaf down_bundles {
        type uint32;
      }
      leaf bundles_not_connected {
        type uint32;
      }
      leaf total_bports {
        type uint32;
      }
      leaf down_bports {
        type uint32;
      }
      leaf bports_not_connected {
        type uint32;
      }
    }
  }

  grouping bundle_all_show {
    list bundle_all_list {
      key "idx";
      leaf idx {
        type int64;
      }
      leaf bundle_id {
        type string;
      }
      leaf oper_state {
        type string;
      }
      leaf plane_id {
        type uint32;
      }
      leaf total_links {
        type uint32;
      }
      leaf down_links {
        type uint32;
      }
      leaf bport1 {
        type string;
      }
      leaf bport2 {
        type string;
      }
    }
  }

  grouping bconnection_all_show {
    list bconnection_all_list {
      key "idx";
      leaf idx {
        type int64;
      }
      leaf bport_id {
        type string;
      }
      leaf oper_state {
        type string;
      }
      leaf bport_expected_id {
        type string;
      }
      leaf bport_actual_id {
        type string;
      }
      leaf bport_mismatch {
        type string;
      }
    }
  }

  grouping bport_all_show {
    list bport_all_list {
      key "idx";
      leaf idx {
        type int64;
      }
      leaf bport_id {
        type string;
      }
      leaf admin-state {
        type string;
      }
      leaf oper_state {
        type string;
      }
      leaf down_flags {
        type string;
      }
    }
  }

  grouping bport_all_stats_show {
    list bport_stats_all_racks {
      key "idx";
      leaf idx {
        type int32;
      }
      leaf total_racks {
        type uint32;
      }
      list bport_stats_rack {
        key "idx";
        leaf idx {
          type int32;
        }
        leaf rack_num_str {
          type string;
        }
        list bport_stats {
          key "idx";
          leaf idx {
            type int64;
          }
          leaf bport_id {
            type string;
          }
          leaf rx_data_cells {
            type uint64;
          }
          leaf tx_data_cells {
            type uint64;
          }
          leaf rx_ce_cells_is_overflow {
            type boolean;
          }
          leaf rx_ce_cells {
            type uint64;
          }
          leaf rx_uce_cells_is_overflow {
            type boolean;
          }
          leaf rx_uce_cells {
            type uint64;
          }
          leaf rx_pe_cells_is_overflow {
            type boolean;
          }
          leaf rx_pe_cells {
            type uint64;
          }
          leaf last_clear_ts {
            type string;
          }
        }
      }
    }
  }

  grouping fsdb_cluster_aggr_bundle {
    container connectivity {
      list location {
        key "loc_str";
        leaf loc_str {
          type node_location_type_iosxrwbd;
        }
        uses bconnection_all_show;
      }
    }
  }

  grouping fsdb_aggr_bundle {
    container bundle {
      container summary {
        uses bundle_summary_show;
      }
      container all {
        uses bundle_all_show;
      }
      container connection {
        container all {
          uses bconnection_all_show;
        }
        list location {
          key "loc_str";
          leaf loc_str {
            type fabric-types:bundle_location_type_iosxrwbd;
          }
          uses bconnection_all_show;
        }
      }
      container port {
        container all {
          uses bport_all_show;
          container statistics {
            uses bport_all_stats_show;
          }
        }
        list location {
          key "loc_str";
          leaf loc_str {
            type fabric-types:bundle_location_type_iosxrwbd;
          }
          uses bport_all_show;
          container statistics {
            uses bport_all_stats_show;
          }
        }
      }
      list location {
        key "loc_str";
        leaf loc_str {
          type fabric-types:bundle_location_type_iosxrwbd;
        }
        uses bundle_all_show;
      }
    }
  }

  grouping fsdb_aggr_clear {
    container counter {
      config false;
      uses fsdb_agg_plane_clear;
    }
    container clear_statistics {
      config false;
      uses fsdb_agg_plane_clear;
    }
  }

  grouping fsdb_aggr {
    container fsdbagg_active {
      uses plane_show;
      uses fsdb_aggr_bundle;
      container statistics {
        uses plane_show;
      }
    }
    container fsdbagg_link {
      list port {
        key "portname";
        leaf portname {
          type fabric-types:link_port_type_iosxrwbd;
        }
        leaf description {
          type string;
          default "port.";
        }
      }
    }
    container fsdbagg_sfe_asic_type {
      list asic_types {
        key "asicname";
        leaf asicname {
          type string;
        }
        leaf description {
          type string;
          default "asic.";
        }
        list block {
          key "blockname";
          leaf blockname {
            type string;
          }
          leaf description {
            type string;
            default "asic block.";
          }
        }
      }
    }
    container fsdbagg_standby {
      uses plane_show;
      container statistics {
        uses plane_show;
      }
    }
    uses fabric_health;
    uses fsdb_aggr_trace;
  }
}
