module Cisco-IOS-XR-platforms-ofa-table-stats-oper {
  namespace "http://cisco.com/ns/yang/Cisco-IOS-XR-platforms-ofa-table-stats-oper";
  prefix platforms-ofa-table-stats-oper;

  import Cisco-IOS-XR-types {
    prefix xr;
  }
  import cisco-semver {
    prefix semver;
  }
  include Cisco-IOS-XR-platforms-ofa-table-stats-oper-sub1 {
    revision-date 2020-06-19;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR platforms-ofa-table-stats package operational data.
     
     This module contains definitions
     for the following management objects:
       ofa: OFA Data
     
     Copyright (c) 2013-2020 by Cisco Systems, Inc.
     All rights reserved.";

  revision 2020-06-19 {
    description
      "Bwalk Error Counters";
    semver:module-version "2.0.0";
  }
  revision 2019-12-14 {
    description
      "Added the Yang Model for ofa sw resources";
    semver:module-version "1.1.0";
  }
  revision 2019-06-06 {
    description
      "Added the Yang Model for ofa sw resources";
    semver:module-version "1.0.0";
  }
  revision 2019-04-05 {
    description
      "Establish semantic version baseline.";
  }
  revision 2015-11-09 {
    description
      "IOS XR 6.0 revision.";
  }

  typedef Ofa-table {
    type enumeration {
      enum "test-if" {
        value 0;
        description
          "test if";
      }
      enum "test-if-with-create-reject" {
        value 1;
        description
          "testifwithcreatereject";
      }
      enum "test-nh" {
        value 2;
        description
          "test nh";
      }
      enum "test-global-discard" {
        value 3;
        description
          "testglobaldiscard";
      }
      enum "test-nhg" {
        value 4;
        description
          "test nhg";
      }
      enum "test-rt" {
        value 5;
        description
          "test rt";
      }
      enum "test-dynhg" {
        value 6;
        description
          "testdynhg";
      }
      enum "test-async-nhg" {
        value 7;
        description
          "testasyncnhg";
      }
      enum "test-async-nhgstats" {
        value 8;
        description
          "testasyncnhgstats";
      }
      enum "test-ip-punt-policy" {
        value 9;
        description
          "test ippuntpolicy";
      }
      enum "test-punt" {
        value 10;
        description
          "test punt";
      }
      enum "test-punt-policy-stats" {
        value 11;
        description
          "testpuntpolicystats";
      }
      enum "test-async-update" {
        value 12;
        description
          "testasyncupdate";
      }
      enum "test-async-barrier-with-knob" {
        value 13;
        description
          "testasyncbarrierwithknob";
      }
      enum "test-async-barrier-with-outknob" {
        value 14;
        description
          "testasyncbarrierwithoutknob";
      }
      enum "test-o-fast-ats" {
        value 15;
        description
          "testofastats";
      }
      enum "test-o-fast-ats1" {
        value 16;
        description
          "testofastats1";
      }
      enum "test-o-fast-ats2" {
        value 17;
        description
          "testofastats2";
      }
      enum "test-dpastats1" {
        value 18;
        description
          "testdpastats1";
      }
      enum "test-dpastats2" {
        value 19;
        description
          "testdpastats2";
      }
      enum "test-srvgrid" {
        value 20;
        description
          "testsrvgrid";
      }
      enum "test-ddel-q" {
        value 21;
        description
          "test ddel q";
      }
      enum "test-mco-list" {
        value 22;
        description
          "testmcolist";
      }
      enum "test-syncmco-list" {
        value 23;
        description
          "testsyncmcolist";
      }
      enum "test-syncmctblstats" {
        value 24;
        description
          "testsyncmctblstats";
      }
      enum "test-dddp" {
        value 25;
        description
          "testdddp";
      }
      enum "test-grid1" {
        value 26;
        description
          "testgrid1";
      }
      enum "sys" {
        value 27;
        description
          "sys";
      }
      enum "npu" {
        value 28;
        description
          "npu";
      }
      enum "npuhwid" {
        value 29;
        description
          "npuhwid";
      }
      enum "optics-port" {
        value 30;
        description
          "opticsport";
      }
      enum "gi-port" {
        value 31;
        description
          "giport";
      }
      enum "l1-port" {
        value 32;
        description
          "l1port";
      }
      enum "mac-port" {
        value 33;
        description
          "macport";
      }
      enum "l2-port" {
        value 34;
        description
          "l2port";
      }
      enum "eth-port" {
        value 35;
        description
          "ethport";
      }
      enum "l2intf" {
        value 36;
        description
          "l2intf";
      }
      enum "l2if" {
        value 37;
        description
          "l2if";
      }
      enum "mplspwe-port" {
        value 38;
        description
          "mplspweport";
      }
      enum "mplspwe-port-o-list" {
        value 39;
        description
          "mplspweport olist";
      }
      enum "mhpwe-port" {
        value 40;
        description
          "mhpweport";
      }
      enum "l2xc" {
        value 41;
        description
          "l2xc";
      }
      enum "l2vpnstats" {
        value 42;
        description
          "l2vpnstats";
      }
      enum "l1-ports-tats" {
        value 43;
        description
          "l1portstats";
      }
      enum "mac-ports-tats" {
        value 44;
        description
          "macportstats";
      }
      enum "l3intf" {
        value 45;
        description
          "l3intf";
      }
      enum "l3if" {
        value 46;
        description
          "l3if";
      }
      enum "l3intfrxstats" {
        value 47;
        description
          "l3intfrxstats";
      }
      enum "ip-route" {
        value 48;
        description
          "iproute";
      }
      enum "ip6-route" {
        value 49;
        description
          "ip6route";
      }
      enum "punt-policy-stats" {
        value 50;
        description
          "puntpolicystats";
      }
      enum "lpts-policy-stats" {
        value 51;
        description
          "lptspolicystats";
      }
      enum "tep" {
        value 52;
        description
          "tep";
      }
      enum "ip-punt-policy" {
        value 53;
        description
          "ippuntpolicy";
      }
      enum "ip6-punt-policy" {
        value 54;
        description
          "ip6puntpolicy";
      }
      enum "iplpts-policy" {
        value 55;
        description
          "iplptspolicy";
      }
      enum "ip6lpts-policy" {
        value 56;
        description
          "ip6lptspolicy";
      }
      enum "isis-punt-policy" {
        value 57;
        description
          "isispuntpolicy";
      }
      enum "isislpts-policy" {
        value 58;
        description
          "isislptspolicy";
      }
      enum "nh-group" {
        value 59;
        description
          "nhgroup";
      }
      enum "ipnh-group" {
        value 60;
        description
          "ipnhgroup";
      }
      enum "ip6nh-group" {
        value 61;
        description
          "ip6nhgroup";
      }
      enum "ipnh" {
        value 62;
        description
          "ipnh";
      }
      enum "ip6nh" {
        value 63;
        description
          "ip6nh";
      }
      enum "ipvrf" {
        value 64;
        description
          "ipvrf";
      }
      enum "vrfid" {
        value 65;
        description
          "vrfid";
      }
      enum "mplsnh" {
        value 66;
        description
          "mplsnh";
      }
      enum "lspnh" {
        value 67;
        description
          "lspnh";
      }
      enum "mpls-label" {
        value 68;
        description
          "mplslabel";
      }
      enum "punt" {
        value 69;
        description
          "punt";
      }
      enum "punt-police-r" {
        value 70;
        description
          "puntpolicer";
      }
      enum "lpts-police-r" {
        value 71;
        description
          "lptspolicer";
      }
      enum "punt-lpts-police-r" {
        value 72;
        description
          "puntlptspolicer";
      }
      enum "punt-stats" {
        value 73;
        description
          "puntstats";
      }
      enum "tm-port" {
        value 74;
        description
          "tmport";
      }
      enum "span-session" {
        value 75;
        description
          "spansession";
      }
      enum "police-rstats" {
        value 76;
        description
          "policerstats";
      }
      enum "tm-ports-tats" {
        value 77;
        description
          "tmportstats";
      }
      enum "l3intftxstats" {
        value 78;
        description
          "l3intftxstats";
      }
      enum "mplstetxstats" {
        value 79;
        description
          "mplstetxstats";
      }
      enum "mplslblstats" {
        value 80;
        description
          "mplslblstats";
      }
      enum "police-r" {
        value 81;
        description
          "policer";
      }
      enum "l2intfrxstats" {
        value 82;
        description
          "l2intfrxstats";
      }
      enum "l2intftxstats" {
        value 83;
        description
          "l2intftxstats";
      }
      enum "pbr-tt-ipv4" {
        value 84;
        description
          "pbr tt ipv4";
      }
      enum "pbr-tt-ipv6" {
        value 85;
        description
          "pbr tt ipv6";
      }
      enum "bfdhwoff" {
        value 86;
        description
          "bfdhwoff";
      }
      enum "bfdoff" {
        value 87;
        description
          "bfdoff";
      }
      enum "bfdoffstats" {
        value 88;
        description
          "bfdoffstats";
      }
      enum "global" {
        value 89;
        description
          "global";
      }
      enum "lag-port" {
        value 90;
        description
          "lagport";
      }
      enum "agg-port" {
        value 91;
        description
          "aggport";
      }
      enum "agg-member" {
        value 92;
        description
          "aggmember";
      }
      enum "qos-profile" {
        value 93;
        description
          "qosprofile";
      }
      enum "acl-profile" {
        value 94;
        description
          "acl profile";
      }
      enum "tmrate-profile" {
        value 95;
        description
          "tmrateprofile";
      }
      enum "ipacl" {
        value 96;
        description
          "ipacl";
      }
      enum "ip6acl" {
        value 97;
        description
          "ip6acl";
      }
      enum "sched-tree" {
        value 98;
        description
          "schedtree";
      }
      enum "tmcos" {
        value 99;
        description
          "tmcos";
      }
      enum "statsagg" {
        value 100;
        description
          "statsagg";
      }
      enum "nhprotect" {
        value 101;
        description
          "nhprotect";
      }
      enum "sampler" {
        value 102;
        description
          "sampler";
      }
      enum "l2qos" {
        value 103;
        description
          "l2qos";
      }
      enum "peer-qos" {
        value 104;
        description
          "peerqos";
      }
      enum "ipqos" {
        value 105;
        description
          "ipqos";
      }
      enum "ip6qos" {
        value 106;
        description
          "ip6qos";
      }
      enum "mplsqos" {
        value 107;
        description
          "mplsqos";
      }
      enum "qos-group" {
        value 108;
        description
          "qosgroup";
      }
      enum "qosid" {
        value 109;
        description
          "qosid";
      }
      enum "extlif" {
        value 110;
        description
          "extlif";
      }
      enum "elif" {
        value 111;
        description
          "elif";
      }
      enum "ingaclstats" {
        value 112;
        description
          "ingaclstats";
      }
      enum "egraclstats" {
        value 113;
        description
          "egraclstats";
      }
      enum "edpl" {
        value 114;
        description
          "edpl";
      }
      enum "l2protect" {
        value 115;
        description
          "l2protect";
      }
      enum "sat" {
        value 116;
        description
          "sat";
      }
      enum "satstats" {
        value 117;
        description
          "satstats";
      }
      enum "cfmoam-profile-def" {
        value 118;
        description
          "cfmoamprofiledef";
      }
      enum "cfmmaid" {
        value 119;
        description
          "cfmmaid";
      }
      enum "cfmdefmps" {
        value 120;
        description
          "cfmdefmps";
      }
      enum "cfmofflmep" {
        value 121;
        description
          "cfmofflmep";
      }
      enum "cfmoffrmep" {
        value 122;
        description
          "cfmoffrmep";
      }
      enum "cfmnonoff" {
        value 123;
        description
          "cfmnonoff";
      }
      enum "cfmhwoffrxstats" {
        value 124;
        description
          "cfmhwoffrxstats";
      }
      enum "ipmc-route" {
        value 125;
        description
          "ipmcroute";
      }
      enum "l2ipmc-route" {
        value 126;
        description
          "l2ipmcroute";
      }
      enum "ipmco-list" {
        value 127;
        description
          "ipmcolist";
      }
      enum "l2mco-list" {
        value 128;
        description
          "l2mcolist";
      }
      enum "meshmc" {
        value 129;
        description
          "meshmc";
      }
      enum "l2-bridge" {
        value 130;
        description
          "l2bridge";
      }
      enum "l2-bridge-port" {
        value 131;
        description
          "l2bridgeport";
      }
      enum "l2-bridge-vni" {
        value 132;
        description
          "l2bridgevni";
      }
      enum "l2-bridge-vnidecap" {
        value 133;
        description
          "l2bridgevnidecap";
      }
      enum "l2-bridge-mac" {
        value 134;
        description
          "l2bridgemac";
      }
      enum "l2brmac" {
        value 135;
        description
          "l2brmac";
      }
      enum "ip-tunnel-decap" {
        value 136;
        description
          "iptunneldecap";
      }
      enum "l2vlan-range" {
        value 137;
        description
          "l2vlanrange";
      }
      enum "ip-tunnel-encap" {
        value 138;
        description
          "iptunnelencap";
      }
      enum "iptnl-encap" {
        value 139;
        description
          "iptnlencap";
      }
      enum "iptnldecap" {
        value 140;
        description
          "iptnldecap";
      }
      enum "iptnlnh" {
        value 141;
        description
          "iptnlnh";
      }
      enum "rawget" {
        value 142;
        description
          "rawget";
      }
      enum "ip6mc-route" {
        value 143;
        description
          "ip6mcroute";
      }
      enum "ip6mc-comp-grp" {
        value 144;
        description
          "ip6mc comp grp";
      }
      enum "l2evpnact-remote-peer-id" {
        value 145;
        description
          "l2evpnactremotepeerid";
      }
      enum "l2evpnact-local-shl" {
        value 146;
        description
          "l2evpnactlocalshl";
      }
      enum "l2evpnact-remote-shl" {
        value 147;
        description
          "l2evpnactremoteshl";
      }
      enum "evpn-iml-range" {
        value 148;
        description
          "evpn imlrange";
      }
      enum "l2-bridge-o-list" {
        value 149;
        description
          "l2bridgeolist";
      }
      enum "l2-bridge-vnio-list" {
        value 150;
        description
          "l2bridgevniolist";
      }
      enum "l2acl" {
        value 151;
        description
          "l2acl";
      }
      enum "l2evpn-nh" {
        value 152;
        description
          "l2evpn nh";
      }
      enum "l2-bridge-port-sc" {
        value 153;
        description
          "l2bridgeport sc";
      }
      enum "l3intfmctxstats" {
        value 154;
        description
          "l3intfmctxstats";
      }
      enum "tidl-sample" {
        value 155;
        description
          "tidl sample";
      }
      enum "tidl-ref-sample" {
        value 156;
        description
          "tidl ref sample";
      }
      enum "ipacl-prefix" {
        value 157;
        description
          "ipaclprefix";
      }
      enum "ip6acl-prefix" {
        value 158;
        description
          "ip6aclprefix";
      }
      enum "ipacl-port" {
        value 159;
        description
          "ipaclport";
      }
      enum "scaleacl" {
        value 160;
        description
          "scaleacl";
      }
      enum "ipmcf-hop" {
        value 161;
        description
          "ipmcfhop";
      }
      enum "bundle-swoff" {
        value 162;
        description
          "bundle swoff";
      }
      enum "mcidswoff" {
        value 163;
        description
          "mcidswoff";
      }
      enum "dest-map" {
        value 164;
        description
          "destmap";
      }
      enum "l2-bridge-port-pw" {
        value 165;
        description
          "l2bridgeport pw";
      }
      enum "l2evpnact-local-shlstats" {
        value 166;
        description
          "l2evpnactlocalshlstats";
      }
      enum "test-hidden" {
        value 167;
        description
          "testhidden";
      }
      enum "test-local" {
        value 168;
        description
          "testlocal";
      }
      enum "test-repeated" {
        value 169;
        description
          "testrepeated";
      }
      enum "limd" {
        value 170;
        description
          "limd";
      }
      enum "litap" {
        value 171;
        description
          "litap";
      }
      enum "l3ifstats" {
        value 172;
        description
          "l3ifstats";
      }
      enum "mplsstats" {
        value 173;
        description
          "mplsstats";
      }
      enum "sr-test-ats" {
        value 174;
        description
          "srtestats";
      }
      enum "srteifstats" {
        value 175;
        description
          "srteifstats";
      }
      enum "exception-nh" {
        value 176;
        description
          "exceptionnh";
      }
      enum "srv6sid" {
        value 177;
        description
          "srv6sid";
      }
      enum "srv6nh" {
        value 178;
        description
          "srv6nh";
      }
      enum "sr6sid" {
        value 179;
        description
          "sr6sid";
      }
      enum "sr6nh" {
        value 180;
        description
          "sr6nh";
      }
      enum "redirect-vrf" {
        value 181;
        description
          "redirectvrf";
      }
      enum "test-xtf" {
        value 182;
        description
          "test xtf";
      }
      enum "ippbr" {
        value 183;
        description
          "ippbr";
      }
      enum "ippbrstats" {
        value 184;
        description
          "ippbrstats";
      }
      enum "mpls-mdt-bud" {
        value 185;
        description
          "mplsmdtbud";
      }
      enum "mpls-label-rxstats" {
        value 186;
        description
          "mplslabelrxstats";
      }
      enum "l2mac-static" {
        value 187;
        description
          "l2macstatic";
      }
      enum "dot1x" {
        value 188;
        description
          "dot1x";
      }
      enum "iprte" {
        value 189;
        description
          "iprte";
      }
      enum "ip6rte" {
        value 190;
        description
          "ip6rte";
      }
      enum "llnh" {
        value 191;
        description
          "llnh";
      }
      enum "urpfintf" {
        value 192;
        description
          "urpfintf";
      }
      enum "ipmcrxstats" {
        value 193;
        description
          "ipmcrxstats";
      }
      enum "mplsrte" {
        value 194;
        description
          "mplsrte";
      }
      enum "protectnh" {
        value 195;
        description
          "protectnh";
      }
      enum "ipllnh" {
        value 196;
        description
          "ipllnh";
      }
      enum "ip6llnh" {
        value 197;
        description
          "ip6llnh";
      }
      enum "macnh" {
        value 198;
        description
          "macnh";
      }
      enum "qos-match-stats" {
        value 199;
        description
          "qosmatchstats";
      }
      enum "ofal2xc" {
        value 200;
        description
          "ofal2xc";
      }
      enum "ofamplspwe-port" {
        value 201;
        description
          "ofamplspweport";
      }
      enum "pwenh" {
        value 202;
        description
          "pwenh";
      }
      enum "pwenh-group" {
        value 203;
        description
          "pwenhgroup";
      }
      enum "ipmcrte" {
        value 204;
        description
          "ipmcrte";
      }
      enum "ip6mcrte" {
        value 205;
        description
          "ip6mcrte";
      }
      enum "ipmcr-test-ats" {
        value 206;
        description
          "ipmcrtestats";
      }
      enum "ip6mcr-test-ats" {
        value 207;
        description
          "ip6mcrtestats";
      }
      enum "transport-nh" {
        value 208;
        description
          "transportnh";
      }
      enum "port-range" {
        value 209;
        description
          "portrange";
      }
      enum "bvi-port" {
        value 210;
        description
          "bviport";
      }
      enum "mcid" {
        value 211;
        description
          "mcid";
      }
      enum "mc-gid" {
        value 212;
        description
          "mc gid";
      }
      enum "mco-list" {
        value 213;
        description
          "mcolist";
      }
      enum "test-da" {
        value 214;
        description
          "testda";
      }
      enum "test-ca" {
        value 215;
        description
          "testca";
      }
      enum "test-ba" {
        value 216;
        description
          "testba";
      }
      enum "test-aa" {
        value 217;
        description
          "testaa";
      }
      enum "test-async-aa" {
        value 218;
        description
          "testasyncaa";
      }
      enum "test-reliable-notif" {
        value 219;
        description
          "testreliablenotif";
      }
      enum "test-de" {
        value 220;
        description
          "testde";
      }
      enum "test-ce" {
        value 221;
        description
          "testce";
      }
      enum "test-be" {
        value 222;
        description
          "testbe";
      }
      enum "test-db" {
        value 223;
        description
          "testdb";
      }
      enum "test-cb" {
        value 224;
        description
          "testcb";
      }
      enum "test-bb" {
        value 225;
        description
          "testbb";
      }
      enum "test-df" {
        value 226;
        description
          "testdf";
      }
      enum "test-cf" {
        value 227;
        description
          "testcf";
      }
      enum "test-bf" {
        value 228;
        description
          "testbf";
      }
      enum "test-af" {
        value 229;
        description
          "testaf";
      }
      enum "test-cz" {
        value 230;
        description
          "testcz";
      }
      enum "test-ax" {
        value 231;
        description
          "testax";
      }
      enum "test-ay" {
        value 232;
        description
          "testay";
      }
      enum "test-ef" {
        value 233;
        description
          "testef";
      }
      enum "test-ff" {
        value 234;
        description
          "testff";
      }
      enum "test-gf" {
        value 235;
        description
          "testgf";
      }
      enum "test-eastwestscheduling" {
        value 236;
        description
          "testeastwestscheduling";
      }
      enum "test-transnh" {
        value 237;
        description
          "testtransnh";
      }
      enum "test-eth-port" {
        value 238;
        description
          "testethport";
      }
      enum "test-eastwest" {
        value 239;
        description
          "testeastwest";
      }
      enum "test-ifstats" {
        value 240;
        description
          "testifstats";
      }
      enum "test-async-oor" {
        value 241;
        description
          "testasyncoor";
      }
      enum "test-syncmcas-too-r" {
        value 242;
        description
          "testsyncmcastoor";
      }
      enum "test-syncdeviceoor" {
        value 243;
        description
          "testsyncdeviceoor";
      }
      enum "test-az" {
        value 244;
        description
          "testaz";
      }
      enum "test-by" {
        value 245;
        description
          "testby";
      }
      enum "police-r-group" {
        value 246;
        description
          "policergroup";
      }
      enum "meter-profile" {
        value 247;
        description
          "meterprofile";
      }
      enum "acl-mirror" {
        value 248;
        description
          "acl mirror";
      }
      enum "meter-action-profile" {
        value 249;
        description
          "meteractionprofile";
      }
      enum "voqrm" {
        value 250;
        description
          "voqrm";
      }
      enum "port-wfq-profile" {
        value 251;
        description
          "portwfqprofile";
      }
      enum "rpfif" {
        value 252;
        description
          "rpfif";
      }
      enum "brmac" {
        value 253;
        description
          "brmac";
      }
      enum "br-static-mac" {
        value 254;
        description
          "brstaticmac";
      }
      enum "xconnect" {
        value 255;
        description
          "xconnect";
      }
      enum "bridge" {
        value 256;
        description
          "bridge";
      }
      enum "pwe-port" {
        value 257;
        description
          "pweport";
      }
      enum "olist" {
        value 258;
        description
          "olist";
      }
      enum "lsmprotect" {
        value 259;
        description
          "lsmprotect";
      }
      enum "monitor-session" {
        value 260;
        description
          "monitorsession";
      }
      enum "monitor-session-stats" {
        value 261;
        description
          "monitorsessionstats";
      }
      enum "mplsmcast" {
        value 262;
        description
          "mplsmcast";
      }
      enum "l2ifstats" {
        value 263;
        description
          "l2ifstats";
      }
      enum "imlnh" {
        value 264;
        description
          "imlnh";
      }
      enum "evinh" {
        value 265;
        description
          "evinh";
      }
      enum "member-list" {
        value 266;
        description
          "memberlist";
      }
      enum "test-oor" {
        value 267;
        description
          "testoor";
      }
      enum "hwre-source-s-oor" {
        value 268;
        description
          "hwresources oor";
      }
      enum "qospfcstats" {
        value 269;
        description
          "qospfcstats";
      }
      enum "pfctc" {
        value 270;
        description
          "pfctc";
      }
      enum "pfc-watchdog" {
        value 271;
        description
          "pfc watchdog";
      }
      enum "qos-shared" {
        value 272;
        description
          "qosshared";
      }
      enum "ecntxstats" {
        value 273;
        description
          "ecntxstats";
      }
      enum "tm-remote-credit" {
        value 274;
        description
          "tmremotecredit";
      }
      enum "ipmcole" {
        value 275;
        description
          "ipmcole";
      }
      enum "ip6mcole" {
        value 276;
        description
          "ip6mcole";
      }
      enum "pbr" {
        value 277;
        description
          "pbr";
      }
      enum "pbrstats" {
        value 278;
        description
          "pbrstats";
      }
      enum "punt-stormcontrol" {
        value 279;
        description
          "puntstormcontrol";
      }
      enum "ip6mcrxstats" {
        value 280;
        description
          "ip6mcrxstats";
      }
      enum "ipmctxintf" {
        value 281;
        description
          "ipmctxintf";
      }
      enum "ipmc-mdt-encap" {
        value 282;
        description
          "ipmcmdtencap";
      }
      enum "ipmc-mdt-decap" {
        value 283;
        description
          "ipmcmdtdecap";
      }
      enum "op2tap" {
        value 284;
        description
          "op2tap";
      }
      enum "mplsole" {
        value 285;
        description
          "mplsole";
      }
      enum "syncrpc" {
        value 286;
        description
          "syncrpc";
      }
      enum "tnlstats" {
        value 287;
        description
          "tnlstats";
      }
      enum "pbrsbf" {
        value 288;
        description
          "pbrsbf";
      }
      enum "statsrpc" {
        value 289;
        description
          "statsrpc";
      }
      enum "oglpts" {
        value 290;
        description
          "oglpts";
      }
      enum "oglpts-prefix" {
        value 291;
        description
          "oglptsprefix";
      }
      enum "og6lpts-prefix" {
        value 292;
        description
          "og6lptsprefix";
      }
    }
    description
      "Ofa table";
  }

  container ofa {
    config false;
    description
      "OFA Data";
    container stats {
      description
        "OFA Stats Data";
      container nodes {
        description
          "OFA data for available nodes";
        list node {
          key "node-name";
          description
            "OFA operational data for a particular node";
          container table-datas {
            description
              "OFA Resources table";
            list table-data {
              key "resource";
              description
                "OFA Resources table";
              leaf resource {
                type Ofa-table;
                description
                  "Resource type";
              }
              uses OFA-NPD-SYSDB-TABLE-RESOURCE;
            }
          }
          leaf node-name {
            type xr:Node-id;
            description
              "Node ID";
          }
        }
      }
    }
  }
}
