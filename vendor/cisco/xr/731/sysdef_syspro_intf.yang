/******************************************************************
*
* sysdef_syspro_intf.yang
*
* Copyright (c) 2020-2021 by cisco Systems, Inc.
* All rights reserved.
*******************************************************************/

module sysdef_syspro_intf {
  namespace "http://www.cisco.com/ns/yang/plat_sys_profile/sysdef_syspro_intf";
  prefix sysdef_syspro_intf;

  organization
    "Cisco Systems Inc.";

  contact
    "Cisco Systems, Inc.
    170 West Tasman Drive
    San Jose, CA  95134-1706
    US";

  description
    "syspro_intf model";

  revision "2020-05-01" {
    description "Initial revision";
  }

  grouping sysdef_syspro_intf {
    description
      "Syspro Intf EA System Profile";

    leaf default_ttl {
      type uint32;
      description "Default Maximum ttl for Interface";
    }

    leaf default_mtu {
      type uint32;
      description "Default MTU for Interface";
    }

    leaf default_hash_type {
      type uint32;
      description "Default Hash type - 0 for 7-tuple";
    }

    leaf max_subintf_vlob {
      type uint32;
      description "Max Number of subinterfaces for bundles";
    }
  }
}
