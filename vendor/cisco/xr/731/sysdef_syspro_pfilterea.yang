/******************************************************************
*
* sysdef_syspro_pfilterea.yang
*
* Copyright (c) 2020-2021 by cisco Systems, Inc.
* All rights reserved.
*******************************************************************/

module sysdef_syspro_pfilterea {
  namespace "http://www.cisco.com/ns/yang/plat_sys_profile/sysdef_syspro_pfilterea";
  prefix sysdef_syspro_pfilterea;

  organization
    "Cisco Systems Inc.";

  contact
    "Cisco Systems, Inc.
    170 West Tasman Drive
    San Jose, CA  95134-1706
    US";

  description
    "syspro_pfilterea model";

  revision "2020-05-01" {
    description "Initial revision";
  }

  grouping sysdef_syspro_pfilterea {
    description
      "Syspro Pfilter EA System Profile";

    leaf ipv4_acl_l3intf_ingress_supported {
      type uint32;
      description "is ipv4 acl on l3 intf ingress supported";
    }

    leaf ipv4_acl_l3intf_egress_supported {
      type uint32;
      description "is ipv4 acl on l3 intf egress supported";
    }

    leaf ipv4_acl_l3subintf_ingress_supported {
      type uint32;
      description "is ipv4 acl on l3 subintf ingress supported";
    }

    leaf ipv4_acl_l3subintf_egress_supported {
      type uint32;
      description "is ipv4 acl on l3 subintf egress supported";
    }

    leaf ipv4_acl_l2intf_ingress_supported {
      type uint32;
      description "is ipv4 acl on l2 intf ingress supported";
    }

    leaf ipv4_acl_l2intf_egress_supported {
      type uint32;
      description "is ipv4 acl on l2 intf egress supported";
    }

    leaf ipv4_acl_l2subintf_ingress_supported {
      type uint32;
      description "is ipv4 acl on l2 subintf ingress supported";
    }

    leaf ipv4_acl_l2subintf_egress_supported {
      type uint32;
      description "is ipv4 acl on l2 subintf egress supported";
    }

    leaf ipv4_acl_l3bundleintf_ingress_supported {
      type uint32;
      description "is ipv4 acl on l3bundle intf ingress supported";
    }

    leaf ipv4_acl_l3bundleintf_egress_supported {
      type uint32;
      description "is ipv4 acl on l3bundle intf egress supported";
    }

    leaf ipv4_acl_l3bundlesubintf_ingress_supported {
      type uint32;
      description "is ipv4 acl on l3bundle subintf ingress supported";
    }

    leaf ipv4_acl_l3bundlesubintf_egress_supported {
      type uint32;
      description "is ipv4 acl on l3bundle subintf egress supported";
    }

    leaf ipv4_acl_l2bundleintf_ingress_supported {
      type uint32;
      description "is ipv4 acl on l2bundle intf ingress supported";
    }

    leaf ipv4_acl_l2bundleintf_egress_supported {
      type uint32;
      description "is ipv4 acl on l2bundle intf egress supported";
    }

    leaf ipv4_acl_l2bundlesubintf_ingress_supported {
      type uint32;
      description "is ipv4 acl on l2bundle subintf ingress supported";
    }

    leaf ipv4_acl_l2bundlesubintf_egress_supported {
      type uint32;
      description "is ipv4 acl on l2bundle subintf egress supported";
    }

    leaf ipv6_acl_l3intf_ingress_supported {
      type uint32;
      description "is ipv6 acl on l3 intf ingress supported";
    }

    leaf ipv6_acl_l3intf_egress_supported {
      type uint32;
      description "is ipv6 acl on l3 intf egress supported";
    }

    leaf ipv6_acl_l3subintf_ingress_supported {
      type uint32;
      description "is ipv6 acl on l3 subintf ingress supported";
    }

    leaf ipv6_acl_l3subintf_egress_supported {
      type uint32;
      description "is ipv6 acl on l3 subintf egress supported";
    }

    leaf ipv6_acl_l2intf_ingress_supported {
      type uint32;
      description "is ipv6 acl on l2 intf ingress supported";
    }

    leaf ipv6_acl_l2intf_egress_supported {
      type uint32;
      description "is ipv6 acl on l2 intf egress supported";
    }

    leaf ipv6_acl_l2subintf_ingress_supported {
      type uint32;
      description "is ipv6 acl on l2 subintf ingress supported";
    }

    leaf ipv6_acl_l2subintf_egress_supported {
      type uint32;
      description "is ipv6 acl on l2 subintf egress supported";
    }

    leaf ipv6_acl_l3bundleintf_ingress_supported {
      type uint32;
      description "is ipv6 acl on l3bundle intf ingress supported";
    }

    leaf ipv6_acl_l3bundleintf_egress_supported {
      type uint32;
      description "is ipv6 acl on l3bundle intf egress supported";
    }

    leaf ipv6_acl_l3bundlesubintf_ingress_supported {
      type uint32;
      description "is ipv6 acl on l3bundle subintf ingress supported";
    }

    leaf ipv6_acl_l3bundlesubintf_egress_supported {
      type uint32;
      description "is ipv6 acl on l3bundle subintf egress supported";
    }

    leaf ipv6_acl_l2bundleintf_ingress_supported {
      type uint32;
      description "is ipv6 acl on l2bundle intf ingress supported";
    }

    leaf ipv6_acl_l2bundleintf_egress_supported {
      type uint32;
      description "is ipv6 acl on l2bundle intf egress supported";
    }

    leaf ipv6_acl_l2bundlesubintf_ingress_supported {
      type uint32;
      description "is ipv6 acl on l2bundle subintf ingress supported";
    }

    leaf ipv6_acl_l2bundlesubintf_egress_supported {
      type uint32;
      description "is ipv6 acl on l2bundle subintf egress supported";
    }

    leaf es_acl_l3intf_ingress_supported {
      type uint32;
      description "is es acl on l3 intf ingress supported";
    }

    leaf es_acl_l3intf_egress_supported {
      type uint32;
      description "is es acl on l3 intf egress supported";
    }

    leaf es_acl_l3subintf_ingress_supported {
      type uint32;
      description "is es acl on l3 subintf ingress supported";
    }

    leaf es_acl_l3subintf_egress_supported {
      type uint32;
      description "is es acl on l3 subintf egress supported";
    }

    leaf es_acl_l2intf_ingress_supported {
      type uint32;
      description "is es acl on l2 intf ingress supported";
    }

    leaf es_acl_l2intf_egress_supported {
      type uint32;
      description "is es acl on l2 intf egress supported";
    }

    leaf es_acl_l2subintf_ingress_supported {
      type uint32;
      description "is es acl on l2 subintf ingress supported";
    }

    leaf es_acl_l2subintf_egress_supported {
      type uint32;
      description "is es acl on l2 subintf egress supported";
    }

    leaf es_acl_l3bundleintf_ingress_supported {
      type uint32;
      description "is es acl on l3bundle intf ingress supported";
    }

    leaf es_acl_l3bundleintf_egress_supported {
      type uint32;
      description "is es acl on l3bundle intf egress supported";
    }

    leaf es_acl_l3bundlesubintf_ingress_supported {
      type uint32;
      description "is es acl on l3bundle subintf ingress supported";
    }

    leaf es_acl_l3bundlesubintf_egress_supported {
      type uint32;
      description "is es acl on l3bundle subintf egress supported";
    }

    leaf es_acl_l2bundleintf_ingress_supported {
      type uint32;
      description "is es acl on l2bundle intf ingress supported";
    }

    leaf es_acl_l2bundleintf_egress_supported {
      type uint32;
      description "is es acl on l2bundle intf egress supported";
    }

    leaf es_acl_l2bundlesubintf_ingress_supported {
      type uint32;
      description "is es acl on l2bundle subintf ingress supported";
    }

    leaf es_acl_l2bundlesubintf_egress_supported {
      type uint32;
      description "is es acl on l2bundle subintf egress supported";
    }

    leaf acl_bulk_install_supported {
      type uint32;
      description "is acl bulk install supported";
    }

    leaf ttl_both_supported {
      type uint32;
      description "is ingress and egress TTL supported";
    }

    leaf acl_share_both_supported {
      type uint32;
      description "shared on both ingress and egress acl supported";
    }

    leaf acl_attach_int_in_verify {
      type uint32;
      description "attach interface in verify phase";
    }

    leaf egr_stats_supported {
      type uint32;
      description "is egress stats supported";
    }

    leaf igmp_supported {
      type uint32;
      description "is igmp filter supported";
    }

    leaf egr_v6_acl_counter_supported {
      type uint32;
      description "is v6 acl egress counter supported";
    }

    leaf v6_frag_supported {
      type uint32;
      description "is v6 fragment filter supported";
    }

    leaf clear_acl_counter_on_mod {
      type uint32;
      description "clear acl counter in modification is supported";
    }

    leaf per_intf_stats {
      type uint32;
      description "per interface stats is supported";
    }

    leaf v6_tcp_flags {
      type uint32;
      description "IPV6 TCP flags is supported";
    }

    leaf log_input {
      type uint32;
      description "log input is supported";
    }
  }
}
