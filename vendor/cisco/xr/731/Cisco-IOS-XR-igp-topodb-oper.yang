module Cisco-IOS-XR-igp-topodb-oper {
  namespace "http://cisco.com/ns/yang/Cisco-IOS-XR-igp-topodb-oper";
  prefix igp-topodb-oper;

  import Cisco-IOS-XR-types {
    prefix xr;
  }
  import cisco-semver {
    prefix semver;
  }
  include Cisco-IOS-XR-igp-topodb-oper-sub1 {
    revision-date 2020-08-13;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR igp-topodb package operational data.
     
     This module contains definitions
     for the following management objects:
       topo-db: Open Topology Database library operational data
     
     Copyright (c) 2013-2020 by Cisco Systems, Inc.
     All rights reserved.";

  revision 2020-08-13 {
    description
      "Added task name ospf to restrict unlimited permission.
       2020-03-20
         Modified for Flex algo TILFA support.";
    semver:module-version "2.0.0";
  }
  revision 2020-01-02 {
    description
      "Added topodb operational data support.";
    semver:module-version "1.1.0";
  }
  revision 2019-04-05 {
    description
      "Establish semantic version baseline.";
    semver:module-version "1.0.1";
  }
  revision 2015-11-09 {
    description
      "IOS XR 6.0 revision.";
  }

  container topo-db {
    config false;
    description
      "Open Topology Database library operational data";
    container topo-db-processes {
      description
        "Table for each process using topology library";
      list topo-db-process {
        key "process-name";
        description
          "Operational data for a particular process";
        container topology-prefixes {
          description
            "Container for Topology prefix information";
          list topology-prefix {
            key "topo-vrf-name";
            description
              "Topology prefix information";
            leaf topo-vrf-name {
              type xr:Cisco-ios-xr-string;
              description
                "VRF Name";
            }
            uses OTLIB-SHOW-INSTANCE;
          }
        }
        container topology-paths {
          description
            "Container for Topology path information";
          list topology-path {
            key "topo-vrf-name";
            description
              "Topology path information";
            leaf topo-vrf-name {
              type xr:Cisco-ios-xr-string;
              description
                "VRF Name";
            }
            uses OTLIB-SHOW-PATH-INSTANCE;
          }
        }
        container topology-routes {
          description
            "Container for Topology route information";
          list topology-route {
            key "topo-vrf-name";
            description
              "Topology Route Information";
            leaf topo-vrf-name {
              type xr:Cisco-ios-xr-string;
              description
                "VRF Name";
            }
            uses OTLIB-SHOW-ROUTE-INSTANCE;
          }
        }
        container topology-summaries {
          description
            "Container for Topology summary information";
          list topology-summary {
            key "topo-vrf-name";
            description
              "Topology summary information";
            leaf topo-vrf-name {
              type xr:Cisco-ios-xr-string;
              description
                "VRF Name";
            }
            uses OTLIB-SH-INST-SUMMARY;
          }
        }
        container topologies {
          description
            "Container for Topology information";
          list topology {
            key "topo-vrf-name";
            description
              "Topology information";
            leaf topo-vrf-name {
              type xr:Cisco-ios-xr-string;
              description
                "VRF Name";
            }
            uses OTLIB-SHOW-INSTANCE;
          }
        }
        leaf process-name {
          type xr:Cisco-ios-xr-string;
          description
            "Process name";
        }
      }
    }
  }
}
