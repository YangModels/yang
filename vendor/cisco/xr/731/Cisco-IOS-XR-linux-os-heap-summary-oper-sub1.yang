submodule Cisco-IOS-XR-linux-os-heap-summary-oper-sub1 {
  belongs-to Cisco-IOS-XR-linux-os-heap-summary-oper {
    prefix Cisco-IOS-XR-linux-os-heap-summary-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR linux-os-heap-summary package operational data.
     
     Copyright (c) 2013-2019 by Cisco Systems, Inc.
     All rights reserved.";

  revision 2019-04-05 {
    description
      "Establish semantic version baseline.";
    semver:module-version "1.0.1";
  }
  revision 2015-11-09 {
    description
      "IOS XR 6.0 revision.";
  }

  grouping SHOW-MEMORY-HEAP-SUMMARY-ALL-EDM-STRING {
    description
      "SHOW MEMORY HEAP SUMMARY ALL EDM STRING";
    leaf show-output {
      type string;
      description
        "string output";
    }
  }
}
