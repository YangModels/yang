module Cisco-IOS-XR-optics-port-mode-cfg {
  namespace "http://cisco.com/ns/yang/Cisco-IOS-XR-optics-port-mode-cfg";
  prefix optics-port-mode-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR optics-port-mode package configuration.
     
     This module contains definitions
     for the following management objects:
       node: Hardware Module Portmode configuration
     
     Copyright (c) 2013-2020 by Cisco Systems, Inc.
     All rights reserved.";

  revision 2020-06-23 {
    description
      "New parameter instance added in CLI for MPA handling.
       2020-06-12
         New port modes of 1x100, 3x100 and 4x100 added.";
    semver:module-version "2.0.0";
  }
  revision 2020-05-12 {
    description
      "New port modes of 4x10-4x25, 4x10, 4x25 added.";
    semver:module-version "1.0.2";
  }
  revision 2019-04-05 {
    description
      "Establish semantic version baseline.";
    semver:module-version "1.0.1";
  }
  revision 2015-11-09 {
    description
      "IOS XR 6.0 revision.";
  }

  container node {
    description
      "Hardware Module Portmode configuration";
    container acts {
      description
        "none";
      list act {
        key "node-name";
        description
          "Nodename";
        container port-ranges {
          description
            "port mode configuration";
          list port-range {
            key "first-port sec-port";
            description
              "Hardware Module Portmode configuration";
            leaf first-port {
              type uint32;
              description
                "Specify port number";
            }
            leaf sec-port {
              type uint32;
              description
                "Specify port number";
            }
            list instance {
              key "inst-id";
              description
                "MPA number if a MPA supported card";
              container mode {
                description
                  "Mode";
                leaf speed {
                  type string;
                  description
                    "speed 40-100, 400, 2x100, 4x10-4x25, 4x10,
                     4x25, 1x100, 2x100-PAM4, 3x100, 4x100";
                }
              }
              leaf inst-id {
                type uint32 {
                  range "0..5";
                }
                description
                  "Instance number";
              }
            }
          }
        }
        leaf node-name {
          type xr:Cisco-ios-xr-string;
          description
            "NodeName";
        }
      }
    }
  }
}
