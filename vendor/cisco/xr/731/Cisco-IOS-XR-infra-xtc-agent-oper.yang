module Cisco-IOS-XR-infra-xtc-agent-oper {
  namespace "http://cisco.com/ns/yang/Cisco-IOS-XR-infra-xtc-agent-oper";
  prefix infra-xtc-agent-oper;

  import ietf-inet-types {
    prefix inet;
  }
  import Cisco-IOS-XR-types {
    prefix xr;
  }
  import cisco-semver {
    prefix semver;
  }
  include Cisco-IOS-XR-infra-xtc-agent-oper-sub3 {
    revision-date 2020-09-16;
  }
  include Cisco-IOS-XR-infra-xtc-agent-oper-sub2 {
    revision-date 2020-09-16;
  }
  include Cisco-IOS-XR-infra-xtc-agent-oper-sub1 {
    revision-date 2020-09-16;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR infra-xtc-agent package operational data.
     
     This module contains definitions
     for the following management objects:
       pcc: Path-computation client in XTC
       xtc: XTC Agent operational data
     
     Copyright (c) 2013-2020 by Cisco Systems, Inc.
     All rights reserved.";

  revision 2020-09-16 {
    description
      "Adding operational nodes for new features path invalidation drop protected and unprotected path
       2020-09-04
         Modified the Extended-Affinities and ASLA-Extended-Affinities to be list instead of a leaf-list
       2020-05-12
         Add SRv6TE policy operational data
       2020-05-05
         changes related to treat SRv6 and SID as well-known when parsing XML for yang";
    semver:module-version "4.0.0";
  }
  revision 2020-01-16 {
    description
      "Removed event buffer from SR-TE policy model. Implement new statistic info for policy performance-measurement session. Added support for per-flow policy output. Added additional filter for policy type i.e. per-flow and per-destination.";
    semver:module-version "3.0.0";
  }
  revision 2019-09-09 {
    description
      "PCE/SRTE topology should display P-flag set for OSPF prefix-SID with explicit-null";
    semver:module-version "2.0.0";
  }
  revision 2019-05-01 {
    description
      "Added operational models for interface database.";
    semver:module-version "1.0.0";
  }
  revision 2019-04-15 {
    description
      "Hierarchical changes to policy forwarding model to organize the paths under the proper segment lists and LSPs.";
  }
  revision 2019-04-05 {
    description
      "Establish semantic version baseline.";
  }
  revision 2018-11-28 {
    description
      "Various modifications to policy-related models for better compatibility with the IETF policy draft.";
  }
  revision 2017-09-11 {
    description
      "Initial version";
  }
  revision 2015-11-09 {
    description
      "IOS XR 6.0 revision.";
  }

  typedef Xtcigp-protocol {
    type enumeration {
      enum "unknown" {
        value 0;
        description
          "Unknown protocol";
      }
      enum "isis" {
        value 1;
        description
          "ISIS protocol";
      }
      enum "ospf" {
        value 2;
        description
          "OSPF protocol";
      }
      enum "bgp" {
        value 3;
        description
          "BGP protocol";
      }
      enum "te" {
        value 4;
        description
          "TE protocol";
      }
    }
    description
      "Xtcigp protocol";
  }

  typedef Xtc-label {
    type uint32 {
      range "16..1048575";
    }
    description
      "Xtc label";
  }

  typedef Xtc-registration-entry {
    type enumeration {
      enum "color" {
        value 0;
        description
          "Color";
      }
      enum "color-endpoint" {
        value 1;
        description
          "Color and Endpoint";
      }
      enum "policy-name" {
        value 2;
        description
          "Policy Name";
      }
    }
    description
      "Xtc registration entry";
  }

  typedef Xtc-address-family {
    type enumeration {
      enum "ipv4" {
        value 1;
        description
          "IPv4 address family";
      }
      enum "ipv6" {
        value 2;
        description
          "IPv6 address family";
      }
    }
    description
      "Xtc address family";
  }

  container pcc {
    config false;
    description
      "Path-computation client in XTC";
    container plsps {
      description
        "PCC PLSP database in XTC";
      list plsp {
        key "plsp-id";
        description
          "PCC PLSP information";
        leaf plsp-id {
          type uint32;
          description
            "PLSP ID";
        }
        uses PCEP-PLSP-BAG;
      }
    }
    container peers {
      description
        "PCC peer database in XTC";
      list peer {
        key "peer-addr";
        description
          "PCC peer information";
        leaf peer-addr {
          type inet:ip-address-no-zone;
          description
            "Peer Address";
        }
        uses PCEP-CONN-BAG;
      }
    }
  }
  container xtc {
    config false;
    description
      "XTC Agent operational data";
    container policies {
      description
        "Policy database in XTC Agent";
      list policy {
        key "id";
        description
          "Policy information";
        leaf id {
          type uint32;
          description
            "Policy ID";
        }
        uses XTC-POLICY-BAG;
      }
    }
    container first-segments {
      description
        "First segments of all segment-lists";
      list first-segment {
        key "label";
        description
          "first-segment of an SR-TE segment-list";
        leaf label {
          type Xtc-label;
          description
            "Label";
        }
        uses XTC-FS-BAG;
      }
    }
    container interfaces {
      description
        "Interface database in XTC Agent";
      list interface {
        key "interface-name";
        description
          "Interface information";
        leaf interface-name {
          type xr:Interface-name;
          description
            "Interface name";
        }
        uses XTC-INTERFACE-BAG;
      }
    }
    container policy-forwardings {
      description
        "Forwarding information for policies";
      list policy-forwarding {
        key "name";
        description
          "Forwarding information for the policy";
        leaf name {
          type xr:Cisco-ios-xr-string;
          description
            "Policy Name";
        }
        uses XTC-FWDING-POLICY-BAG;
      }
    }
    container policy-summary {
      description
        "Summary of all policies";
      uses XTC-POLICY-SUMMARY-BAG;
    }
    container p2mp-policy-infos {
      description
        "P2MP policy database indexed by Root address in
         XTC Agent";
      list p2mp-policy-info {
        key "root-address tree-id";
        description
          "Policy information";
        leaf root-address {
          type inet:ip-address-no-zone;
          description
            "Root Address";
        }
        leaf tree-id {
          type uint32;
          description
            "P2MP Policy Tree-ID";
        }
        uses XTC-TREESID-BAG;
      }
    }
    container trace-buffer-summaries {
      description
        "Summary of all trace buffers";
      list trace-buffer-summary {
        key "name";
        description
          "Summary of specific trace buffer";
        leaf name {
          type xr:Cisco-ios-xr-string;
          description
            "Trace buffer name";
        }
        uses CMN-TRACE-BUFFER-SUMMARY-BAG;
      }
    }
    container on-demand-colors {
      description
        "On-Demand Color database in XTC Agent";
      list on-demand-color {
        key "color";
        description
          "On Demand Color information";
        leaf color {
          type uint32;
          description
            "Color";
        }
        uses XTC-ON-DEMAND-COLOR-BAG;
      }
    }
    container srv6-prefixes {
      description
        "SRv6 Prefixes database in XTC Agent";
      list srv6-prefix {
        key "srv6-prefix prefix-length";
        description
          "Prefix information";
        leaf srv6-prefix {
          type inet:ip-address-no-zone;
          description
            "Match SRv6 prefix address";
        }
        leaf prefix-length {
          type uint32;
          description
            "Address Length";
        }
        uses XTC-SRV6-PREFIX-BAG;
      }
    }
    container controller {
      description
        "Controller information";
      container policy-requests {
        description
          "Table containing policy requests";
        list policy-request {
          key "source-address endpoint-type endpoint-address color route-distinguisher";
          description
            "Policy request information";
          leaf source-address {
            type inet:ip-address-no-zone;
            description
              "Source Address";
          }
          leaf endpoint-type {
            type Xtc-address-family;
            description
              "Endpoint Address Type";
          }
          leaf endpoint-address {
            type inet:ip-address-no-zone;
            description
              "Endpoint Address";
          }
          leaf color {
            type uint32 {
              range "1..4294967295";
            }
            description
              "Color";
          }
          leaf route-distinguisher {
            type uint32 {
              range "0..4294967295";
            }
            description
              "Route Distinguisher";
          }
          uses XTC-CONTROLLER-POLICY-REQ-BAG;
        }
      }
    }
    container p2mp-policies {
      description
        "P2MP policy database in XTC Agent";
      list p2mp-policy {
        key "name";
        description
          "Policy information";
        leaf name {
          type xr:Cisco-ios-xr-string;
          description
            "Policy name";
        }
        uses XTC-TREESID-BAG;
      }
    }
    container registrations {
      description
        "Registrations";
      list registration {
        description
          "Registration";
        leaf entry-type {
          type Xtc-registration-entry;
          description
            "Entry Type";
        }
        leaf color {
          type uint32 {
            range "1..4294967295";
          }
          description
            "Color";
        }
        leaf endpoint {
          type inet:ip-address-no-zone;
          description
            "Endpoint Address";
        }
        leaf policy-name {
          type xr:Cisco-ios-xr-string;
          description
            "Policy Name";
        }
        uses XTC-REGIST-ENTRY-BAG;
      }
    }
    container topology-nodes {
      description
        "Node database in XTC Agent";
      list topology-node {
        key "node-identifier";
        description
          "Node information";
        leaf node-identifier {
          type uint32;
          description
            "Node Identifier";
        }
        uses XTC-TOPO-NODE-BAG;
      }
    }
    container topology-summaries {
      description
        "Node summary table";
      list topology-summary {
        description
          "Node summary database";
        leaf af {
          type Xtc-address-family;
          description
            "Only show data related to the specified
             address family";
        }
        leaf protocol {
          type Xtcigp-protocol;
          description
            "Match nodes from the specified IGP protocol";
        }
        uses XTC-TOPO-SUMMARY-BAG;
      }
    }
    container prefix-infos {
      description
        "Prefixes database in XTC Agent";
      list prefix-info {
        key "node-identifier";
        description
          "Prefix information";
        leaf node-identifier {
          type uint32;
          description
            "Node ID";
        }
        uses XTC-PFX-BAG;
      }
    }
    container interface-summary {
      description
        "Summary of all interfaces";
      uses XTC-INTERFACE-SUMMARY-BAG;
    }
  }
}
