module Cisco-IOS-XR-sysadmin-controllers-iosxrwbd {
  namespace "http://www.cisco.com/ns/yang/Cisco-IOS-XR-sysadmin-controllers-iosxrwbd";
  prefix calvados_controllers;

  import Cisco-IOS-XR-sysadmin-ethsw-esdma-cli-iosxrwbd {
    prefix esdma;
  }
  import Cisco-IOS-XR-sysadmin-fabric-iosxrwbd {
    prefix fabric;
  }
  import fit {
    prefix fit;
  }
  import Cisco-IOS-XR-sysadmin-card-mgr {
    prefix card_mgr;
  }
  import cisco-semver {
    prefix semver;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains a collection of YANG
     definitions for Cisco IOS-XR SysAdmin configuration.
     
     This module defines the top level container for
     all hardware devices managed in Sysadmin.
     
     Copyright(c) 2020 by Cisco Systems, Inc.
     All rights reserved.
     
     Copyright (c) 2012-2020 by Cisco Systems, Inc.
     All rights reserved.";

  revision 2020-05-19 {
    description
      "Card Mgr event history implementation for Whitebox";
    semver:module-version "1.0.0";
  }
  revision 2020-01-10 {
    description
      "Created initial 'controller' implementation for Whitebox";
  }

  container set {
    container controller {
      uses fit:fit-grp;
    }
  }
  container controller {
    container switch {
      uses esdma:switch;
    }
    uses fabric:fabric;
    uses fabric:fabric_action_cmds;
    uses card_mgr:card_mgr-group;
  }
}
