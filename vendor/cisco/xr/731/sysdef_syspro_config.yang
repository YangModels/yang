/******************************************************************
*
* sysdef_syspro_config.yang
*
* Copyright (c) 2020-2021 by cisco Systems, Inc.
* All rights reserved.
*******************************************************************/

module sysdef_syspro_config {
  namespace "http://www.cisco.com/ns/yang/plat_sys_profile/sysdef_syspro_config";
  prefix sysdef_syspro_config;

  organization
    "Cisco Systems Inc.";

  contact
    "Cisco Systems, Inc.
    170 West Tasman Drive
    San Jose, CA  95134-1706
    US";

  description
    "syspro_config model";

  revision "2020-05-01" {
    description "Initial revision";
  }

  grouping sysdef_syspro_config {
    description
      "Syspro System config Profile";

    leaf max_num_npus {
      type uint32;
      description "Maximum number of npus";
    }

    leaf avail_npu_mask {
      type uint64;
      description "Available npu mask";
    }

    leaf all_npu_mask {
      type uint64;
      description "Mask for all NPUs";
    }

    leaf is_modular_platform {
      type uint32;
      description "Is modular/multi-LC system";
    }

    leaf port_statically_inited {
      type uint32;
      description "Is Port Statically Inited";
    }

    leaf is_vsq_supported {
      type uint32;
      description "Is VSQ supported";
    }

    leaf is_channelized_intfs_supported {
      type uint32;
      description "Is Channelized Interfaces supported";
    }

    leaf extended_lif_supported {
      type uint32;
      description "Is extended lif supported";
    }

    leaf max_npus_at_startup {
      type uint32;
      description "Maximum number of npus";
    }

    leaf report_dpa_init_to_ext_driver {
      type uint32;
      description "Report dpa init to external driver";
    }

    leaf is_asic_ard {
      type uint32;
      description "Is ASIC Type ARD";
    }

    leaf is_asic_leaba {
      type uint32;
      description "Is ASIC Type LEABA";
    }

    leaf is_asic_qax {
      type uint32;
      description "Is ASIC Type QAX";
    }

    leaf is_default_route_special_handling {
      type uint32;
      description "Special Default Route handling";
    }

    leaf is_asic_qux {
      type uint32;
      description "Is ASIC Type QUX";
    }

    leaf is_mesh_platform {
      type uint32;
      description "is_mesh_platform";
    }

    leaf max_port_per_npu {
      type uint32;
      description "Maximum Ports Per NPU";
    }

    leaf max_lcvm_per_chassis {
      type uint32;
      description "Maximum Line Card VM per Chassis";
    }

    leaf is_npu_oir_allowed {
      type uint32;
      description "NPU can have Online Insertion and Removal ";
    }

    leaf is_mask_avail {
      type uint32;
      description "Is Mask available from plat mgr";
    }

    leaf linkscan_required {
      type uint32;
      description "Whether platform requires linkscan functionality";
    }

    leaf cpu_port {
      type uint32;
      description "Return the CPU port to be used";
    }

    leaf oam_rcy_core {
      type uint32;
      description "Return the core where oam_rcy_port is present";
    }

    leaf num_cores {
      type uint32;
      description "Return the number of cores";
    }

    leaf local_slot {
      type uint32;
      description "Return the local slot to be used";
    }

    leaf vlan_domain_mask {
      type uint32;
      description "Return the mask for VTT VLAN Domain";
    }

    leaf max_fap_bw {
      type uint32;
      description "Return the max supported ILKN Bandwidth";
    }

    leaf is_slot_dual_core {
      type uint32;
      description "Check if a slot has Dual Core NPU";
    }

    leaf tm_port {
      type uint32;
      description "Return the tm_port corresponding to a pp_port";
    }

    leaf is_feature_init_reqd {
      type uint32;
      description "Return feature init required";
    }

    leaf lcvm_redundancy_on {
      type uint32;
      description "Presence of standby LC VM for platform";
    }

    leaf tpid_port_1 {
      type uint32;
      description "Initialize TPIDs";
    }

    leaf tpid_port_2 {
      type uint32;
      description "Initialize TPIDs";
    }

    leaf fabric_port_start {
      type uint32;
      description "SDK Fabric port id start";
    }

    leaf max_nif_port_id {
      type uint32;
      description "Max NIF port id";
    }

    leaf l2_and_l3_intf_support {
      type uint32;
      description "support for l2 and l3 interfaces for platform";
    }

    leaf rewrite_profile {
      type uint8;
      description "get the rewirite profile option";
    }

    leaf is_rw_supported {
      type uint32;
      description "get the rewirite profile option";
    }

    leaf itmh2_hdr_support {
      type uint32;
      description "support for itmh2 header for platform";
    }

    leaf lb_capability {
      type uint32;
      description "Load balance capability";
    }

    leaf max_dpa_table_objects {
      type uint32;
      description "Maximum number of objects allowed in a DPA Table";
    }

    leaf tpa_supported {
      type uint32;
      description "Third-party Apps Supported";
    }

    leaf single_router_supported {
      type uint32;
      description "Single Router support";
    }

    leaf pktio_supported {
      type uint32;
      description "TPA using Packet I/O Supported";
    }

    leaf max_intfs_supported {
      type uint32;
      description "Maximum number of interfaces supported";
    }

    leaf udh_hdr_support {
      type uint32;
      description "support for user defined header for platform";
    }

    leaf is_lbl_collapse_supported {
      type uint32;
      description "support for lbl_collapse";
    }

    leaf is_tenh_not_merged {
      type uint32;
      description "support for Not Merged TENH";
    }

    leaf max_num_fec {
      type uint32;
      description "Maximum number of FEC resources";
    }

    leaf max_num_ecmp_fec {
      type uint32;
      description "Maximum number of ECMP FEC resources";
    }

    leaf punt_speed_get_wa_enabled {
      type uint32;
      description "Punt port speed work-around is enabled";
    }

    leaf ftmh_stacking_hdr_enabled {
      type uint32;
      description "FTMH Stacking Header is enabled";
    }

    leaf ftmh_lb_ext_hdr_enabled {
      type uint32;
      description "FTMH Load Balancing Ext Header is enabled";
    }

    leaf ftmh_dsp_ext_hdr_enabled {
      type uint32;
      description "DSP Ext Header is enabled";
    }

    leaf two_level_lb {
      type uint32;
      description "support for 2-level load balance";
    }

    leaf three_level_lb {
      type uint32;
      description "support for three-level load balance";
    }

    leaf push_swap_path_shared {
      type uint32;
      description "share resources in imposition and label path";
    }

    leaf l2fib_num_npus {
      type uint32;
      description "l2fib number of npus";
    }

    leaf is_egr_rw_supp {
      type uint32;
      description "Is Egress rewrite supported";
    }

    leaf rcpu_supported {
      type uint32;
      description "Is RCPU feature supported";
    }

    leaf is_platform_centralized {
      type uint32;
      description "Is platform centralized";
    }

    leaf is_platform_need_mpls_lif_bank_offset {
      type uint32;
      description "Is platform needed the mpls lif bank offset";
    }

    leaf is_dpa_tm_mcast_supported {
      type uint32;
      description "Is DPA TM Multicast supported";
    }

    leaf mpls_ext_lif_supported {
      type uint32;
      description "MPLS Label in Extended out Lif is supported";
    }

    leaf is_pfc_supported {
      type uint32;
      description "Is PFC supported on this platform variant";
    }

    leaf label_stack_max {
      type uint32;
      description "Max number of labels per Egress packet";
    }

    leaf max_labels_per_encap {
      type uint32;
      description "Max number of labels per MPLS encap";
    }

    leaf max_encaps {
      type uint32;
      description "Max MPLS encap entries per packet";
    }

    leaf max_bds {
      type uint32;
      description "Max BDs supported";
    }

    leaf grid_encap_return_delay_timer {
      type uint32;
      description "grid encap return to pool delay timer";
    }

    leaf nof_remote_cores {
      type uint32;
      description "num of remote cores for NPU";
    }

    leaf stats_soc_config_init {
      type uint32;
      description "STATS config initialization in SOC file";
    }

    leaf hw_max_mac_limit {
      type uint32;
      description "HW mac limit";
    }

    leaf is_l2cp_tunneling_supported {
      type uint32;
      description "if L2 control packet tunneling is supported";
    }

    leaf l2_lif_start {
      type uint32;
      description "L2 LIF range start";
    }

    leaf l2_lif_end {
      type uint32;
      description "L2 LIF range end";
    }

    leaf num_l2_lif_bitlists {
      type uint32;
      description "Number of L2 LIF bitlists per VM";
    }

    leaf l2_lif_mask {
      type uint64;
      description "L2 LIF bitlist mask";
    }

    leaf l2_reserved_port {
      type uint32;
      description "reserved ports to do initialization";
    }

    leaf olr_enabled {
      type uint32;
      description "flag to indicate if OLR is enabled or not";
    }

    leaf max_vrids_allowed {
      type uint32;
      description "max numbers of VRIDs supported on LC";
    }

    leaf is_platform_ofa_compliant {
      type uint32;
      description "Is the platform OFA compliant?";
    }

    leaf is_platform_crt_remote_intf_chain_reqd {
      type uint32;
      description "Does it require to create interface chain on remote LC";
    }

    leaf is_dlb_supported {
      type uint32;
      description "Is Destination based Load balancing supported?";
    }

    leaf is_card_sdkless {
      type uint32;
      description "flag to indicate if a card is in sdkless state in FIA";
    }

    leaf is_port_creation_with_breakout_supported {
      type uint32;
      description "flag to indicate if BO logic to be used in port creation";
    }

    leaf is_process_exit_on_lpts_pd_err_allowed {
      type uint32;
      description "flag to indicate if process exit need to be triggered in case of lpts pre-ifib default entry PD programming errors";
    }

    leaf is_sr_range_update_supported {
      type uint32;
      description "Support of SR range update";
    }

    leaf port_mapper_max_entries {
      type uint32;
      description "Maximum number of entries in port mapper";
    }

    leaf need_egress_punt_pm_entry {
      type uint32;
      description "Need entries in port mapper for egress punts";
    }

    leaf max_supported_mtu {
      type uint32;
      description "Maximum supported MTU";
    }

    leaf is_fixed_copper_port {
      type uint32;
      description "Is fixed Copper port";
    }

    leaf is_eight_queue_hqos_supported {
      type uint32;
      description "Is 8 queue HQOS supported on this platform variant";
    }

    leaf is_mpls_te_acct_supported {
      type uint32;
      description "Is MPLS TE acct supported on this platform variant";
    }

    leaf is_srte_acct_supported {
      type uint32;
      description "Is SRTE acct supported on this platform variant";
    }

    leaf is_ll_acct_supported {
      type uint32;
      description "Is Link Layer acct supported on this platform variant";
    }

    leaf local_outlif_offset_needed {
      type uint32;
      description "local outlif offset might be needed on some asics";
    }

    leaf local_outlif_offset {
      type uint32;
      description "local outlif offset might be needed on some asics";
    }

    leaf is_vrf_scale_supported {
      type uint32;
      description "NL TCAM information on basis of dn asic";
    }
  }
}
