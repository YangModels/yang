module Cisco-IOS-XR-sysadmin-ext-alarm {
  namespace "http://www.cisco.com/ns/yang/Cisco-IOS-XR-sysadmin-ext-alarm";
  prefix ext-alarm;

  import cisco-semver {
    prefix semver;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains a collection of YANG
     definitions for Cisco IOS-XR SysAdmin configuration.
     
     This module defines the external alarms config
     functionality in the sysadmin plane.
     
     Copyright(c) 2020 by Cisco Systems, Inc.
     All rights reserved.
     
     Copyright (c) 2012-2020 by Cisco Systems, Inc.
     All rights reserved.";

  revision 2020-07-31 {
    description
      "Initial revision.";
    semver:module-version "1.0.0";
  }

  container alarm-contact-config {
    list alarm-contact {
      key "num";
      leaf num {
        type uint32 {
          range "0..3";
        }
        must "true() = (../desc)" {
          error-message
            "User cannot configure pin alone,
             Usage: <pin number> desc <> severity <>";
        }
        description
          "Alarm pin number [0-3]";
      }
      leaf desc {
        type string {
          length "1..80";
        }
        must "true() = (../severity)" {
          error-message
            "User must configure both desc and severity,
             Usage: desc <> severity <>";
        }
        config true;
        description
          "Description of the alarm";
      }
      leaf severity {
        type enumeration {
          enum "minor" {
            value 3;
          }
          enum "major" {
            value 4;
          }
          enum "critical" {
            value 5;
          }
        }
        must "true() = (../desc)" {
          error-message
            "User must configure both desc and severity,
             Usage: severity <> desc <>";
        }
        config true;
        description
          "Severity of the alarm";
      }
    }
  }
}
