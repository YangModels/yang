submodule Cisco-IOS-XR-ipv4-dhcpd-oper-sub2 {
  belongs-to Cisco-IOS-XR-ipv4-dhcpd-oper {
    prefix Cisco-IOS-XR-ipv4-dhcpd-oper;
  }

  import ietf-inet-types {
    prefix inet;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR ipv4-dhcpd package operational data.
     
     Copyright (c) 2013-2020 by Cisco Systems, Inc.
     All rights reserved.";

  revision 2020-09-30 {
    description
      "Modified to accommodate cdm changes";
    semver:module-version "1.0.1";
  }
  revision 2019-06-25 {
    description
      "Introduced an option to show dhcp rate limit hit counters.";
    semver:module-version "1.0.1";
  }
  revision 2019-04-05 {
    description
      "Establish semantic version baseline.";
  }
  revision 2018-09-20 {
    description
      "Fixing yang gaps.";
  }
  revision 2015-11-09 {
    description
      "IOS XR 6.0 revision.";
  }

  typedef Dhcpc-ipv4-state {
    type enumeration {
      enum "init" {
        value 0;
        description
          "Init state";
      }
      enum "init-reboot" {
        value 1;
        description
          "Init Reboot state";
      }
      enum "rebooting" {
        value 2;
        description
          "Rebooting state";
      }
      enum "selecting" {
        value 3;
        description
          "Selecting state";
      }
      enum "requesting" {
        value 4;
        description
          "Requesting state";
      }
      enum "bound" {
        value 5;
        description
          "Bound state";
      }
      enum "renewing" {
        value 6;
        description
          "Renewing state";
      }
      enum "rebinding" {
        value 7;
        description
          "Rebinding state";
      }
      enum "invalid" {
        value 8;
        description
          "Invalid state";
      }
    }
    description
      "Dhcp Client IPv4 State";
  }

  grouping DHCPC-EDM-CLIENT-IPV4-BAG {
    description
      "ipv4 dhcp client";
    leaf interface-name {
      type string {
        length "0..65";
      }
      description
        "Dhcp Client interface name";
    }
    leaf client-mac-address {
      type string {
        length "0..17";
      }
      description
        "Dhcp Client Interface MAC address";
    }
    leaf client-id {
      type string {
        length "0..256";
      }
      description
        "Dhcp Client ID";
    }
    leaf ipv4-client-state {
      type Dhcpc-ipv4-state;
      description
        "Dhcp Client State";
    }
    leaf ipv4-address {
      type inet:ipv4-address;
      description
        "Dhcp Client IP Address";
    }
    leaf ipv4-subnet-mask {
      type inet:ipv4-address;
      description
        "Dhcp Client IP Address mask";
    }
    leaf ipv4-server-address {
      type inet:ipv4-address;
      description
        "Dhcp Client selected server IP Address";
    }
    leaf next-hop-ipv4-address {
      type inet:ipv4-address;
      description
        "Dhcp Client next hop IP Address";
    }
    leaf ipv4-lease-time {
      type uint32;
      description
        "Dhcp Client Lease time";
    }
    leaf ipv4-renew-time {
      type uint32;
      description
        "Dhcp Client Renew time";
    }
    leaf ipv4-rebind-time {
      type uint32;
      description
        "Dhcp Client Rebind time";
    }
    leaf ipv4-address-configured {
      type boolean;
      description
        "Dhcp Client IPV4 address configured in interface";
    }
  }

  grouping DHCPC-EDM-CLIENT-IPV4-STATS-BAG {
    description
      "ipv4 dhcp client statistics";
    leaf interface-name {
      type string {
        length "0..65";
      }
      description
        "Dhcp Client interface name";
    }
    leaf num-events-received {
      type uint32;
      description
        "Number of events received";
    }
    leaf num-create-event-received {
      type uint32;
      description
        "Number of create client event received";
    }
    leaf num-delete-event-received {
      type uint32;
      description
        "Number of delete client event received";
    }
    leaf num-reboot-event-received {
      type uint32;
      description
        "Number of client rebooted event received";
    }
    leaf num-reinit-event-received {
      type uint32;
      description
        "Number of reinit client event received";
    }
    leaf num-packet-event-received {
      type uint32;
      description
        "Number of packet event received";
    }
    leaf num-init-timer-eventi {
      type uint32;
      description
        "Number of init timer event";
    }
    leaf num-t1-timer-event {
      type uint32;
      description
        "Number of T1 timer event";
    }
    leaf num-t2-timer-event {
      type uint32;
      description
        "Number of T2 timer event";
    }
    leaf num-lease-timer-event {
      type uint32;
      description
        "Number of Lease timer event";
    }
    leaf num-vbind-timer-event {
      type uint32;
      description
        "Number of vbind timer event";
    }
    leaf num-discovers-sent-successfully {
      type uint32;
      description
        "Number of discovers sent successfully";
    }
    leaf num-requests-sent-successfully {
      type uint32;
      description
        "Number of requests sent successfully";
    }
    leaf num-releases-sent-successfully {
      type uint32;
      description
        "Number of releases sent successfully";
    }
    leaf num-renews-sent-successfully {
      type uint32;
      description
        "Number of renews sent successfully";
    }
    leaf num-rebinds-sent-successfully {
      type uint32;
      description
        "Number of rebinds sent successfully";
    }
    leaf num-declines-sent-successfully {
      type uint32;
      description
        "Number of declines sent successfully";
    }
    leaf num-request-after-reboot-sent {
      type uint32;
      description
        "Number of requests sent after reboot";
    }
    leaf num-valid-offers-received {
      type uint32;
      description
        "Number of valid offers received";
    }
    leaf num-valid-acks-received {
      type uint32;
      description
        "Number of valid acks received";
    }
    leaf num-valid-nacks-received {
      type uint32;
      description
        "Number of valid nacks received";
    }
    leaf num-unicast-packet-sent-successfully {
      type uint32;
      description
        "Number of unicast packet sent successfully";
    }
    leaf num-broadcast-packet-sent-success {
      type uint32;
      description
        "Number of broadcast packet sent successfully";
    }
    leaf num-init-timer-start {
      type uint32;
      description
        "Number of init timer starts";
    }
    leaf num-init-timer-stop {
      type uint32;
      description
        "Number of init timer stops";
    }
    leaf num-t1-timer-start {
      type uint32;
      description
        "Number of T1 timer starts";
    }
    leaf num-t1-timer-stop {
      type uint32;
      description
        "Number of T1 timer stops";
    }
    leaf num-t2-timer-start {
      type uint32;
      description
        "Number of T2 timer starts";
    }
    leaf num-t2-timer-stop {
      type uint32;
      description
        "Number of T2 timer stops";
    }
    leaf num-lease-timer-start {
      type uint32;
      description
        "Number of Lease timer starts";
    }
    leaf num-lease-timer-stop {
      type uint32;
      description
        "Number of Lease timer stops";
    }
    leaf num-vbind-timer-start {
      type uint32;
      description
        "Number of vbind timer starts";
    }
    leaf num-vbind-timer-stop {
      type uint32;
      description
        "Number of vbind timer stops";
    }
    leaf num-invalid-events {
      type uint32;
      description
        "Number of invalid events received";
    }
    leaf num-discovers-failed {
      type uint32;
      description
        "Number of discover send failed";
    }
    leaf num-requests-failed {
      type uint32;
      description
        "Number of request send failed";
    }
    leaf num-releases-failed {
      type uint32;
      description
        "Number of release send failed";
    }
    leaf num-renews-failed {
      type uint32;
      description
        "Number of renew send failed";
    }
    leaf num-rebinds-failed {
      type uint32;
      description
        "Number of rebind send failed";
    }
    leaf num-declines-failed {
      type uint32;
      description
        "Number of decline send failed";
    }
    leaf num-request-after-reboot-failed {
      type uint32;
      description
        "Number of requests sent after reboot failed";
    }
    leaf num-invalid-offers {
      type uint32;
      description
        "Number of invalid offers received";
    }
    leaf num-invalid-acks {
      type uint32;
      description
        "Number of invalid acks received";
    }
    leaf num-invalid-nacks {
      type uint32;
      description
        "Number of invalid nacks received";
    }
    leaf num-invalid-packets {
      type uint32;
      description
        "Number of invalid packets dropped";
    }
    leaf num-unicast-failed {
      type uint32;
      description
        "Number of unicast packet send failed";
    }
    leaf num-broadcast-failed {
      type uint32;
      description
        "Number of broadcast packet send failed";
    }
    leaf num-xid-mismatch {
      type uint32;
      description
        "Number of XID mismatch packets received";
    }
    leaf num-vbind-failed {
      type uint32;
      description
        "Number of socket vbind failed";
    }
  }
}
