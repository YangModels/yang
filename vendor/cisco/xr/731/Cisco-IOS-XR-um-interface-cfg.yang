module Cisco-IOS-XR-um-interface-cfg {
  namespace "http://cisco.com/ns/yang/Cisco-IOS-XR-um-interface-cfg";
  prefix um-interface-cfg;

  import cisco-semver {
    prefix semver;
  }
  import Cisco-IOS-XR-types {
    prefix xr;
  }
  import tailf-common {
    prefix tailf;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR interface package configuration.
     
     This YANG module augments the
     modules with configuration data.
     
     Copyright (c) 2019 by Cisco Systems, Inc.
     All rights reserved.";

  revision 2019-06-10 {
    description
      "Establish semantic version baseline.";
    semver:module-version "1.0.1";
  }
  revision 2019-03-29 {
    description
      "Initial version";
  }

  grouping GROUP-BODY {
    container sub-interface-type {
      description
        "Specify type of sub-interface";
      container l2transport {
        presence "Indicates a l2transport node is configured.";
        description
          "l2transport sub-interface";
      }
      container point-to-point {
        presence "Indicates a point-to-point node is configured.";
        description
          "point-to-point sub-interface";
      }
      container multipoint {
        presence "Indicates a multipoint node is configured.";
        description
          "multipoint sub-interface";
      }
    }
    container ipv4 {
      description
        "Interface IPv4 config commands";
    }
    container ipv6 {
      description
        "Interface IPv6 config commands";
    }
    container dampening {
      when "../interface-name[not(starts-with(text(),'sbc'))] and ../interface-name[not(starts-with(text(),'tunnel-te'))] and ../interface-name[not(starts-with(text(),'tunnel-mte'))] and ../interface-name[not(starts-with(text(),'tunnel-gre'))] and ../interface-name[not(starts-with(text(),'tunnel-ip'))] and ../interface-name[not(starts-with(text(),'vasileft'))] and ../interface-name[not(starts-with(text(),'vasiright'))] and ../interface-name[not(starts-with(text(),'service-gre'))] and ../interface-name[not(starts-with(text(),'service-ipsec'))] and ../interface-name[not(starts-with(text(),'interflexleft'))] and ../interface-name[not(starts-with(text(),'interflexright'))] and ../interface-name[not(starts-with(text(),'cem'))]" {
        tailf:dependency "../interface-name";
      }
      presence "Indicates a dampening node is configured.";
      description
        "configure state dampening on the given interface";
      container decay-half-life {
        presence "Indicates a decay-half-life node is configured.";
        description
          "Decay half life (in minutes)";
        leaf value {
          type uint32 {
            range "1..45" {
              description
                "Decay half life (in minutes)";
            }
          }
          mandatory true;
          description
            "Decay half life (in minutes)";
        }
        container reuse-threshold {
          must "suppress-threshold";
          presence "Indicates a reuse-threshold node is configured.";
          description
            "Reuse threshold";
          leaf value {
            type uint32 {
              range "1..20000" {
                description
                  "Reuse threshold";
              }
            }
            mandatory true;
            description
              "Reuse threshold";
          }
          container suppress-threshold {
            must "max-suppress-time";
            presence "Indicates a suppress-threshold node is configured.";
            description
              "Suppress threshold";
            leaf value {
              type uint32 {
                range "1..20000" {
                  description
                    "Suppress threshold";
                }
              }
              mandatory true;
              description
                "Suppress threshold";
            }
            container max-suppress-time {
              presence "Indicates a max-suppress-time node is configured.";
              description
                "Max suppress time (in minutes)";
              leaf value {
                type uint32 {
                  range "1..255" {
                    description
                      "Max suppress time (in minutes)";
                  }
                }
                mandatory true;
                description
                  "Max suppress time (in minutes)";
              }
              container restart-penalty {
                presence "Indicates a restart-penalty node is configured.";
                description
                  "Restart penalty";
                leaf value {
                  type uint32 {
                    range "0..20000" {
                      description
                        "Restart penalty";
                    }
                  }
                  mandatory true;
                  description
                    "Restart penalty";
                }
              }
            }
          }
        }
      }
    }
    container encapsulation {
      when "../interface-name[starts-with(text(),'pos')] or ../interface-name[starts-with(text(),'serial')] or ../interface-name[starts-with(text(),'multilink')]" {
        tailf:dependency "../interface-name";
      }
      description
        "Set the encapsulation on an interface";
      container ppp {
        presence "Indicates a ppp node is configured.";
        description
          "Point-to-Point protocol";
      }
      container hdlc {
        presence "Indicates a hdlc node is configured.";
        description
          "Serial HDLC synchronous";
      }
      container mfr {
        when "../../interface-name[starts-with(text(),'serial')]" {
          tailf:dependency "../../interface-name";
        }
        presence "Indicates a mfr node is configured.";
        description
          "Multilink Frame Relay Member Link";
      }
      container frame-relay {
        when "../../interface-name[not(contains(text(),'.'))]" {
          tailf:dependency "../../interface-name";
        }
        presence "Indicates a frame-relay node is configured.";
        description
          "Frame Relay networks";
        container IETF {
          presence "Indicates a IETF node is configured.";
          description
            "Use RFC1490/RFC2427 encapsulation";
        }
      }
    }
    container shutdown {
      presence "Indicates a shutdown node is configured.";
      description
        "shutdown the given interface";
    }
    leaf mtu {
      when "../interface-name[not(starts-with(text(),'sbc'))] and ../interface-name[not(starts-with(text(),'tunnel-te'))] and ../interface-name[not(starts-with(text(),'tunnel-mte'))] and ../interface-name[not(starts-with(text(),'vasileft'))] and ../interface-name[not(starts-with(text(),'vasiright'))] and ../interface-name[not(starts-with(text(),'service-gre'))] and ../interface-name[not(starts-with(text(),'service-ipsec'))] and ../interface-name[not(starts-with(text(),'interflexleft'))] and ../interface-name[not(starts-with(text(),'interflexright'))] and ../interface-name[not(starts-with(text(),'cem'))]" {
        tailf:dependency "../interface-name";
      }
      type uint32 {
        range "64..65535" {
          description
            "MTU size in bytes";
        }
      }
      description
        "Set the MTU on an interface";
    }
    container logging {
      when "../interface-name[starts-with(text(),'loopback')] or ../interface-name[starts-with(text(),'etherbundle')] or ../interface-name[starts-with(text(),'posbundle')] or ../interface-name[starts-with(text(),'tunnel')] or ../interface-name[starts-with(text(),'service')] or ../interface-name[starts-with(text(),'vasileft')] or ../interface-name[starts-with(text(),'vasiright')] or ../interface-name[starts-with(text(),'firewallmanagement')] or ../interface-name[starts-with(text(),'sbc')] or ../interface-name[starts-with(text(),'serviceinfra')] or ../interface-name[starts-with(text(),'serviceapp')] or ../interface-name[starts-with(text(),'interflexleft')] or ../interface-name[starts-with(text(),'interflexright')] or ../interface-name[starts-with(text(),'bvi')] or ../interface-name[starts-with(text(),'pw-ether')] or ../interface-name[starts-with(text(),'pw-iw')] or ../interface-name[starts-with(text(),'Odu-Group-Mp')] or ../interface-name[starts-with(text(),'Odu-Group-Te')] or ../interface-name[starts-with(text(),'nve')] or ../interface-name[starts-with(text(),'csi')] or ../interface-name[contains(text(),'.')]" {
        tailf:dependency "../interface-name";
      }
      description
        "Per-interface logging configuration";
      container events {
        description
          "Per-interface logging events";
        container link-status {
          presence "Indicates a link-status node is configured.";
          description
            "Enable interface and line-protocol state change alarms";
        }
      }
    }
    leaf bandwidth {
      when "../interface-name[not(starts-with(text(),'sbc'))] and ../interface-name[not(starts-with(text(),'firewallmanagement'))] and ../interface-name[not(starts-with(text(),'vasileft'))] and ../interface-name[not(starts-with(text(),'vasiright'))] and ../interface-name[not(starts-with(text(),'service-gre'))] and ../interface-name[not(starts-with(text(),'service-ipsec'))] and ../interface-name[not(starts-with(text(),'interflexleft'))] and ../interface-name[not(starts-with(text(),'interflexright'))] and ../interface-name[not(starts-with(text(),'cem'))]" {
        tailf:dependency "../interface-name";
      }
      type uint32 {
        range "0..4294967295" {
          description
            "bandwidth in kbps";
        }
      }
      description
        "Set the bandwidth of an interface";
    }
    leaf description {
      type string {
        length "1..1024" {
          description
            "Description for this interface";
        }
      }
      description
        "Set description for this interface";
    }
  }

  container interfaces {
    description
      "Interface configuration";
    list interface {
      key "interface-name";
      description
        "Interface configuration subcommands";
      leaf interface-name {
        type xr:Interface-name;
        description
          "Interface configuration subcommands";
      }
      uses GROUP-BODY;
    }
    list interface-preconfigure {
      key "interface-name";
      description
        "Specify a preconfig interface";
      leaf interface-name {
        type xr:Interface-name;
        description
          "Interface configuration subcommands";
      }
      uses GROUP-BODY;
    }
  }
}
