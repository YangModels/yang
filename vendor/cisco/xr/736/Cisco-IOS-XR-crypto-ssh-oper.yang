module Cisco-IOS-XR-crypto-ssh-oper {
  namespace "http://cisco.com/ns/yang/Cisco-IOS-XR-crypto-ssh-oper";
  prefix crypto-ssh-oper;

  import Cisco-IOS-XR-types {
    prefix xr;
  }
  import cisco-semver {
    prefix semver;
  }
  include Cisco-IOS-XR-crypto-ssh-oper-sub2 {
    revision-date 2021-09-05;
  }
  include Cisco-IOS-XR-crypto-ssh-oper-sub1 {
    revision-date 2021-09-05;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR crypto-ssh package operational data.
     
     This module contains definitions
     for the following management objects:
       ssh1: Crypto Secure Shell(SSH) data
       ssh: Crypto Secure Shell(SSH) data
     
     Copyright (c) 2013-2021 by Cisco Systems, Inc.
     All rights reserved.";

  revision 2021-09-05 {
    description
      "Removing NBC changes for oper model
       2021-06-04
         Default option for authentication.
       2021-05-10
         RSA keys allowed in FIPS mode
       2021-03-16
         Max auth limit and certificate username option added for show ssh server.
       2020-11-18
         Port forwarding options in oper data.";
    semver:module-version "1.3.0";
  }
  revision 2020-03-05 {
    description
      "Modified show ssh CLI.";
    semver:module-version "1.2.0";
  }
  revision 2020-01-21 {
    description
      "Yang support to import pubkey for user in config mode";
    semver:module-version "1.1.0";
  }
  revision 2019-07-08 {
    description
      "Introducing show ssh server CLI.";
    semver:module-version "1.0.1";
  }
  revision 2019-04-05 {
    description
      "Establish semantic version baseline.";
  }
  revision 2017-08-25 {
    description
      "Introducing show ssh history CLI.";
  }
  revision 2017-05-01 {
    description
      "Fixing backward compatibility error in module.";
  }
  revision 2015-06-02 {
    description
      "IOS XR 5.3.2 revision.";
  }
  revision 2015-01-07 {
    description
      "IOS XR 5.3.1 revision.";
  }

  container ssh1 {
    config false;
    description
      "Crypto Secure Shell(SSH) data";
    container kex {
      description
        "key exchange method data";
      container nodes {
        description
          "Node-specific ssh session details";
        list node {
          key "node-name";
          description
            "SSH session details for a particular node";
          leaf node-name {
            type xr:Node-id;
            description
              "Node name";
          }
          uses SSH-SESSION-DETAIL;
        }
      }
    }
  }
  container ssh {
    config false;
    description
      "Crypto Secure Shell(SSH) data";
    container session {
      description
        "Crypto SSH session";
      container rekey {
        description
          "SSH session rekey information";
        uses SSH-SESSION-REKEY;
      }
      container history-detail {
        description
          "SSH session history detail information";
        uses SSH-SESSION-DETAIL;
      }
      container brief {
        description
          "SSH session brief information";
        uses SSH-SESSION-BRIEF;
      }
      container history {
        description
          "SSH session history information";
        uses SSH-SESSION-HISTORY;
      }
      container detail {
        description
          "SSH session detail information";
        uses SSH-SESSION-DETAIL;
      }
    }
    container server {
      description
        "SSH server parameters";
      uses SSH-SERVER-PARAMS;
    }
  }
}
