submodule Cisco-IOS-XR-infra-xtc-agent-oper-sub2 {
  belongs-to Cisco-IOS-XR-infra-xtc-agent-oper {
    prefix Cisco-IOS-XR-infra-xtc-agent-oper;
  }

  import ietf-inet-types {
    prefix inet;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR infra-xtc-agent package operational data.
     
     Copyright (c) 2013-2021 by Cisco Systems, Inc.
     All rights reserved.";

  revision 2021-08-31 {
    description
      "Added leaf segment-algorithm-set under grouping XTC-SEGMENTS-BAG.
       2021-07-27
         Added invalid reason leaf under segment-list container
       2021-06-08
         OBSOLETE the srv6-prefix command and associated bag changes.
       2021-02-18
         Remove deprecated performance-measurement oper bag and renamed pm config field name in xtc_pm_lsp_info. Added performance-measurement config data bag in lsp bag.
       2021-02-08
         Added performance-measurement config data bag in lsp bag.
       2020-12-13
         Added performance-measurement liveness-detection oper schema.";
    semver:module-version "5.0.0";
  }
  revision 2020-09-16 {
    description
      "Adding operational nodes for new features path invalidation drop protected and unprotected path
       2020-09-04
       Modified the Extended-Affinities and ASLA-Extended-Affinities to be list instead of a leaf-list
       2020-05-12
       Add SRv6TE policy operational data
       2020-05-05
       changes related to treat SRv6 and SID as well-known when parsing XML for yang";
    semver:module-version "4.0.0";
  }
  revision 2020-01-16 {
    description
      "Removed event buffer from SR-TE policy model. Implement new statistic info for policy performance-measurement session. Added support for per-flow policy output. Added additional filter for policy type i.e. per-flow and per-destination.";
    semver:module-version "3.0.0";
  }
  revision 2019-09-09 {
    description
      "PCE/SRTE topology should display P-flag set for OSPF prefix-SID with explicit-null";
    semver:module-version "2.0.0";
  }
  revision 2019-05-01 {
    description
      "Added operational models for interface database.";
    semver:module-version "1.0.0";
  }
  revision 2019-04-15 {
    description
      "Hierarchical changes to policy forwarding model to organize the paths under the proper segment lists and LSPs.";
  }
  revision 2019-04-05 {
    description
      "Establish semantic version baseline.";
  }
  revision 2018-11-28 {
    description
      "Various modifications to policy-related models for better compatibility with the IETF policy draft.";
  }
  revision 2017-09-11 {
    description
      "Initial version";
  }
  revision 2015-11-09 {
    description
      "IOS XR 6.0 revision.";
  }

  typedef Xtc-srv6-sid {
    type inet:ipv6-address;
    description
      "Xtc srv6 sid";
  }

  typedef Xtc-sid {
    type enumeration {
      enum "none" {
        value 0;
        description
          "None";
      }
      enum "mpls" {
        value 1;
        description
          "MPLS";
      }
      enum "ipv6" {
        value 2;
        description
          "IPv6";
      }
      enum "srv6" {
        value 3;
        description
          "SRv6";
      }
    }
    description
      "Xtc sid";
  }

  typedef Xtc-ipv6-address {
    type inet:ipv6-address;
    description
      "Xtc ipv6 address";
  }

  typedef Xtc-ipv4-address {
    type inet:ipv4-address;
    description
      "Xtc ipv4 address";
  }

  grouping XTC-PREFIX-SID-TYPE {
    description
      "XTC PREFIX SID TYPE";
    leaf sid-type {
      type Xtc-sid;
      description
        "SIDType";
    }
    leaf label {
      when "../sid-type = 'mpls'" {
        description
          "../SIDType = 'MPLS'";
      }
      type uint32;
      description
        "MPLS label";
    }
    leaf ipv6 {
      when "../sid-type = 'ipv6'" {
        description
          "../SIDType = 'IPv6'";
      }
      type Xtc-ipv6-address;
      description
        "IPv6 address";
    }
    leaf srv6sid {
      when "../sid-type = 'srv6'" {
        description
          "../SIDType = 'SRV6'";
      }
      type Xtc-srv6-sid;
      description
        "SRv6 SID";
    }
  }
}
