module Cisco-IOS-XR-um-event-manager-policy-map-cfg {
  namespace "http://cisco.com/ns/yang/Cisco-IOS-XR-um-event-manager-policy-map-cfg";
  prefix um-event-manager-policy-map-cfg;

  import Cisco-IOS-XR-types {
    prefix xr;
  }
  import Cisco-IOS-XR-um-event-manager-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR event-manager-policy-map package configuration.
     
     This YANG module augments the
     modules with configuration data.
     
     Copyright (c) 2021 by Cisco Systems, Inc.
     All rights reserved.";

  revision 2021-06-16 {
    description
      "Initial release";
  }

  augment "/a1:event/a1:manager" {
    container event-trigger {
      description
        "Configure event-trigger";
      list event {
        key "event-name";
        description
          "Name of the event";
        leaf event-name {
          type xr:Cisco-ios-xr-string {
            length "1..31" {
              description
                "Name of the event";
            }
          }
          description
            "Name of the event";
        }
        leaf occurrence {
          type uint32 {
            range "2..32" {
              description
                "Integer value for occurrence";
            }
          }
          description
            "No of occurrences before the event is raised";
        }
        container period {
          description
            "Time interval during which configured occurrence should take place";
          leaf seconds {
            type uint32 {
              range "1..4294967295" {
                description
                  "Integer value for time interval";
              }
            }
            description
              "Time interval in seconds";
          }
        }
        container type {
          description
            "Configure the type of event";
          container syslog {
            presence "Indicates a syslog node is configured.";
            description
              "Configure syslog event";
            leaf pattern {
              type string {
                length "1..800" {
                  description
                    "Syslog pattern or regex";
                }
              }
              mandatory true;
              description
                "Configure syslog pattern or regex";
            }
            container severity {
              description
                "Configure the syslog message severity to be screened (default: all)";
              container emergency {
                presence "Indicates a emergency node is configured.";
                description
                  "Syslog priority 0 (highest)";
              }
              container alert {
                presence "Indicates a alert node is configured.";
                description
                  "Syslog priority 1";
              }
              container critical {
                presence "Indicates a critical node is configured.";
                description
                  "Syslog priority 2";
              }
              container error {
                presence "Indicates a error node is configured.";
                description
                  "Syslog priority 3";
              }
              container warning {
                presence "Indicates a warning node is configured.";
                description
                  "Syslog priority 4";
              }
              container notice {
                presence "Indicates a notice node is configured.";
                description
                  "Syslog priority 5";
              }
              container info {
                presence "Indicates a info node is configured.";
                description
                  "Syslog priority 6";
              }
              container debug {
                presence "Indicates a debug node is configured.";
                description
                  "Syslog priority 7 (lowest)";
              }
            }
          }
        }
      }
    }
    container actions {
      description
        "Configure action";
      list action {
        key "action-name";
        description
          "Name of the action";
        leaf action-name {
          type xr:Cisco-ios-xr-string {
            length "1..31" {
              description
                "Name of the action";
            }
          }
          description
            "Name of the action";
        }
        container type {
          description
            "Type of action";
          container script {
            must "../../username and checksum/sha256";
            presence "Indicates a script node is configured.";
            description
              "Configure a Python script as action";
            leaf script-name {
              type xr:Cisco-ios-xr-string {
                length "1..800" {
                  description
                    "Python script name (must have .py extension)";
                }
              }
              mandatory true;
              description
                "Name of Python script (must have .py extension)";
            }
            container maxrun {
              description
                "Configure the max run time of script (default: 20seconds)";
              leaf seconds {
                type uint32 {
                  range "10..4294967295" {
                    description
                      "Maxrun in seconds";
                  }
                }
                description
                  "Maxrun in seconds";
              }
            }
            container checksum {
              description
                "Configure script checksum";
              leaf sha256 {
                type xr:Cisco-ios-xr-string {
                  length "64" {
                    description
                      "Checksum value";
                  }
                }
                description
                  "Configure sha256 checksum";
              }
            }
          }
        }
        leaf username {
          type xr:Cisco-ios-xr-string {
            length "1..253" {
              description
                "A configured user name";
            }
          }
          must "../type/script";
          description
            " Username under whom this policy will execute";
        }
      }
    }
    container policy-maps {
      description
        "Configure eem policy map";
      list policy-map {
        key "policy-map-name";
        description
          "Name of the policy-map";
        leaf policy-map-name {
          type xr:Cisco-ios-xr-string {
            length "1..31" {
              description
                "Name of the policy-map";
            }
          }
          description
            "Name of the policy-map";
        }
        container trigger {
          description
            "Configure trigger for this policy-map";
          leaf event {
            type xr:Cisco-ios-xr-string {
              length "1..1024" {
                description
                  "Name of event to map with this policy-map";
              }
            }
            description
              "Set an event as trigger for this policy-map";
          }
        }
        container actions {
          description
            "Map action for policy-map (Maximum 5)";
          list action {
            key "action-name";
            description
              "Name of action";
            leaf action-name {
              type xr:Cisco-ios-xr-string {
                length "1..31" {
                  description
                    "Name of action";
                }
              }
              description
                "Name of action";
            }
          }
        }
      }
    }
  }
}
