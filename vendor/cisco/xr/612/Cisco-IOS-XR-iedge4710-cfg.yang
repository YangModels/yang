module Cisco-IOS-XR-iedge4710-cfg {

  /*** NAMESPACE / PREFIX DEFINITION ***/

  namespace "http://cisco.com/ns/yang/Cisco-IOS-XR-iedge4710-cfg";


  prefix "iedge4710-cfg";

  /*** LINKAGE (IMPORTS / INCLUDES) ***/

  import Cisco-IOS-XR-types { prefix "xr"; }

  import Cisco-IOS-XR-ifmgr-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR iedge4710 package configuration.

     This module contains definitions
     for the following management objects:
       subscriber-manager: iEdge subscriber manager configuration
       iedge-license-manager: iedge license manager

     This YANG module augments the
       Cisco-IOS-XR-ifmgr-cfg
     module with configuration data.

     Copyright (c) 2013-2016 by Cisco Systems, Inc.
     All rights reserved.";

  revision "2015-11-09" {
    description
      "IOS XR 6.0 revision.";
  }


  container subscriber-manager {
    description "iEdge subscriber manager configuration";

    container accounting {
      description "iEdge accounting feature";

      container send-stop {
        description "Accounting send stop feature";
        leaf setup-failure {
          type string;
          description "Set up failure feature";
        }
      }
    }
  }

  container iedge-license-manager {
    description "iedge license manager";

    list node {
      key "node-name";
      description "Location. For eg., 0/1/CPU0";
      leaf session-limit {
        type int32;
        description "Session limit configured on linecard";
      }
      leaf session-threshold {
        type int32;
        description "Session threshold configured on linecard";
      }
      leaf node-name {
        type xr:Cisco-ios-xr-string;
        description "The node id to filter on. For eg., 0/1/CPU0";
      }
    }
  }

  augment "/a1:interface-configurations/a1:interface-configuration" {

    container service-policies {
      description
        "Interface control subscriber policy
        configuration";

      list service-policy {
        key "service-policy-name";
        description
          "Service policy to be applied to access
          interface  for subscribers";
        leaf service-policy-name {
          type string {
            length "0..63";
          }
          description "Name of policy-map";
        }
      }
    }
    description
      "This augment extends the configuration data of
      'Cisco-IOS-XR-ifmgr-cfg'";
  }
}
