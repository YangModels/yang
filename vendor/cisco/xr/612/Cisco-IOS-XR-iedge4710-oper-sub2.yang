submodule Cisco-IOS-XR-iedge4710-oper-sub2 {

  belongs-to Cisco-IOS-XR-iedge4710-oper {
    prefix Cisco-IOS-XR-iedge4710-oper;
  }

  /*** LINKAGE (IMPORTS / INCLUDES) ***/

  import ietf-inet-types { prefix "inet"; }

  import ietf-yang-types { prefix "yang"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR iedge4710 package operational data.

     Copyright (c) 2013-2016 by Cisco Systems, Inc.
     All rights reserved.";

  revision "2015-11-09" {
    description
      "IOS XR 6.0 revision.";
  }

  typedef Iedge-oper-session-af-state {
    type enumeration {
      enum not-started {
        description "Not started";
      }
      enum down {
        description "Down";
      }
      enum up-pending {
        description "Up Pending";
      }
      enum up {
        description "Up";
      }
    }
    description "Subscriber session address family state";
  }
  typedef Aaa-terminate-cause {
    type enumeration {
      enum none {
        description "None";
      }
      enum user-request {
        description "User request";
      }
      enum lost-carrier {
        description "Lost carrier";
      }
      enum lost-service {
        description "Lost service";
      }
      enum idle-timeout {
        description "Idle timeout";
      }
      enum session-timeout {
        description "Session timeout";
      }
      enum admin-reset {
        description "Admin reset";
      }
      enum admin-reboot {
        description "Admin reboot";
      }
      enum port-error {
        description "Port error";
      }
      enum nas-error {
        description "NAS error";
      }
      enum nas-request {
        description "NAS request";
      }
      enum nas-reboot {
        description "NAS reboot";
      }
      enum port-unneeded {
        description "Port unneeded";
      }
      enum port-preempted {
        description "Port preempted";
      }
      enum port-suspended {
        description "Port suspended";
      }
      enum service-unavailable {
        description "Service unavailable";
      }
      enum callback {
        description "Callback";
      }
      enum user-error {
        description "User error";
      }
      enum host-request {
        description "Host request";
      }
      enum supplicant-restart {
        description "Supplicant restart";
      }
      enum reauthorization-failure {
        description "Reauthorization failure";
      }
      enum port-reinitialized {
        description "Port reinitialized";
      }
      enum admin-disabled {
        description "Admin disabled";
      }
    }
    description "AAA terminate cause types";
  }
  typedef Aaa-interface {
    type enumeration {
      enum none {
        description "None";
      }
      enum primary-rate {
        description "Primary rate";
      }
      enum basic-rate {
        description "Basic rate";
      }
      enum serial {
        description "Serial";
      }
      enum asynchronous {
        description "Asynchronous";
      }
      enum vty {
        description "VTY";
      }
      enum atm {
        description "ATM";
      }
      enum ethernet {
        description "Ethernet";
      }
      enum ppp-over-atm {
        description "PPP over ATM";
      }
      enum pppoe-over-atm {
        description "PPPoE over ATM";
      }
      enum pppoe-over-ethernet {
        description "PPPoE over ethernet";
      }
      enum ppp-over-vlan {
        description "PPP over VLAN";
      }
      enum ppp-over-qinq {
        description "PPP over Q in Q";
      }
      enum v120 {
        description "V120";
      }
      enum v110 {
        description "V110";
      }
      enum piafs {
        description "PHS internet access forum standard";
      }
      enum x75 {
        description "X75";
      }
      enum ip-sec {
        description "IP sec";
      }
      enum other {
        description "Other";
      }
      enum virtual-pppoe-over-ethernet {
        description "Virtual PPPoE over ethernet";
      }
      enum virtual-pppoe-over-vlan {
        description "Virtual PPPoE over VLAN";
      }
      enum virtual-pppoe-over-qinq {
        description "Virtual PPPoE over Q in Q";
      }
      enum ipo-e-over-ethernet {
        description "IPoE over ethernet";
      }
      enum ipo-e-over-vlan {
        description "IPoE over VLAN";
      }
      enum ipo-e-over-qinq {
        description "IPoE over Q in Q";
      }
      enum virtual-i-po-e-over-ethernet {
        description "Virtual IPoE over ethernet";
      }
      enum virtual-i-po-e-over-vlan {
        description "Virtual IPoE over VLAN";
      }
      enum virtual-i-po-e-over-qinq {
        description "Virtual IPoE over Q in Q";
      }
    }
    description "AAA interface types";
  }
  typedef Aaa-tunnel-proto {
    type enumeration {
      enum none {
        description "None";
      }
      enum pptp {
        description "Point-to-point tunneling protocol";
      }
      enum l2f {
        description "Layer 2 forwarding";
      }
      enum l2tp {
        description "Layer 2 tunneling protocol";
      }
      enum atmp {
        description "Ascend tunnel management protocol";
      }
      enum vtp {
        description "VLAN trunk protocol";
      }
      enum ah {
        description "Authentication header";
      }
      enum ip-over-ip {
        description "IP over IP";
      }
      enum minimum-ip-over-ip {
        description "Minimum IP over IP";
      }
      enum esp {
        description "Encapsulating security payload";
      }
      enum gre {
        description "Generic routing encapsulation";
      }
      enum bay-dvs {
        description "Bay dial virtual services";
      }
      enum ip-in-ip {
        description "IP in IP";
      }
      enum vlan {
        description "VLAN";
      }
    }
    description "Tunnel protocol types";
  }
  typedef Aaa-tunnel-medium {
    type enumeration {
      enum none {
        description "None";
      }
      enum ipv4 {
        description "IPv4";
      }
      enum ipv6 {
        description "IPv6";
      }
      enum nsap {
        description "NSAP";
      }
      enum hdlc {
        description "HDLC";
      }
      enum bbn {
        description "BBN";
      }
      enum all802 {
        description "ALL 802";
      }
    }
    description "Tunnel medium types";
  }
  typedef Aaa-auth-service {
    type enumeration {
      enum none {
        description "None";
      }
      enum login {
        description "Login";
      }
      enum framed {
        description "Framed";
      }
      enum callback-login {
        description "Callback login";
      }
      enum callback-framed {
        description "Callback framed";
      }
      enum outbound {
        description "Outbound";
      }
      enum administrator {
        description "Administrator";
      }
      enum prompt {
        description "Prompt";
      }
      enum authentication-only {
        description "Authentication only";
      }
      enum callback-nas-prompt {
        description "Callback NAS prompt";
      }
      enum call-check {
        description "Call check";
      }
      enum callback-administrator {
        description "Callback administrator";
      }
      enum voice {
        description "Voice";
      }
      enum fax {
        description "Fax";
      }
      enum modem-relay {
        description "Modem relay";
      }
      enum eap-over-udp {
        description "EAP over UDP";
      }
    }
    description "AAA authorization service types";
  }
  typedef Iedge-oper-session-state {
    type enumeration {
      enum initialize {
        description "Initialize";
      }
      enum connecting {
        description "Connecting";
      }
      enum connected {
        description "Connected";
      }
      enum activated {
        description "Activated";
      }
      enum idle {
        description "Idle";
      }
      enum disconnecting {
        description "Disconnecting";
      }
      enum end {
        description "End";
      }
    }
    description "Subscriber session states";
  }
  typedef Mac-address {
    type yang:mac-address;
    description "MAC address type";
  }
  typedef Hex-binary {
    type yang:hex-string;
    description "Hex binary data";
  }
  typedef Ipv4-address {
    type inet:ipv4-address;
    description "IP address type";
  }
  typedef Iedge-ppp-sub {
    type enumeration {
      enum pta {
        description "PPP termination and aggregation";
      }
      enum lac {
        description "L2TP access controller";
      }
    }
    description "PPPoE sub types";
  }
  typedef Iedge-oper-session {
    type enumeration {
      enum unknown {
        description "Unknown";
      }
      enum pppoe {
        description "PPPoE/PPP client";
      }
      enum ppp {
        description "PPP serial client";
      }
      enum ip-packet-trigger {
        description "IP subscriber - packet trigger";
      }
      enum ip-packet-dhcp-trigger {
        description "IP subscriber - DHCP trigger";
      }
    }
    description "Subscriber session types";
  }

  grouping IEDGE-MOBILITY-SESSION-DATA {
    description "Mobility attributes";
    leaf mpc-protocol {
      type boolean;
      description "Cisco MPC Protocol";
    }
    leaf mobility-ipv4-address {
      type string;
      description "IPv4 address of Mobility Node";
    }
    leaf mobility-default-ipv4-gateway {
      type string;
      description "Default Gateway IPv4 Address";
    }
    leaf mobility-dns-server {
      type string;
      description "DNS Server Primary";
    }
    leaf mobility-dhcp-server {
      type string;
      description "DHCP Server";
    }
    leaf mobility-ipv4-netmask {
      type string;
      description "IPv4 Netmask";
    }
    leaf domain-name {
      type string;
      description "Domain Name";
    }
    leaf uplink-gre-key {
      type string;
      description "Uplink GRE Key";
    }
    leaf downlink-gre-key {
      type string;
      description "Downlink GRE Key";
    }
    leaf lease-time {
      type string;
      units "second";
      description "Duration of lease in seconds";
    }
  }

  grouping IEDGE-AAA-ATTR {
    description "AAA attributes";
    leaf ipv4mtu {
      type uint32;
      description "IPv4 maximum transmission unit";
    }
    leaf ipv4-unnumbered {
      type string;
      description "IPv4 unnumbered";
    }
    leaf authorization-service-type {
      type Aaa-auth-service;
      description "Authorization service type";
    }
    leaf tunnel-client-endpoint {
      type Ipv4-address;
      description "Tunnel client endpoint";
    }
    leaf tunnel-server-endpoint {
      type Ipv4-address;
      description "Tunnel server endpoint";
    }
    leaf tunnel-tos-setting {
      type uint32;
      description "Tunnel TOS setting";
    }
    leaf tunnel-medium {
      type Aaa-tunnel-medium;
      description "Tunnel medium";
    }
    leaf tunnel-preference {
      type uint32;
      description "Tunnel preference";
    }
    leaf tunnel-client-authentication-id {
      type string;
      description "Tunnel client authentication ID";
    }
    leaf tunnel-protocol {
      type Aaa-tunnel-proto;
      description "Tunnel protocol";
    }
    leaf actual-data-rate-upstream {
      type uint32;
      units "Mbit/s";
      description "Actual data rate upstream (in Mbps)";
    }
    leaf actual-data-rate-downstream {
      type uint32;
      units "Mbit/s";
      description "Actual data rate downstream (in Mbps)";
    }
    leaf attainable-data-rate-upstream {
      type uint32;
      units "Mbit/s";
      description "Attainable data rate upstream (in Mbps)";
    }
    leaf attainable-data-rate-downstream {
      type uint32;
      units "Mbit/s";
      description "Attainable data rate downstream (in Mbps)";
    }
    leaf pool-address {
      type string;
      description "IP address pool";
    }
    leaf circuit-id {
      type string;
      description "Circuit ID";
    }
    leaf connection-receive-speed {
      type uint32;
      description "Connection receive speed";
    }
    leaf connection-transmission-speed {
      type uint32;
      description "Connection transmission speed";
    }
    leaf destination-station-id {
      type string;
      description "Destination station ID";
    }
    leaf primary-dns-server-address {
      type Ipv4-address;
      description "Primary DNS server address";
    }
    leaf secondary-dns-server-address {
      type Ipv4-address;
      description "Secondary DNS server address";
    }
    leaf formatted-calling-station-id {
      type string;
      description "Formatted calling station id";
    }
    leaf interface-name {
      type string;
      description "Interface name";
    }
    leaf interface-type {
      type Aaa-interface;
      description "Interface type";
    }
    leaf interim-accounting-interval {
      type uint32;
      description "Interim accounting interval";
    }
    leaf ingress-access-list {
      type string;
      description "Ingress access list";
    }
    leaf egress-access-list {
      type string;
      description "Egress access list";
    }
    leaf ip-netmask {
      type Ipv4-address;
      description "IP netmask for the user";
    }
    leaf is-interworking-functionality {
      type boolean;
      description "True, if interworking functionality";
    }
    leaf max-interleaving-delay-downstream {
      type uint32;
      units "Mbit/s";
      description "Maximum interleaving delay downstream (in Mbps)";
    }
    leaf max-interleaving-delay-upstream {
      type uint32;
      units "Mbit/s";
      description "Maximum interleaving delay upstream (in Mbps)";
    }
    leaf max-data-rate-upstream {
      type uint32;
      units "Mbit/s";
      description "Maximum data rate upstream (in Mbps)";
    }
    leaf max-data-rate-downstream {
      type uint32;
      units "Mbit/s";
      description "Maximum data rate downstream (in Mbps)";
    }
    leaf min-data-rate-downstream {
      type uint32;
      units "Mbit/s";
      description "Minimum data rate downstream (in Mbps)";
    }
    leaf min-data-rate-downstream-low-power {
      type uint32;
      units "Mbit/s";
      description
        "Minimum data rate downstream low power (in Mbps)";
    }
    leaf min-data-rate-upstream-low-power {
      type uint32;
      units "Mbit/s";
      description "Minimum data rate upstream low power (in Mbps)";
    }
    leaf primary-net-bios-server-address {
      type Ipv4-address;
      description "Primary net bios server address";
    }
    leaf secondary-net-bios-server-address {
      type Ipv4-address;
      description "Secondary net bios server address";
    }
    leaf parent-interface-name {
      type xr:Interface-name;
      description "Parent interface name";
    }
    leaf remote-id {
      type string;
      description "Remote ID";
    }
    leaf route {
      type string;
      description "Route information for a user session";
    }
    leaf session-timeout {
      type uint32;
      units "second";
      description "Session timeout (in seconds)";
    }
    leaf strict-rpf-packets {
      type uint32;
      description "Strict RPF packets";
    }
    leaf accounting-session-id {
      type string;
      description "Accounting session ID";
    }
    leaf upstream-parameterized-qos-policy {
      type string;
      description
        "Upstream parameterized QoS policy to be applied
        on the subscriber side";
    }
    leaf downstream-parameterized-qos-policy {
      type string;
      description
        "Downstream parameterized QoS policy to be
        applied on the subscriber side";
    }
    leaf upstream-qos-policy {
      type string;
      description
        "Upstream QoS policy to be applied on the
        subscriber side";
    }
    leaf downstream-qos-policy {
      type string;
      description
        "Downstream QoS policy to be applied on the
        subscriber side";
    }
    leaf session-termination-cause {
      type Aaa-terminate-cause;
      description "Session termination cause";
    }
  }

  grouping IEDGE-OPER-COA-DATA {
    description "IEDGE OPER COA DATA";
    leaf request-acked {
      type boolean;
      description "Coa Request Acked";
    }
    leaf request-time {
      type string;
      description
        "Request time in DDD MMM DD HH:MM:SS YYYY format
        eg: Tue Apr 11 21:30:47 2011";
    }
    leaf coa-request-attributes {
      type yang:hex-string;
      description
        "List of Request Attributes collected in COA
        response";
    }
    leaf reply-time {
      type string;
      description
        "Reply time in DDD MMM DD HH:MM:SS YYYY format eg
        : Tue Apr 11 21:30:47 2011";
    }
    leaf coa-reply-attributes {
      type yang:hex-string;
      description
        "List of Reply Attributes collected in COA
        response";
    }
  }

  grouping IEDGE-OPER-ACCOUNTING-DATA {
    description "Session/Service accounting information";
    leaf accounting-state-rc {
      type uint32;
      description
        "Accounting State Error Code for Accounting
        Session";
    }
    leaf accounting-stop-state {
      type uint32;
      description "Accounting Stop State";
    }
    leaf record-context-name {
      type string;
      description "Accounting record context name";
    }
    leaf method-list-name {
      type string;
      description "AAA method list name used to perform accounting";
    }
    leaf account-session-id {
      type string;
      description "Accounting session ID";
    }
    leaf accounting-start-time {
      type string;
      description
        "Accounting start time in DDD MMM DD HH:MM:SS
        YYYY format eg: Tue Feb 15 15:12:49 2011";
    }
    leaf is-interim-accounting-enabled {
      type boolean;
      description "True if interim accounting is enabled";
    }
    leaf interim-interval {
      type uint32;
      units "minute";
      description "Interim accounting interval (in minutes)";
    }
    leaf last-successful-interim-update-time {
      type string;
      description
        "Time of last successful interim update in DDD
        MMM DD HH:MM:SS YYYY format eg: Tue Apr 11 21:30
        :47 2011";
    }
    leaf next-interim-update-attempt-time {
      type uint32;
      units "second";
      description
        "Time of next interim update attempt (in seconds)";
    }
    leaf last-interim-update-attempt-time {
      type string;
      description
        "Time of last interim update attempt in DDD MMM
        DD HH:MM:SS YYYY format eg: Tue Apr 11 21:30:47
        2011";
    }
    leaf sent-interim-updates {
      type uint32;
      description "Number of interim updates sent";
    }
    leaf accepted-interim-updates {
      type uint32;
      description "Number of interim updates accepted";
    }
    leaf rejected-interim-updates {
      type uint32;
      description "Number of interim updates rejected";
    }
    leaf sent-interim-update-failures {
      type uint32;
      description "Number of interim update send failures";
    }
  }

  grouping IEDGE-ACCNT-DATA {
    description "Accounting information";

    list accounting-session {
      description "Accounting information";
      uses IEDGE-OPER-ACCOUNTING-DATA;
    }
  }

  grouping SUBSCRIBER-SESSION-DATA {
    description "Subscriber session information";

    container accounting {
      description "Accounting information";
      uses IEDGE-ACCNT-DATA;
    }

    container user-profile-attributes {
      description
        "List of user profile attributes collected for
        subscriber session";
      uses IEDGE-AAA-ATTR;
    }

    container mobility-attributes {
      description
        "List of mobility attributes collected for
        subscriber session";
      uses IEDGE-MOBILITY-SESSION-DATA;
    }
    leaf session-type {
      type Iedge-oper-session;
      description "Subscriber session type";
    }
    leaf pppoe-sub-type {
      type Iedge-ppp-sub;
      description "PPPoE sub type";
    }
    leaf interface-name {
      type xr:Interface-name;
      description "Interface name";
    }
    leaf vrf-name {
      type string;
      description "VRF name";
    }
    leaf circuit-id {
      type string;
      description "Circuit ID";
    }
    leaf remote-id {
      type string;
      description "Remote ID";
    }
    leaf lns-address {
      type Ipv4-address;
      description "PPPoE LNS address";
    }
    leaf lac-address {
      type Ipv4-address;
      description "PPPoE LAC address";
    }
    leaf tunnel-client-authentication-id {
      type string;
      description "PPPoE LAC tunnel client authentication ID";
    }
    leaf tunnel-server-authentication-id {
      type string;
      description "PPPoE LAC tunnel server authentication ID";
    }
    leaf session-ip-address {
      type Ipv4-address;
      description "Session ip address";
    }
    leaf session-ipv6-address {
      type string;
      description "Session IPv6 address";
    }
    leaf session-ipv6-prefix {
      type string;
      description "Session IPv6 prefix";
    }
    leaf delegated-ipv6-prefix {
      type string;
      description "Session delegated IPv6 prefix";
    }
    leaf ipv6-interface-id {
      type Hex-binary;
      description "IPv6 Interface ID";
    }
    leaf mac-address {
      type Mac-address;
      description "MAC address";
    }
    leaf account-session-id {
      type string;
      description "Accounting session ID";
    }
    leaf nas-port {
      type string;
      description "NAS port";
    }
    leaf username {
      type string;
      description "Username";
    }
    leaf clientname {
      type string;
      description "Client Username";
    }
    leaf formattedname {
      type string;
      description "Formatted Username";
    }
    leaf is-session-authentic {
      type boolean;
      description "If true, session is authentic";
    }
    leaf is-session-author {
      type boolean;
      description "If true, session is authorized";
    }
    leaf session-state {
      type Iedge-oper-session-state;
      description "Session state";
    }
    leaf session-creation-time {
      type string;
      description
        "Session creation time in DDD MMM DD HH:MM:SS
        YYYY format eg: Tue Apr 11 21:30:47 2011";
    }
    leaf idle-state-change-time {
      type string;
      description
        "Time when idle state change occurred in DDD MMM
        DD HH:MM:SS YYYY format eg: Tue Apr 11 21:30:47
        2011";
    }
    leaf total-session-idle-time {
      type uint32;
      units "second";
      description "Total session idle time (in seconds)";
    }
    leaf access-interface-name {
      type xr:Interface-name;
      description
        "Access interface name associated with the
        session";
    }
    leaf pending-callbacks {
      type uint64;
      description "Active pending callbacks bitmask";
    }
    leaf af-up-status {
      type uint32;
      description "AF status per Subscriber Session";
    }
    leaf session-ipv4-state {
      type Iedge-oper-session-af-state;
      description "Session IPv4 state";
    }
    leaf session-ipv6-state {
      type Iedge-oper-session-af-state;
      description "Session IPv6 state";
    }

    list session-change-of-authorization {
      description "Subscriber change of authorization information";
      uses IEDGE-OPER-COA-DATA;
    }
  }

  grouping SUBSCRIBER-SESSION-AF-COUNTS {
    description "Subscriber address family session counts";
    leaf in-progress-sessions {
      type uint32;
      description "Sessions with undecided address family";
    }
    leaf ipv4-only-sessions {
      type uint32;
      description "IPv4 only sessions ";
    }
    leaf ipv6-only-sessions {
      type uint32;
      description "IPv6 only sessions ";
    }
    leaf dual-part-up-sessions {
      type uint32;
      description "Dual stack partially up sessions";
    }
    leaf dual-up-sessions {
      type uint32;
      description "Dual stack up sessions";
    }
    leaf lac-sessions {
      type uint32;
      description "LAC sessions";
    }
  }

  grouping SUBSCRIBER-SESSION-AF-SUMMARY {
    description
      "Subscriber session address family summary
      information";

    container pppoe {
      description "PPPoE summary";
      uses SUBSCRIBER-SESSION-AF-COUNTS;
    }

    container ip-subscriber-dhcp {
      description "IP subscriber DHCP summary";
      uses SUBSCRIBER-SESSION-AF-COUNTS;
    }

    container ip-subscriber-packet {
      description "IP subscriber packet summary";
      uses SUBSCRIBER-SESSION-AF-COUNTS;
    }
  }

  grouping SUBSCRIBER-SESSION-STATE-COUNTS {
    description "Subscriber state session counts";
    leaf initialized-sessions {
      type uint32;
      description "Sessions in initialized state";
    }
    leaf connecting-sessions {
      type uint32;
      description "Sessions in connecting state";
    }
    leaf connected-sessions {
      type uint32;
      description "Sessions in connected state";
    }
    leaf activated-sessions {
      type uint32;
      description "Sessions in activated state";
    }
    leaf idle-sessions {
      type uint32;
      description "Sessions in idle state";
    }
    leaf disconnecting-sessions {
      type uint32;
      description "Sessions in disconnecting state";
    }
    leaf end-sessions {
      type uint32;
      description "Sessions in end state";
    }
  }

  grouping SUBSCRIBER-SESSION-STATE-SUMMARY {
    description "Subscriber session state summary information";

    container pppoe {
      description "PPPoE summary";
      uses SUBSCRIBER-SESSION-STATE-COUNTS;
    }

    container ip-subscriber-dhcp {
      description "IP subscriber DHCP summary";
      uses SUBSCRIBER-SESSION-STATE-COUNTS;
    }

    container ip-subscriber-packet {
      description "IP subscriber packet summary";
      uses SUBSCRIBER-SESSION-STATE-COUNTS;
    }
  }

  grouping SUBSCRIBER-SESSION-SUMMARY {
    description "Subscriber session summary information";

    container state-xr {
      description "State summary";
      uses SUBSCRIBER-SESSION-STATE-SUMMARY;
    }

    container address-family-xr {
      description "Address family summary";
      uses SUBSCRIBER-SESSION-AF-SUMMARY;
    }
  }
}
