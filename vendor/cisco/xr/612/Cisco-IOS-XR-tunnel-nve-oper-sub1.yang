submodule Cisco-IOS-XR-tunnel-nve-oper-sub1 {

  belongs-to Cisco-IOS-XR-tunnel-nve-oper {
    prefix Cisco-IOS-XR-tunnel-nve-oper;
  }

  /*** LINKAGE (IMPORTS / INCLUDES) ***/

  import ietf-inet-types { prefix "inet"; }

  import ietf-yang-types { prefix "yang"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR tunnel-nve package operational data.

     Copyright (c) 2013-2016 by Cisco Systems, Inc.
     All rights reserved.";

  revision "2015-11-09" {
    description
      "IOS XR 6.0 revision.";
  }


  grouping NVE-SHOW-NVE-INTF-BD {
    description "NVE Interface Information";
    leaf interface-name-xr {
      type string;
      description "Interface name";
    }
    leaf state {
      type int8;
      description "State";
    }
    leaf admin-state {
      type int8;
      description "Admin State";
    }
    leaf flags {
      type uint32;
      description "Flags";
    }
    leaf encap {
      type int8;
      description "Encap";
    }
    leaf source-interface-name {
      type string;
      description "Source Interface name";
    }
    leaf source-ipv4-address {
      type inet:ipv4-address;
      description "Source IPv4 Address";
    }
    leaf if-handle {
      type uint64;
      description "NVE IfHandle";
    }
    leaf source-state {
      type int8;
      description "Source Intf State";
    }
    leaf udp-port {
      type uint32;
      description "UDP Port";
    }
    leaf any-cast-source-interface-name {
      type string;
      description "Anycast Source Interface name";
    }
    leaf any-cast-source-ipv4-address {
      type inet:ipv4-address;
      description "Anycast Source IPv4 Address";
    }
    leaf any-cast-source-state {
      type int8;
      description "Anycast Source Interface State";
    }
    leaf sync-mcast-ipv4-address {
      type inet:ipv4-address;
      description "MCAST sync group IPv4 Address";
    }
    leaf sync-mcast-flags {
      type uint32;
      description "Sync McastFlags";
    }
  }

  grouping NVE-SHOW-VNI-BD {
    description "VNI Information";
    leaf interface-name {
      type string;
      description "NVE Interface name";
    }
    leaf vni-xr {
      type uint32;
      description "VNI Number";
    }
    leaf state {
      type int8;
      description "State";
    }
    leaf mcast-ipv4-address {
      type inet:ipv4-address;
      description "MCAST IPv4 Address";
    }
    leaf flags {
      type uint32;
      description "Flags";
    }
    leaf vni-min {
      type uint32;
      description "VNI Min in Range";
    }
    leaf vni-max {
      type uint32;
      description "VNI Max in Range";
    }
    leaf mcast-flags {
      type uint32;
      description "McastFlags";
    }
    leaf udp-port {
      type uint32;
      description "UDP Port";
    }
    leaf bvi-ifh {
      type uint32;
      description "BVI Interface Handle";
    }
    leaf bvi-state {
      type uint8;
      description "BVI Interface Oper State";
    }
    leaf bvi-mac {
      type yang:hex-string;
      description "BVI MAC address";
    }
    leaf vrf-name {
      type string;
      description "L3 VRF Name";
    }
    leaf vrf-id {
      type uint32;
      description "L3 VRF ID";
    }
    leaf ipv4-tbl-id {
      type uint32;
      description "IPv4 Table ID";
    }
    leaf ipv6-tbl-id {
      type uint32;
      description "IPv6 Table ID";
    }
    leaf vrf-vni {
      type uint32;
      description "VRF VNI";
    }
    leaf topo-valid {
      type boolean;
      description "TOPO ID valid flag";
    }
    leaf topo-id {
      type uint32;
      description "L2RIB Topology ID";
    }
    leaf topo-name {
      type string {
        length "0..50";
      }
      description "L2RIB Topology Name";
    }
  }
}
