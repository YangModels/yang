module Cisco-IOS-XR-sdr-invmgr-oper {

  /*** NAMESPACE / PREFIX DEFINITION ***/

  namespace "http://cisco.com/ns/yang/Cisco-IOS-XR-sdr-invmgr-oper";


  prefix "sdr-invmgr-oper";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR sdr-invmgr package operational data.

     This module contains definitions
     for the following management objects:
       sdr-inventory: SDR information

     Copyright (c) 2013-2016 by Cisco Systems, Inc.
     All rights reserved.";

  revision "2015-11-09" {
    description
      "IOS XR 6.0 revision.";
  }


  container sdr-inventory {
    config false;
    description "SDR information";

    container racks {
      description "RackTable";

      list rack {
        key "name";
        description "Rack name";
        leaf name {
          type xr:Cisco-ios-xr-string;
          description "Rack name";
        }

        list slot {
          key "name";
          description "Slot name";
          leaf name {
            type xr:Cisco-ios-xr-string;
            description "Slot name";
          }

          list card {
            key "name";
            description "Card";

            container attributes {
              description "Attributes";
              leaf power {
                type int32;
                default "0";
                description "Power";
              }
              leaf config-state {
                type int32;
                default "0";
                description "ConfigState";
              }
              leaf card-state {
                type int32;
                default "0";
                description "CardState";
              }
              leaf vm-state {
                type int32;
                default "0";
                description "VM State information";
              }
              leaf card-admin-state {
                type int32;
                default "0";
                description "Card Admin State";
              }
              leaf card-type {
                type int32;
                default "0";
                description "CardType";
              }
              leaf pi-slot-number {
                type int32;
                default "0";
                description "Pi Slot Number";
              }
              leaf shutdown {
                type int32;
                default "0";
                description "Shutdown";
              }
              leaf ctype {
                type int32;
                default "0";
                description "CType";
              }
              leaf monitor {
                type int32;
                default "0";
                description "Monitor";
              }
            }
            leaf name {
              type xr:Cisco-ios-xr-string;
              description "Card";
            }
          }
        }
      }
    }
  }
}
