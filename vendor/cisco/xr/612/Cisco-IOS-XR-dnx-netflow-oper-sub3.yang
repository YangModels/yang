submodule Cisco-IOS-XR-dnx-netflow-oper-sub3 {

  belongs-to Cisco-IOS-XR-dnx-netflow-oper {
    prefix Cisco-IOS-XR-dnx-netflow-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR dnx-netflow package operational data.

     Copyright (c) 2013-2016 by Cisco Systems, Inc.
     All rights reserved.";

  revision "2015-11-09" {
    description
      "IOS XR 6.0 revision.";
  }

  typedef Nfmgr-fem-edm-exp-ver {
    type enumeration {
      enum v9 {
        description "Version 9 export format";
      }
      enum ip-fix {
        description "IPFIX export format";
      }
    }
    description "Netflow export version";
  }
  typedef Nfmgr-fem-edm-trans-proto {
    type enumeration {
      enum unspecified {
        description "Unspecified transport protocol";
      }
      enum udp {
        description "UDP transport protocol";
      }
    }
    description "Netflow export transport protocol";
  }

  grouping NFMGR-IPFIX-EXP-INFO {
    description "Netflow IPFIX export info";
    leaf sampler-table-export-timeout {
      type uint32;
      units "second";
      description "Sampler table export timeout in seconds";
    }
    leaf interface-table-export-timeout {
      type uint32;
      units "second";
      description "Interface table export timeout in seconds";
    }
    leaf vrf-table-export-timeout {
      type uint32;
      units "second";
      description "VRF table export timeout in seconds";
    }
    leaf options-template-export-timeout {
      type uint32;
      units "second";
      description "Options template export timeout in seconds";
    }
    leaf data-template-export-timeout {
      type uint32;
      units "second";
      description "Data template export timeout in seconds";
    }
    leaf common-template-export-timeout {
      type uint32;
      units "second";
      description "Common template export timeout in seconds";
    }
  }

  grouping NFMGR-V9-EXP-INFO {
    description "Netflow version 9 export info";
    leaf sampler-table-export-timeout {
      type uint32;
      units "second";
      description "Sampler table export timeout in seconds";
    }
    leaf interface-table-export-timeout {
      type uint32;
      units "second";
      description "Interface table export timeout in seconds";
    }
    leaf vrf-table-export-timeout {
      type uint32;
      units "second";
      description "VRF table export timeout in seconds";
    }
    leaf options-template-export-timeout {
      type uint32;
      units "second";
      description "Options template export timeout in seconds";
    }
    leaf data-template-export-timeout {
      type uint32;
      units "second";
      description "Data template export timeout in seconds";
    }
    leaf common-template-export-timeout {
      type uint32;
      units "second";
      description "Common template export timeout in seconds";
    }
  }

  grouping NFMGR-FEM-EDM-VER-INFO {
    description "Netflow export version info";

    container version9 {
      when "../version = 'v9'" {
        description "../version = 'V9'";
      }
      description "version9";
      uses NFMGR-V9-EXP-INFO;
    }

    container ipfix {
      when "../version = 'ip-fix'" {
        description "../version = 'IP_FIX'";
      }
      description "ipfix";
      uses NFMGR-IPFIX-EXP-INFO;
    }
    leaf version {
      type Nfmgr-fem-edm-exp-ver;
      description "version";
    }
  }

  grouping NFMGR-FEM-EDM-CLTR-INFO {
    description "Netflow export collector info";
    leaf destination-address {
      type string;
      description
        "Destination IPv4 address in AAA.BBB.CCC.DDD
        format";
    }
    leaf source-address {
      type string;
      description "Source IPv4 address in AAA.BBB.CCC.DDD format";
    }
    leaf vrf-name {
      type string;
      description "VRF name";
    }
    leaf source-interface {
      type string;
      description "Source interface name";
    }
    leaf dscp {
      type uint8;
      description "DSCP";
    }
    leaf transport-protocol {
      type Nfmgr-fem-edm-trans-proto;
      description "Transport protocol";
    }
    leaf destination-port {
      type uint16;
      description "Transport destination port number";
    }
  }

  grouping NFMGR-FEM-EDM-INFO {
    description "Netflow flow exporter data";

    container version {
      description "Export version data";
      uses NFMGR-FEM-EDM-VER-INFO;
    }
    leaf id {
      type uint32;
      description "Unique ID in the global flow exporter ID space";
    }
    leaf name {
      type string;
      description "Name of the flow exporter map";
    }

    list collector {
      description "Export collector array";
      uses NFMGR-FEM-EDM-CLTR-INFO;
    }
  }
}
