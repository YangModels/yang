module Cisco-IOS-XR-dnx-netflow-oper {

  /*** NAMESPACE / PREFIX DEFINITION ***/

  namespace "http://cisco.com/ns/yang/Cisco-IOS-XR-dnx-netflow-oper";


  prefix "dnx-netflow-oper";

  /*** LINKAGE (IMPORTS / INCLUDES) ***/

  import Cisco-IOS-XR-types { prefix "xr"; }

  include Cisco-IOS-XR-dnx-netflow-oper-sub5 {
    revision-date 2015-11-09;
  }

  include Cisco-IOS-XR-dnx-netflow-oper-sub4 {
    revision-date 2015-11-09;
  }

  include Cisco-IOS-XR-dnx-netflow-oper-sub3 {
    revision-date 2015-11-09;
  }

  include Cisco-IOS-XR-dnx-netflow-oper-sub2 {
    revision-date 2015-11-09;
  }

  include Cisco-IOS-XR-dnx-netflow-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR dnx-netflow package operational data.

     This module contains definitions
     for the following management objects:
       net-flow: NetFlow operational data

     Copyright (c) 2013-2016 by Cisco Systems, Inc.
     All rights reserved.";

  revision "2015-11-09" {
    description
      "IOS XR 6.0 revision.";
  }


  container net-flow {
    config false;
    description "NetFlow operational data";

    container configuration {
      description "NetFlow configuration information";

      container flow-monitor-maps {
        description "Flow monitor map configuration information";

        list flow-monitor-map {
          key "monitor-name";
          description "Flow monitor map information";
          leaf monitor-name {
            type xr:Cisco-ios-xr-string;
            description "Monitor name";
          }
          uses NFMGR-FMM-EDM-INFO;
        }
      }

      container flow-sampler-maps {
        description "Flow sampler map configuration information";

        list flow-sampler-map {
          key "sampler-name";
          description "Flow sampler map information";
          leaf sampler-name {
            type xr:Cisco-ios-xr-string;
            description "Sampler name";
          }
          uses NFMGR-FSM-EDM-INFO;
        }
      }

      container flow-exporter-maps {
        description "Flow exporter map configuration information";

        list flow-exporter-map {
          key "exporter-name";
          description "Flow exporter map information";
          leaf exporter-name {
            type xr:Cisco-ios-xr-string;
            description "Exporter name";
          }
          uses NFMGR-FEM-EDM-INFO;
        }
      }
    }

    container statistics {
      description "Node-specific NetFlow statistics information";

      list statistic {
        key "node";
        description
          "NetFlow statistics information for a particular
          node";

        container producer {
          description "NetFlow producer statistics";

          container statistics {
            description "Statistics information";
            uses NF-PRODUCER-STATS;
          }
        }

        container server {
          description "NetFlow server statistics";

          container flow-exporters {
            description "Flow exporter information";

            list flow-exporter {
              key "exporter-name";
              description "Exporter information";

              container exporter {
                description
                  "Statistics information for the exporter";
                uses NFSVR-SHOW-FLOW-EXPORTER-RESP-ARRAY;
              }
              leaf exporter-name {
                type xr:Cisco-ios-xr-string;
                description "Exporter name";
              }
            }
          }
        }
        leaf node {
          type xr:Node-id;
          description "Node location";
        }
      }
    }
  }
}
