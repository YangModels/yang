module Cisco-IOS-XR-tunnel-nve-oper {

  /*** NAMESPACE / PREFIX DEFINITION ***/

  namespace "http://cisco.com/ns/yang/Cisco-IOS-XR-tunnel-nve-oper";


  prefix "tunnel-nve-oper";

  /*** LINKAGE (IMPORTS / INCLUDES) ***/

  import Cisco-IOS-XR-types { prefix "xr"; }

  include Cisco-IOS-XR-tunnel-nve-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR tunnel-nve package operational data.

     This module contains definitions
     for the following management objects:
       nve: NVE operational data

     Copyright (c) 2013-2016 by Cisco Systems, Inc.
     All rights reserved.";

  revision "2015-11-09" {
    description
      "IOS XR 6.0 revision.";
  }


  container nve {
    config false;
    description "NVE operational data";

    container vnis {
      description "Table for VNIs";

      list vni {
        key "vni";
        description "The attributes for a particular VNI";
        leaf vni {
          type xr:Cisco-ios-xr-string;
          description "VNI ID";
        }
        uses NVE-SHOW-VNI-BD;
      }
    }

    container interfaces {
      description "Table for NVE interface attributes";

      list interface {
        key "interface-name";
        description "The attributes for a particular interface";
        leaf interface-name {
          type xr:Interface-name;
          description "Interface Name";
        }
        uses NVE-SHOW-NVE-INTF-BD;
      }
    }
  }
}
