module Cisco-IOS-XR-ethernet-loopback-oper {
  namespace "http://cisco.com/ns/yang/Cisco-IOS-XR-ethernet-loopback-oper";
  prefix ethernet-loopback-oper;

  import Cisco-IOS-XR-types {
    prefix xr;
  }
  import cisco-semver {
    prefix semver;
  }
  include Cisco-IOS-XR-ethernet-loopback-oper-sub1 {
    revision-date 2021-04-27;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ethernet-loopback package operational data.
     
     This module contains definitions
     for the following management objects:
       ethernet-loopback: Ethernet Loopback operational data.
     
     Copyright (c) 2013-2021 by Cisco Systems, Inc.
     All rights reserved.";

  revision 2021-04-27 {
    description
      "Add COS filter support flag to active sessions";
    semver:module-version "1.1.0";
  }
  revision 2019-04-05 {
    description
      "Establish semantic version baseline.";
    semver:module-version "1.0.0";
  }
  revision 2015-11-09 {
    description
      "IOS XR 6.0 revision.";
  }

  container ethernet-loopback {
    config false;
    description
      "Ethernet Loopback operational data.";
    container messages-interfaces {
      description
        "Container for loopback messages";
      list messages-interface {
        key "interface-name";
        description
          "Loopback messages";
        leaf interface-name {
          type xr:Interface-name;
          description
            "InterfaceName";
        }
        uses EDPL-MESSAGES-BAG;
      }
    }
    container permitted-interfaces {
      description
        "Container for interfaces on which Ethernet
         Loopback is permitted.";
      list permitted-interface {
        key "interface-name";
        description
          "Data for an interface permitted to use Ethernet
           Loopback.";
        leaf interface-name {
          type xr:Interface-name;
          description
            "InterfaceName";
        }
        uses EDPL-PERMITTED-BAG;
      }
    }
    container active-interfaces {
      description
        "Container for interfaces with active Ethernet
         Loopback sessions.";
      list active-interface {
        key "interface-name";
        description
          "Data for an interface with active Ethernet
           Loopback sessions.";
        leaf interface-name {
          type xr:Interface-name;
          description
            "InterfaceName";
        }
        uses EDPL-ACTIVE-BAG;
      }
    }
  }
}
