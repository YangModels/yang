submodule Cisco-IOS-XR-crypto-ssh-oper-sub1 {
  belongs-to Cisco-IOS-XR-crypto-ssh-oper {
    prefix Cisco-IOS-XR-crypto-ssh-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR crypto-ssh package operational data.
     
     Copyright (c) 2013-2022 by Cisco Systems, Inc.
     All rights reserved.";

  revision 2022-11-14 {
    description
      "Fixing inconsistencies between platforms.
       2022-09-05
         Authorized principals command support.
       2022-03-20
         OpenSSH certificate support.";
    semver:module-version "2.1.0";
  }
  revision 2021-06-04 {
    description
      "Default option for authentication.";
    semver:module-version "2.0.0";
  }
  revision 2020-01-21 {
    description
      "Yang support to import pubkey for user in config mode";
    semver:module-version "1.1.0";
  }
  revision 2019-07-08 {
    description
      "Introducing show ssh server CLI.";
    semver:module-version "1.0.1";
  }
  revision 2019-04-05 {
    description
      "Establish semantic version baseline.";
  }
  revision 2017-08-25 {
    description
      "Introducing show ssh history CLI.";
  }
  revision 2017-05-01 {
    description
      "Fixing backward compatibility error in module.";
  }
  revision 2015-06-02 {
    description
      "IOS XR 5.3.2 revision.";
  }
  revision 2015-01-07 {
    description
      "IOS XR 5.3.1 revision.";
  }

  grouping SSH-SERVER-PARAMS {
    description
      "Information about ssh server running parameters";
    leaf version {
      type string {
        length "0..10";
      }
      description
        "Version";
    }
    leaf port {
      type uint32;
      description
        "SSH Port";
    }
    leaf vrf {
      type string {
        length "0..2000";
      }
      description
        "Vrfs and acls";
    }
    leaf netconfport {
      type uint32;
      description
        "Netconf Port";
    }
    leaf netconfvrf {
      type string {
        length "0..2000";
      }
      description
        "Netconf vrfs and acls";
    }
    leaf netconfver {
      type string {
        length "0..10";
      }
      description
        "Netconf Version";
    }
    leaf hostkeyalgo {
      type string {
        length "0..230";
      }
      description
        "Hostkey algorithms";
    }
    leaf kexalgo {
      type string {
        length "0..230";
      }
      description
        "Key exchange algorithms";
    }
    leaf cipheralgo {
      type string {
        length "0..230";
      }
      description
        "Encryption algorithms";
    }
    leaf macalgo {
      type string {
        length "0..230";
      }
      description
        "Mac algorithms";
    }
    leaf backupserver {
      type string {
        length "0..100";
      }
      description
        "Backup SSH server";
    }
    leaf trustpointhost {
      type string {
        length "0..128";
      }
      description
        "Trustpoint for host";
    }
    leaf trustpointuser {
      type string {
        length "0..1289";
      }
      description
        "Trustpoint for user";
    }
    leaf dscp {
      type uint32;
      description
        "Dscp";
    }
    leaf ratelimit {
      type uint32;
      description
        "ratelimit";
    }
    leaf sessionlimit {
      type uint32;
      description
        "session limit";
    }
    leaf rekeytime {
      type uint32;
      description
        "Rekey Time";
    }
    leaf rekeyvolume {
      type uint32;
      description
        "Rekey Volume";
    }
    leaf windowscalefactor {
      type uint32;
      description
        "Window scale factor";
    }
    leaf passwordauthen {
      type boolean;
      description
        "Password Authentication support";
    }
    leaf keyboardinteractiveauthen {
      type boolean;
      description
        "Pubkey Authentication support";
    }
    leaf pubkeyauthen {
      type boolean;
      description
        "Pubkey Authentication support";
    }
    leaf certificateauthen {
      type boolean;
      description
        "Certificate based Authentication support";
    }
    leaf portforwarding {
      type string {
        length "0..10";
      }
      description
        "port forwarding for ssh server";
    }
    leaf maxauthlimit {
      type uint32;
      description
        "Max Auth limit";
    }
    leaf certificate-username {
      type string {
        length "0..50";
      }
      description
        "SSHD certificate username";
    }
    leaf openssh-trustpointhost {
      type string {
        length "0..128";
      }
      description
        "Openssh Trustpoint for host";
    }
    leaf openssh-trustpointuser {
      type string {
        length "0..33023";
      }
      description
        "OpensshTrustpoint for user";
    }
    leaf authorized-principals-cmd {
      type boolean;
      description
        "Enable openssh Authorized principals cmd";
    }
  }
}
