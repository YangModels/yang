module Cisco-IOS-XR-controller-ncs1001-ots-oper {
  namespace "http://cisco.com/ns/yang/Cisco-IOS-XR-controller-ncs1001-ots-oper";
  prefix controller-ncs1001-ots-oper;

  import Cisco-IOS-XR-types {
    prefix xr;
  }
  import cisco-semver {
    prefix semver;
  }
  include Cisco-IOS-XR-controller-ncs1001-ots-oper-sub1 {
    revision-date 2022-11-24;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR controller-ncs1001-ots package operational data.
     
     This module contains definitions
     for the following management objects:
       ots-oper: OTS operational data
     
     Copyright (c) 2013-2022 by Cisco Systems, Inc.
     All rights reserved.";

  revision 2022-11-24 {
    description
      "leaves receive-power, transmit-power are removed and receive-power-dbm, transmit-power-dbm are modified to receive-power, transmit-power in OTS-EDM-LANE-DATA group";
    semver:module-version "1.0.0";
  }
  revision 2022-11-23 {
    description
      "enum names changed in ots_legacy_ui bag";
  }
  revision 2019-04-05 {
    description
      "Establish semantic version baseline.";
  }
  revision 2015-11-09 {
    description
      "IOS XR 6.0 revision.";
  }

  container ots-oper {
    config false;
    description
      "OTS operational data";
    container ots-ports {
      description
        "Port operational data for all OTS controllers";
      list ots-port {
        key "name";
        description
          "OTS controller operational data";
        container ots-info {
          description
            "OTS operational data";
          uses OTS-EDM-INFO;
        }
        container ots-spectrum-info {
          description
            "OTS Spectrum Operational data";
          uses OTS-EDM-SPECTRUM-INFO;
        }
        leaf name {
          type xr:Interface-name;
          description
            "Port name";
        }
      }
    }
  }
}
