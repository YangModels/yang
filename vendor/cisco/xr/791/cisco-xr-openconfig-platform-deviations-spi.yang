//*************  DO-NOT EDIT  **************
//*********** Auto-generated file ********** 

 module cisco-xr-openconfig-platform-deviations {

  namespace "http://cisco.com/ns/yang/cisco-xr-openconfig-platform-deviations";
  prefix  "oc-platformdevs";

  import openconfig-platform { prefix oc-platform; }

  organization "Cisco Systems, Inc.";

  contact
    "Cisco Systems, Inc.
     Customer Service

     Postal: 170 West Tasman Drive
     San Jose, CA 95134

     Tel: +1 800 553-NETS

     E-mail: cs-yang@cisco.com";

  description
    "This module contains a set of deviations for 
 
     openconfig-platform.yang@2021-08-13 

     on Cisco IOS-XR devices.

     Copyright (c) 2017 by Cisco Systems, Inc.
     All rights reserved.";

  revision "2022-03-24" {
    description
      "Initial revision applicable to IOS-XR 6.4.1";
  }


  deviation /oc-platform:components/oc-platform:component/oc-platform:state/oc-platform:mfg-date {
    deviate not-supported;
  }

  deviation /oc-platform:components/oc-platform:component/oc-platform:state/oc-platform:temperature/oc-platform:avg {
    deviate not-supported;
  }

  deviation /oc-platform:components/oc-platform:component/oc-platform:state/oc-platform:temperature/oc-platform:min {
    deviate not-supported;
  }

  deviation /oc-platform:components/oc-platform:component/oc-platform:state/oc-platform:temperature/oc-platform:max {
    deviate not-supported;
  }

  deviation /oc-platform:components/oc-platform:component/oc-platform:state/oc-platform:temperature/oc-platform:interval {
    deviate not-supported;
  }

  deviation /oc-platform:components/oc-platform:component/oc-platform:state/oc-platform:temperature/oc-platform:min-time {
    deviate not-supported;
  }

  deviation /oc-platform:components/oc-platform:component/oc-platform:state/oc-platform:temperature/oc-platform:max-time {
    deviate not-supported;
  }

  deviation /oc-platform:components/oc-platform:component/oc-platform:state/oc-platform:pcie/oc-platform:fatal-errors/oc-platform:total-errors {
    deviate not-supported;
  }

  deviation /oc-platform:components/oc-platform:component/oc-platform:state/oc-platform:pcie/oc-platform:fatal-errors/oc-platform:undefined-errors {
    deviate not-supported;
  }

  deviation /oc-platform:components/oc-platform:component/oc-platform:state/oc-platform:pcie/oc-platform:fatal-errors/oc-platform:data-link-errors {
    deviate not-supported;
  }

  deviation /oc-platform:components/oc-platform:component/oc-platform:state/oc-platform:pcie/oc-platform:fatal-errors/oc-platform:surprise-down-errors {
    deviate not-supported;
  }

  deviation /oc-platform:components/oc-platform:component/oc-platform:state/oc-platform:pcie/oc-platform:fatal-errors/oc-platform:poisoned-tlp-errors {
    deviate not-supported;
  }

  deviation /oc-platform:components/oc-platform:component/oc-platform:state/oc-platform:pcie/oc-platform:fatal-errors/oc-platform:flow-control-protocol-errors {
    deviate not-supported;
  }

  deviation /oc-platform:components/oc-platform:component/oc-platform:state/oc-platform:pcie/oc-platform:fatal-errors/oc-platform:completion-timeout-errors {
    deviate not-supported;
  }

  deviation /oc-platform:components/oc-platform:component/oc-platform:state/oc-platform:pcie/oc-platform:fatal-errors/oc-platform:completion-abort-errors {
    deviate not-supported;
  }

  deviation /oc-platform:components/oc-platform:component/oc-platform:state/oc-platform:pcie/oc-platform:fatal-errors/oc-platform:unexpected-completion-errors {
    deviate not-supported;
  }

  deviation /oc-platform:components/oc-platform:component/oc-platform:state/oc-platform:pcie/oc-platform:fatal-errors/oc-platform:receiver-overflow-errors {
    deviate not-supported;
  }

  deviation /oc-platform:components/oc-platform:component/oc-platform:state/oc-platform:pcie/oc-platform:fatal-errors/oc-platform:malformed-tlp-errors {
    deviate not-supported;
  }

  deviation /oc-platform:components/oc-platform:component/oc-platform:state/oc-platform:pcie/oc-platform:fatal-errors/oc-platform:ecrc-errors {
    deviate not-supported;
  }

  deviation /oc-platform:components/oc-platform:component/oc-platform:state/oc-platform:pcie/oc-platform:fatal-errors/oc-platform:unsupported-request-errors {
    deviate not-supported;
  }

  deviation /oc-platform:components/oc-platform:component/oc-platform:state/oc-platform:pcie/oc-platform:fatal-errors/oc-platform:acs-violation-errors {
    deviate not-supported;
  }

  deviation /oc-platform:components/oc-platform:component/oc-platform:state/oc-platform:pcie/oc-platform:fatal-errors/oc-platform:internal-errors {
    deviate not-supported;
  }

  deviation /oc-platform:components/oc-platform:component/oc-platform:state/oc-platform:pcie/oc-platform:fatal-errors/oc-platform:blocked-tlp-errors {
    deviate not-supported;
  }

  deviation /oc-platform:components/oc-platform:component/oc-platform:state/oc-platform:pcie/oc-platform:fatal-errors/oc-platform:atomic-op-blocked-errors {
    deviate not-supported;
  }

  deviation /oc-platform:components/oc-platform:component/oc-platform:state/oc-platform:pcie/oc-platform:fatal-errors/oc-platform:tlp-prefix-blocked-errors {
    deviate not-supported;
  }

  deviation /oc-platform:components/oc-platform:component/oc-platform:state/oc-platform:pcie/oc-platform:non-fatal-errors/oc-platform:total-errors {
    deviate not-supported;
  }

  deviation /oc-platform:components/oc-platform:component/oc-platform:state/oc-platform:pcie/oc-platform:non-fatal-errors/oc-platform:undefined-errors {
    deviate not-supported;
  }

  deviation /oc-platform:components/oc-platform:component/oc-platform:state/oc-platform:pcie/oc-platform:non-fatal-errors/oc-platform:data-link-errors {
    deviate not-supported;
  }

  deviation /oc-platform:components/oc-platform:component/oc-platform:state/oc-platform:pcie/oc-platform:non-fatal-errors/oc-platform:surprise-down-errors {
    deviate not-supported;
  }

  deviation /oc-platform:components/oc-platform:component/oc-platform:state/oc-platform:pcie/oc-platform:non-fatal-errors/oc-platform:poisoned-tlp-errors {
    deviate not-supported;
  }

  deviation /oc-platform:components/oc-platform:component/oc-platform:state/oc-platform:pcie/oc-platform:non-fatal-errors/oc-platform:flow-control-protocol-errors {
    deviate not-supported;
  }

  deviation /oc-platform:components/oc-platform:component/oc-platform:state/oc-platform:pcie/oc-platform:non-fatal-errors/oc-platform:completion-timeout-errors {
    deviate not-supported;
  }

  deviation /oc-platform:components/oc-platform:component/oc-platform:state/oc-platform:pcie/oc-platform:non-fatal-errors/oc-platform:completion-abort-errors {
    deviate not-supported;
  }

  deviation /oc-platform:components/oc-platform:component/oc-platform:state/oc-platform:pcie/oc-platform:non-fatal-errors/oc-platform:unexpected-completion-errors {
    deviate not-supported;
  }

  deviation /oc-platform:components/oc-platform:component/oc-platform:state/oc-platform:pcie/oc-platform:non-fatal-errors/oc-platform:receiver-overflow-errors {
    deviate not-supported;
  }

  deviation /oc-platform:components/oc-platform:component/oc-platform:state/oc-platform:pcie/oc-platform:non-fatal-errors/oc-platform:malformed-tlp-errors {
    deviate not-supported;
  }

  deviation /oc-platform:components/oc-platform:component/oc-platform:state/oc-platform:pcie/oc-platform:non-fatal-errors/oc-platform:ecrc-errors {
    deviate not-supported;
  }

  deviation /oc-platform:components/oc-platform:component/oc-platform:state/oc-platform:pcie/oc-platform:non-fatal-errors/oc-platform:unsupported-request-errors {
    deviate not-supported;
  }

  deviation /oc-platform:components/oc-platform:component/oc-platform:state/oc-platform:pcie/oc-platform:non-fatal-errors/oc-platform:acs-violation-errors {
    deviate not-supported;
  }

  deviation /oc-platform:components/oc-platform:component/oc-platform:state/oc-platform:pcie/oc-platform:non-fatal-errors/oc-platform:internal-errors {
    deviate not-supported;
  }

  deviation /oc-platform:components/oc-platform:component/oc-platform:state/oc-platform:pcie/oc-platform:non-fatal-errors/oc-platform:blocked-tlp-errors {
    deviate not-supported;
  }

  deviation /oc-platform:components/oc-platform:component/oc-platform:state/oc-platform:pcie/oc-platform:non-fatal-errors/oc-platform:atomic-op-blocked-errors {
    deviate not-supported;
  }

  deviation /oc-platform:components/oc-platform:component/oc-platform:state/oc-platform:pcie/oc-platform:non-fatal-errors/oc-platform:tlp-prefix-blocked-errors {
    deviate not-supported;
  }

  deviation /oc-platform:components/oc-platform:component/oc-platform:state/oc-platform:pcie/oc-platform:correctable-errors/oc-platform:total-errors {
    deviate not-supported;
  }

  deviation /oc-platform:components/oc-platform:component/oc-platform:state/oc-platform:pcie/oc-platform:correctable-errors/oc-platform:receiver-errors {
    deviate not-supported;
  }

  deviation /oc-platform:components/oc-platform:component/oc-platform:state/oc-platform:pcie/oc-platform:correctable-errors/oc-platform:bad-tlp-errors {
    deviate not-supported;
  }

  deviation /oc-platform:components/oc-platform:component/oc-platform:state/oc-platform:pcie/oc-platform:correctable-errors/oc-platform:bad-dllp-errors {
    deviate not-supported;
  }

  deviation /oc-platform:components/oc-platform:component/oc-platform:state/oc-platform:pcie/oc-platform:correctable-errors/oc-platform:relay-rollover-errors {
    deviate not-supported;
  }

  deviation /oc-platform:components/oc-platform:component/oc-platform:state/oc-platform:pcie/oc-platform:correctable-errors/oc-platform:replay-timeout-errors {
    deviate not-supported;
  }

  deviation /oc-platform:components/oc-platform:component/oc-platform:state/oc-platform:pcie/oc-platform:correctable-errors/oc-platform:advisory-non-fatal-errors {
    deviate not-supported;
  }

  deviation /oc-platform:components/oc-platform:component/oc-platform:state/oc-platform:pcie/oc-platform:correctable-errors/oc-platform:internal-errors {
    deviate not-supported;
  }

  deviation /oc-platform:components/oc-platform:component/oc-platform:state/oc-platform:pcie/oc-platform:correctable-errors/oc-platform:hdr-log-overflow-errors {
    deviate not-supported;
  }

  deviation /oc-platform:components/oc-platform:component/oc-platform:properties/oc-platform:property {
    deviate not-supported;
  }


}
//total deviations:53
