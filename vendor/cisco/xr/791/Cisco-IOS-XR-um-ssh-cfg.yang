module Cisco-IOS-XR-um-ssh-cfg {
  namespace "http://cisco.com/ns/yang/Cisco-IOS-XR-um-ssh-cfg";
  prefix um-ssh-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ssh package configuration.
     
     This YANG module augments the
     modules with configuration data.
     
     Copyright (c) 2021-2022 by Cisco Systems, Inc.
     All rights reserved.";

  revision 2022-09-29 {
    description
      "openssh trustpoint";
    semver:module-version "2.1.0";
  }
  revision 2021-09-20 {
    description
      "New rsa feartures";
    semver:module-version "2.0.0";
  }
  revision 2021-02-10 {
    description
      "Initial release";
    semver:module-version "1.0.0";
  }

  container ssh {
    description
      "Secure Shell configuration";
    leaf timeout {
      type uint32 {
        range "5..120" {
          description
            "Timeout value between 5-120 seconds";
        }
      }
      description
        "Set timeout value for SSH";
    }
    container server {
      description
        "Provide SSH server service";
      container openssh {
        description
          "OpenSSH certificates";
        container enable {
          description
            "Enable extended feature for OpenSSH certificates";
          container authorized-principals-command {
            presence "Indicates a authorized-principals-command node is configured.";
            description
              "Enable AuthorizedPrincipalCommand config";
          }
        }
        container trustpoint {
          description
            "trustpoints for openssh server certificates";
          leaf host {
            type xr:Cisco-ios-xr-string {
              length "1..128" {
                description
                  "trustpoint name";
              }
            }
            description
              "trustpoint from where server will take its certificate";
          }
          container user {
            description
              "trustpoints used for user certificate validation";
            container trustpoints {
              description
                "trustpoint name";
              list trustpoint {
                key "trustpoint-name";
                description
                  "trustpoint name";
                leaf trustpoint-name {
                  type xr:Cisco-ios-xr-string {
                    length "1..128" {
                      description
                        "trustpoint name";
                    }
                  }
                  description
                    "trustpoint name";
                }
              }
            }
          }
        }
      }
      container vrfs {
        description
          "Cisco sshd VRF name";
        list vrf {
          key "vrf-name";
          description
            "Cisco sshd VRF name";
          leaf vrf-name {
            type union {
              type string {
                pattern "default" {
                  description
                    "Default vrf name";
                }
              }
              type xr:Cisco-ios-xr-string {
                length "1..32" {
                  description
                    "Enter vrf name";
                }
              }
            }
            description
              "Cisco sshd VRF name";
          }
          container ipv4 {
            description
              "IPv4 access list for ssh server";
            leaf access-list {
              type xr:Cisco-ios-xr-string {
                length "1..64" {
                  description
                    "Name of IPv4 access list - Max 64 characters";
                }
                pattern "[a-z0-9A-Z][-_.:a-z0-9A-Z]*";
              }
              description
                "Configure IPv4 access-list";
            }
          }
          container ipv6 {
            description
              "IPv6 access list for ssh server";
            leaf access-list {
              type xr:Cisco-ios-xr-string {
                length "1..64" {
                  description
                    "Name of IPv6 access list - Max 64 characters";
                }
                pattern "[a-z0-9A-Z][-_.:a-z0-9A-Z]*";
              }
              description
                "Configure IPv6 access-list";
            }
          }
        }
      }
      container v1 {
        presence "Indicates a v1 node is configured.";
        description
          "Cisco sshd protocol version 1 ";
      }
      container v2 {
        presence "Indicates a v2 node is configured.";
        description
          "Cisco sshd protocol version 2 ";
      }
      container backup {
        description
          "Cisco sshd backup server";
        leaf port {
          type uint32 {
            range "11000..15000" {
              description
                "port number on which backup ssh service runs";
            }
          }
          must "../vrf";
          description
            "port on which backup ssh server listens";
        }
        leaf vrf {
          type xr:Cisco-ios-xr-string {
            length "1..32" {
              description
                "Name of vrf for backup ssh server";
            }
          }
          must "../port";
          must "../port";
          description
            "vrf in which backup ssh server runs";
        }
      }
      leaf rate-limit {
        type uint32 {
          range "1..600" {
            description
              "Limit in term of number of request per minute (default 60)";
          }
        }
        description
          "Cisco sshd rate-limit of service requests";
      }
      container disable {
        description
          "Disable sshd algorithms";
        container hmac {
          description
            "Disable sshd hmac algorithms";
          container hmac-sha2-512 {
            presence "Indicates a hmac-sha2-512 node is configured.";
            description
              "Disable sshd hmac-sha2-512-algorithm";
          }
          container hmac-sha1 {
            presence "Indicates a hmac-sha1 node is configured.";
            description
              "Disable sshd hmac-sha1-algorithm";
          }
          container hmac-sha2-256 {
            presence "Indicates a hmac-sha2-256 node is configured.";
            description
              "Disable sshd hmac-sha2-256-algorithm";
          }
        }
      }
      container enable {
        description
          "Enable AES-CBC and 3DES-CBC algorithms";
        container cipher {
          description
            "Enable ssh server ciphers";
          container aes-cbc {
            presence "Indicates a aes-cbc node is configured.";
            description
              "Enable ssh server aes-cbc algorithms";
          }
          container threedes-cbc {
            presence "Indicates a threedes-cbc node is configured.";
            description
              "Enable ssh server 3des-cbc algorithm";
          }
        }
      }
      leaf session-limit {
        type uint32 {
          range "1..110" {
            description
              "Number of allowable concurrent incoming ssh sessions";
          }
        }
        description
          "Cisco sshd session-limit of service requests";
      }
      container logging {
        presence "Indicates a logging node is configured.";
        description
          "Enable ssh server logging";
      }
      leaf dscp {
        type uint32 {
          range "0..63" {
            description
              "DSCP value range";
          }
        }
        description
          "Cisco ssh server DSCP";
      }
      container netconf {
        description
          "start ssh service for netconf subsystem";
        container vrfs {
          description
            "Cisco netconf VRF name";
          list vrf {
            key "vrf-name";
            description
              "Cisco netconf VRF name";
            leaf vrf-name {
              type union {
                type string {
                  pattern "default" {
                    description
                      "Default vrf name";
                  }
                }
                type xr:Cisco-ios-xr-string {
                  length "1..32" {
                    description
                      "Enter vrf name";
                  }
                }
              }
              description
                "Cisco netconf VRF name";
            }
            container ipv4 {
              description
                "IPv4 access list for netconf ssh server";
              leaf access-list {
                type xr:Cisco-ios-xr-string {
                  length "1..64" {
                    description
                      "Name of IPv4 access list - Max 32 characters";
                  }
                  pattern "[a-z0-9A-Z][-_.:a-z0-9A-Z]*";
                }
                description
                  "Configure IPv4 access-list";
              }
            }
            container ipv6 {
              description
                "IPv6 access list for netconf ssh server";
              leaf access-list {
                type xr:Cisco-ios-xr-string {
                  length "1..64" {
                    description
                      "Name of IPv6 access list - Max 32 characters";
                  }
                  pattern "[a-z0-9A-Z][-_.:a-z0-9A-Z]*";
                }
                description
                  "Configure IPv6 access-list";
              }
            }
          }
        }
        leaf port {
          type uint32 {
            range "1..65535" {
              description
                "port number on which ssh service to be started for netconf";
            }
          }
          description
            "Port to start ssh netconf subsystem service (Default 830)";
        }
      }
      container capability {
        description
          "Turn on Capability";
        container netconf-xml {
          presence "Indicates a netconf-xml node is configured.";
          description
            "Use Netconf XML stack";
        }
      }
      leaf rekey-time {
        type uint32 {
          range "30..1440" {
            description
              "Time Period in minutes";
          }
        }
        description
          "Configures time-based rekey (default 60 minutes)";
      }
      leaf rekey-volume {
        type uint32 {
          range "1024..4095" {
            description
              "Data in MB";
          }
        }
        description
          "Configures volume-based rekey (default 1024MB)";
      }
      container algorithms {
        description
          "server algorithms";
        container key-exchanges {
          description
            "Key exchange algorithms";
          leaf-list key-exchange {
            type union {
              type string {
                pattern "ecdh-sha2-nistp521";
              }
              type string {
                pattern "ecdh-sha2-nistp384";
              }
              type string {
                pattern "ecdh-sha2-nistp256";
              }
              type string {
                pattern "diffie-hellman-group14-sha1";
              }
              type string {
                pattern "diffie-hellman-group1-sha1";
              }
            }
            max-elements "5";
            description
              "Key exchange algorithms";
          }
        }
        container host-key {
          must "ecdsa-nistp256 or ecdsa-nistp384 or ecdsa-nistp521 or rsa or dsa or x509v3-ssh-rsa or ed25519 or rsa-sha512 or rsa-sha256 or ssh-rsa";
          presence "Indicates a ca-certificate node is configured.";
          description
            "Host key algorithms to be used";
          container ecdsa-nistp256 {
            presence "Indicates a ecdsa-nistp256 node is configured.";
            description
              "ecdsa-nistp256";
          }
          container ecdsa-nistp384 {
            presence "Indicates a ecdsa-nistp384 node is configured.";
            description
              "ecdsa-nistp384";
          }
          container ecdsa-nistp521 {
            presence "Indicates a ecdsa-nistp521 node is configured.";
            description
              "ecdsa-nistp521";
          }
          container rsa {
            presence "Indicates a rsa node is configured.";
            description
              "rsa";
          }
          container dsa {
            presence "Indicates a dsa node is configured.";
            description
              "dsa";
          }
          container x509v3-ssh-rsa {
            presence "Indicates a x509v3-ssh-rsa node is configured.";
            description
              "x509v3-ssh-rsa";
          }
          container ed25519 {
            presence "Indicates a ed25519 node is configured.";
            description
              "ed25519";
          }
          container rsa-sha512 {
            presence "Indicates a rsa-sha512 node is configured.";
            description
              "rsa-sha512";
          }
          container rsa-sha256 {
            presence "Indicates a rsa-sha256 node is configured.";
            description
              "rsa-sha256";
          }
          container ssh-rsa {
            presence "Indicates a ssh-rsa node is configured.";
            description
              "ssh-rsa";
          }
        }
        container ciphers {
          description
            "cipher algorithms";
          leaf-list cipher {
            type union {
              type string {
                pattern "aes128-ctr";
              }
              type string {
                pattern "aes192-ctr";
              }
              type string {
                pattern "aes256-ctr";
              }
              type string {
                pattern "aes128-gcm@openssh.com";
              }
              type string {
                pattern "aes256-gcm@openssh.com";
              }
              type string {
                pattern "aes128-cbc";
              }
              type string {
                pattern "aes192-cbc";
              }
              type string {
                pattern "aes256-cbc";
              }
              type string {
                pattern "3des-cbc";
              }
            }
            max-elements "9";
            description
              "cipher algorithms";
          }
        }
      }
      leaf tcp-window-scale {
        type uint32 {
          range "1..14" {
            description
              "Window scale factor";
          }
        }
        description
          "Set tcp window-scale factor for High Latency links";
      }
      container trustpoint {
        description
          "trustpoints for server certificates";
        leaf host {
          type xr:Cisco-ios-xr-string {
            length "1..128" {
              description
                "trustpoint name";
            }
          }
          description
            "trustpoint from where server will take its certificate";
        }
        container user {
          description
            "trustpoints used for user certificate validation";
          container trustpoints {
            description
              "trustpoint name";
            list trustpoint {
              key "trustpoint-name";
              description
                "trustpoint name";
              leaf trustpoint-name {
                type xr:Cisco-ios-xr-string {
                  length "1..128" {
                    description
                      "trustpoint name";
                  }
                }
                description
                  "trustpoint name";
              }
            }
          }
        }
      }
      container certificate {
        description
          "certificate related parameters";
        container username {
          must "common-name or user-principle-name";
          presence "Indicates a username node is configured.";
          description
            "certificate field to be used as username";
          container common-name {
            presence "Indicates a common-name node is configured.";
            description
              "user common name(CN) from subject name field";
          }
          container user-principle-name {
            presence "Indicates a user-principle-name node is configured.";
            description
              "user principle name(UPN) from subject alternate name";
          }
        }
      }
      leaf max-auth-limit {
        type uint32 {
          range "3..20" {
            description
              "Number of allowable authentication attempts";
          }
        }
        description
          "User Configurable max authentication attempts";
      }
      container port-forwarding {
        description
          "Enable port forwarding for ssh server";
        container local {
          presence "Indicates a local node is configured.";
          description
            "Enable local port forwarding for ssh server";
        }
      }
      leaf port {
        type uint32 {
          range "5520..5529" {
            description
              "Allowable non default SSH Port range";
          }
        }
        description
          "User Configurable ssh port (Default 22)";
      }
      container usernames {
        description
          "ssh user";
        list username {
          key "username-name";
          description
            "ssh user";
          leaf username-name {
            type string {
              length "1..800" {
                description
                  "User name";
              }
            }
            description
              "ssh user";
          }
          leaf keystring {
            type string {
              length "1..800" {
                description
                  "Public key";
              }
            }
            description
              "Enter public key in ssh format";
          }
        }
      }
    }
    container client {
      description
        "Provide SSH client service";
      leaf knownhost {
        type xr:Cisco-ios-xr-string {
          length "1..800" {
            description
              "Filename - where to store known_host file";
          }
        }
        description
          "Enable the host pubkey check by local database";
      }
      leaf source-interface {
        type xr:Interface-name;
        description
          "Source interface for ssh client sessions";
      }
      leaf vrf {
        type xr:Cisco-ios-xr-string {
          length "1..32" {
            description
              "VRF name (max:32 chars)";
          }
        }
        description
          "Source interface VRF for ssh client sessions";
      }
      leaf dscp {
        type uint32 {
          range "0..63" {
            description
              "DSCP value range";
          }
        }
        description
          "DSCP value for ssh client sessions";
      }
      leaf rekey-time {
        type uint32 {
          range "30..1440" {
            description
              "Time Period in minutes";
          }
        }
        description
          "Configures time-based rekey (default 60 minutes)";
      }
      leaf rekey-volume {
        type uint32 {
          range "1024..4095" {
            description
              "Data in MB";
          }
        }
        description
          "Configures volume-based rekey (default 1024MB)";
      }
      container disable {
        description
          "Disable sshd algorithms";
        container hmac {
          description
            "Disable sshd hmac algorithms";
          container hmac-sha1 {
            presence "Indicates a hmac-sha1 node is configured.";
            description
              "Disable sshd hmac-sha1-algorithm";
          }
          container hmac-sha2-512 {
            presence "Indicates a hmac-sha2-512 node is configured.";
            description
              "Disable ssh hmac-sha2-512-algorithm";
          }
          container hmac-sha2-256 {
            presence "Indicates a hmac-sha2-256 node is configured.";
            description
              "Disable ssh hmac-sha2-256-algorithm";
          }
        }
      }
      container enable {
        description
          "Enable AES-CBC and 3DES-CBC algorithms";
        container cipher {
          description
            "Enable ssh client ciphers";
          container aes-cbc {
            presence "Indicates a aes-cbc node is configured.";
            description
              "Enable ssh client aes-cbc algorithms";
          }
          container threedes-cbc {
            presence "Indicates a threedes-cbc node is configured.";
            description
              "Enable ssh client 3des-cbc algorithm";
          }
        }
      }
      container algorithms {
        description
          "client algorithms";
        container key-exchanges {
          description
            "Key exchange algorithms";
          leaf-list key-exchange {
            type union {
              type string {
                pattern "ecdh-sha2-nistp521";
              }
              type string {
                pattern "ecdh-sha2-nistp384";
              }
              type string {
                pattern "ecdh-sha2-nistp256";
              }
              type string {
                pattern "diffie-hellman-group14-sha1";
              }
              type string {
                pattern "diffie-hellman-group1-sha1";
              }
            }
            max-elements "5";
            description
              "Key exchange algorithms";
          }
        }
        container ciphers {
          description
            "Cipher algorithms";
          leaf-list cipher {
            type union {
              type string {
                pattern "aes128-ctr";
              }
              type string {
                pattern "aes192-ctr";
              }
              type string {
                pattern "aes256-ctr";
              }
              type string {
                pattern "aes128-gcm@openssh.com";
              }
              type string {
                pattern "aes256-gcm@openssh.com";
              }
              type string {
                pattern "aes128-cbc";
              }
              type string {
                pattern "aes192-cbc";
              }
              type string {
                pattern "aes256-cbc";
              }
              type string {
                pattern "3des-cbc";
              }
            }
            max-elements "9";
            description
              "Cipher algorithms";
          }
        }
      }
      leaf tcp-window-scale {
        type uint32 {
          range "1..14" {
            description
              "Window scale factor";
          }
        }
        description
          "Set tcp window-scale factor for High Latency links";
      }
      container v2 {
        presence "Indicates a v2 node is configured.";
        description
          "Set ssh client to use version 2 ";
      }
      container v1 {
        presence "Indicates a v1 node is configured.";
        description
          "Set ssh client to use version 1 ";
      }
    }
  }
}
