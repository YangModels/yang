module Cisco-IOS-XR-ip-static-srv6-act {
  namespace "http://cisco.com/ns/yang/Cisco-IOS-XR-ip-static-srv6-act";
  prefix static-srv6-act;

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR action package configuration.
     
     Copyright (c) 2022 by Cisco Systems, Inc.
     All rights reserved.";

  revision 2022-10-31 {
    description
      "IOS XR 7.9.1 revision.";
  }

  rpc clear-static-srv6-sid-conflicts {
    description
      "Clear static srv6 sid conflicts";
  }
}
