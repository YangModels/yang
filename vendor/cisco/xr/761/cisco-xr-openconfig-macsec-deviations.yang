//*************  DO-NOT EDIT  **************
//*********** Auto-generated file ********** 

 module cisco-xr-openconfig-macsec-deviations {

  namespace "http://cisco.com/ns/yang/cisco-xr-openconfig-macsec-deviations";
  prefix  "oc-macsecdevs";

  import openconfig-macsec { prefix oc-macsec; }

  organization "Cisco Systems, Inc.";

  contact
    "Cisco Systems, Inc.
     Customer Service

     Postal: 170 West Tasman Drive
     San Jose, CA 95134

     Tel: +1 800 553-NETS

     E-mail: cs-yang@cisco.com";

  description
    "This module contains a set of deviations for 
 
     openconfig-macsec.yang@2020-05-01 

     on Cisco IOS-XR devices.

     Copyright (c) 2017, 2021-2022 by Cisco Systems, Inc.
     All rights reserved.";

  revision "2022-02-04" {
    description
      "Initial revision applicable to IOS-XR 6.4.1";
  }


  deviation /oc-macsec:macsec/oc-macsec:mka/oc-macsec:policies/oc-macsec:policy/oc-macsec:config/oc-macsec:sak-rekey-on-live-peer-loss {
    deviate not-supported;
  }

  deviation /oc-macsec:macsec/oc-macsec:mka/oc-macsec:policies/oc-macsec:policy/oc-macsec:config/oc-macsec:use-updated-eth-header {
    deviate not-supported;
  }

  deviation /oc-macsec:macsec/oc-macsec:mka/oc-macsec:policies/oc-macsec:policy/oc-macsec:state/oc-macsec:sak-rekey-on-live-peer-loss {
    deviate not-supported;
  }

  deviation /oc-macsec:macsec/oc-macsec:mka/oc-macsec:policies/oc-macsec:policy/oc-macsec:state/oc-macsec:use-updated-eth-header {
    deviate not-supported;
  }

  deviation /oc-macsec:macsec/oc-macsec:mka/oc-macsec:key-chains/oc-macsec:key-chain/oc-macsec:mka-keys/oc-macsec:mka-key/oc-macsec:state/oc-macsec:key-clear-text {
    deviate not-supported;
  }

  deviation /oc-macsec:macsec/oc-macsec:mka/oc-macsec:state/oc-macsec:counters/oc-macsec:out-mkpdu-errors {
    deviate not-supported;
  }

  deviation /oc-macsec:macsec/oc-macsec:mka/oc-macsec:state/oc-macsec:counters/oc-macsec:in-mkpdu-icv-verification-errors {
    deviate not-supported;
  }

  deviation /oc-macsec:macsec/oc-macsec:mka/oc-macsec:state/oc-macsec:counters/oc-macsec:in-mkpdu-validation-errors {
    deviate not-supported;
  }

  deviation /oc-macsec:macsec/oc-macsec:mka/oc-macsec:state/oc-macsec:counters/oc-macsec:in-mkpdu-bad-peer-errors {
    deviate not-supported;
  }

  deviation /oc-macsec:macsec/oc-macsec:mka/oc-macsec:state/oc-macsec:counters/oc-macsec:in-mkpdu-peer-list-errors {
    deviate not-supported;
  }

  deviation /oc-macsec:macsec/oc-macsec:mka/oc-macsec:state/oc-macsec:counters/oc-macsec:sak-generation-errors {
    deviate not-supported;
  }

  deviation /oc-macsec:macsec/oc-macsec:mka/oc-macsec:state/oc-macsec:counters/oc-macsec:sak-hash-errors {
    deviate not-supported;
  }

  deviation /oc-macsec:macsec/oc-macsec:mka/oc-macsec:state/oc-macsec:counters/oc-macsec:sak-encryption-errors {
    deviate not-supported;
  }

  deviation /oc-macsec:macsec/oc-macsec:mka/oc-macsec:state/oc-macsec:counters/oc-macsec:sak-decryption-errors {
    deviate not-supported;
  }

  deviation /oc-macsec:macsec/oc-macsec:mka/oc-macsec:state/oc-macsec:counters/oc-macsec:sak-cipher-mismatch-errors {
    deviate not-supported;
  }

  deviation /oc-macsec:macsec/oc-macsec:interfaces/oc-macsec:interface/oc-macsec:config/oc-macsec:enable {
    deviate not-supported;
  }

  deviation /oc-macsec:macsec/oc-macsec:interfaces/oc-macsec:interface/oc-macsec:config/oc-macsec:replay-protection {
    deviate not-supported;
  }

  deviation /oc-macsec:macsec/oc-macsec:interfaces/oc-macsec:interface/oc-macsec:state/oc-macsec:enable {
    deviate not-supported;
  }

  deviation /oc-macsec:macsec/oc-macsec:interfaces/oc-macsec:interface/oc-macsec:state/oc-macsec:replay-protection {
    deviate not-supported;
  }

  deviation /oc-macsec:macsec/oc-macsec:interfaces/oc-macsec:interface/oc-macsec:scsa-tx/oc-macsec:scsa-tx/oc-macsec:state/oc-macsec:counters/oc-macsec:sc-auth-only {
    deviate not-supported;
  }

  deviation /oc-macsec:macsec/oc-macsec:interfaces/oc-macsec:interface/oc-macsec:scsa-tx/oc-macsec:scsa-tx/oc-macsec:state/oc-macsec:counters/oc-macsec:sa-auth-only {
    deviate not-supported;
  }


}
//total deviations:21
