module Cisco-IOS-XR-mpls-vpn-cfg {
  namespace "http://cisco.com/ns/yang/Cisco-IOS-XR-mpls-vpn-cfg";
  prefix mpls-vpn-cfg;

  import cisco-semver {
    prefix semver;
  }
  import Cisco-IOS-XR-snmp-agent-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR mpls-vpn package configuration.
     
     This model is deprecated and is replaced by
     Cisco-IOS-XR-um-mpls-l3vpn-cfg.yang which will provide the
     compatible functionalities.
     
     This YANG module augments the
       Cisco-IOS-XR-snmp-agent-cfg
     module with configuration data.
     
     Copyright (c) 2013-2019 by Cisco Systems, Inc.
     All rights reserved.";

  revision 2019-05-12 {
    description
      "Deprecated the native model, replaced by UM model.";
    semver:module-version "1.0.1";
  }
  revision 2019-04-05 {
    description
      "Establish semantic version baseline.";
  }
  revision 2017-09-07 {
    description
      "Fixed type translation error.";
  }
  revision 2015-11-09 {
    description
      "IOS XR 6.0 revision.";
  }

  augment "/a1:snmp/a1:notification" {
    description
      "This augment extends the configuration data of
       'Cisco-IOS-XR-snmp-agent-cfg'";
    container mpls-l3vpn {
      status deprecated;
      description
        "This model is deprecated and is replaced by
         Cisco-IOS-XR-um-mpls-l3vpn-cfg.yang which will
         provide the compatible functionalities.
         MPLS-L3VPN-STD-MIB notification configuration";
      leaf max-threshold-reissue-notification-time {
        type uint32;
        units "second";
        description
          "Time interval (secs) for re-issuing
           max-threshold notification";
      }
      leaf max-threshold-exceeded {
        type empty;
        description
          "Enable mplsL3VpnVrfNumVrfRouteMaxThreshExceeded
           notification";
      }
      leaf max-threshold-cleared {
        type empty;
        description
          "Enable mplsL3VpnNumVrfRouteMaxThreshCleared
           notification";
      }
      leaf mid-threshold-exceeded {
        type empty;
        description
          "Enable mplsL3VpnVrfRouteMidThreshExceeded
           notification";
      }
      leaf enable {
        type empty;
        description
          "Enable mplsL3VpnMIB notifications";
      }
      leaf vrf-down {
        type empty;
        description
          "Enable mplsL3VpnVrfDown notification";
      }
      leaf vrf-up {
        type empty;
        description
          "Enable mplsL3VpnVrfUp notification";
      }
    }
  }
}
