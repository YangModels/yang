submodule Cisco-IOS-XR-asr9k-fab-health-oper-sub1 {
  belongs-to Cisco-IOS-XR-asr9k-fab-health-oper {
    prefix Cisco-IOS-XR-asr9k-fab-health-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR asr9k-fab-health package operational data.
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  grouping FAB-HEALTH-SPINE {
    description
      "FAB HEALTH SPINE";
    leaf fc-num {
      type uint8;
      description
        "fc num";
    }
    list fc-xbar-info {
      max-elements "2";
      description
        "fc xbar info";
      uses FAB-HEALTH-EDM-INFO;
    }
  }

  grouping FAB-HEALTH-FABMGR-FIA-STATUS {
    description
      "FAB HEALTH FABMGR FIA STATUS";
    leaf fia {
      type uint8;
      description
        "FIA Instance";
    }
    leaf fabmgr-fia-status {
      type string;
      description
        "FIA Status";
    }
  }

  grouping FAB-HEALTH-FABMGR {
    description
      "FAB HEALTH FABMGR";
    leaf slot {
      type uint8;
      description
        "slot";
    }
    list fia-status {
      max-elements "10";
      description
        "fia status";
      uses FAB-HEALTH-FABMGR-FIA-STATUS;
    }
    list alarm-info {
      max-elements "10";
      description
        "alarm info";
      uses FAB-HEALTH-ALARM-INFO;
    }
  }

  grouping FAB-HEALTHCREDIT-RECORD {
    description
      "FAB HEALTHCREDIT RECORD";
    leaf ldi {
      type uint8;
      description
        "ldi";
    }
    leaf cl {
      type uint8;
      description
        "cl";
    }
    leaf credits {
      type uint8;
      description
        "credits";
    }
    leaf vqi {
      type uint32;
      description
        "vqi";
    }
    leaf is-bel {
      type boolean;
      description
        "is bel";
    }
  }

  grouping FAB-HEALTHEDM-CREDITS {
    description
      "FAB HEALTHEDM CREDITS";
    leaf mode {
      type boolean;
      description
        "mode";
    }
    leaf pg {
      type uint8;
      description
        "pg";
    }
    list credit-record {
      max-elements "384";
      description
        "credit record";
      uses FAB-HEALTHCREDIT-RECORD;
    }
  }

  grouping FAB-HEALTHQDEPTH-RECORD {
    description
      "FAB HEALTHQDEPTH RECORD";
    leaf vqi {
      type uint32;
      description
        "vqi";
    }
    leaf cl {
      type uint8;
      description
        "cl";
    }
    leaf count {
      type uint8;
      description
        "count";
    }
  }

  grouping FAB-HEALTHEDM-QDEPTH {
    description
      "FAB HEALTHEDM QDEPTH";
    leaf mode {
      type boolean;
      description
        "mode";
    }
    list qdepth {
      max-elements "96";
      description
        "qdepth";
      uses FAB-HEALTHQDEPTH-RECORD;
    }
  }

  grouping FAB-HEALTH-STUCK-VQI {
    description
      "FAB HEALTH STUCK VQI";
    container qdepth-stats {
      description
        "qdepth stats";
      uses FAB-HEALTHEDM-QDEPTH;
    }
    container credits {
      description
        "credits";
      uses FAB-HEALTHEDM-CREDITS;
    }
  }

  grouping FAB-HEALTH-ALARM-INFO {
    description
      "FAB HEALTH ALARM INFO";
    leaf present {
      type boolean;
      description
        "present";
    }
    leaf alarm-name {
      type string;
      description
        "alarm name";
    }
    leaf last-ts {
      type string;
      description
        "last ts";
    }
  }

  grouping FAB-HEALTH-COUNTERS {
    description
      "FAB HEALTH COUNTERS";
    leaf from-counter {
      type uint64;
      description
        "from counter";
    }
    leaf to-counter {
      type uint64;
      description
        "to counter";
    }
  }

  grouping FAB-HEALTH-EDM-INFO {
    description
      "FAB HEALTH EDM INFO";
    container s1-counters {
      description
        "s1 counters";
      uses FAB-HEALTH-COUNTERS;
    }
    container s2-counters {
      description
        "s2 counters";
      uses FAB-HEALTH-COUNTERS;
    }
    container s3-counters {
      description
        "s3 counters";
      uses FAB-HEALTH-COUNTERS;
    }
    container drop-counters {
      description
        "drop counters";
      uses FAB-HEALTH-COUNTERS;
    }
    container s1-mc-counters {
      description
        "s1 mc counters";
      uses FAB-HEALTH-COUNTERS;
    }
    container s2-mc-counters {
      description
        "s2 mc counters";
      uses FAB-HEALTH-COUNTERS;
    }
    container s3-mc-counters {
      description
        "s3 mc counters";
      uses FAB-HEALTH-COUNTERS;
    }
    container drop-mc-counters {
      description
        "drop mc counters";
      uses FAB-HEALTH-COUNTERS;
    }
    leaf asic-inst {
      type uint8;
      description
        "asic inst";
    }
    leaf admin-state {
      type string;
      description
        "admin state";
    }
    leaf oper-state {
      type string;
      description
        "oper state";
    }
    leaf links-up {
      type uint8;
      description
        "links up";
    }
    leaf links-down {
      type uint8;
      description
        "links down";
    }
    leaf respawn-count {
      type uint32;
      description
        "respawn count";
    }
    leaf respawn-reason {
      type int32;
      description
        "respawn reason";
    }
    leaf proc-state {
      type int32;
      description
        "proc state";
    }
    leaf proc-exit-status {
      type int32;
      description
        "proc exit status";
    }
    list alarm-info {
      max-elements "50";
      description
        "alarm info";
      uses FAB-HEALTH-ALARM-INFO;
    }
  }

  grouping FAB-ALL-HEALTH-EDM-INFO {
    description
      "FAB ALL HEALTH EDM INFO";
    container arb-info {
      description
        "arb info";
      uses FAB-HEALTH-EDM-INFO;
    }
    container stuck-vqi-info {
      description
        "stuck vqi info";
      uses FAB-HEALTH-STUCK-VQI;
    }
    list xbar-info {
      max-elements "2";
      description
        "xbar info";
      uses FAB-HEALTH-EDM-INFO;
    }
    list fia-info {
      max-elements "10";
      description
        "fia info";
      uses FAB-HEALTH-EDM-INFO;
    }
    list fabmgr-info {
      max-elements "22";
      description
        "fabmgr info";
      uses FAB-HEALTH-FABMGR;
    }
    list fc-info {
      max-elements "7";
      description
        "fc info";
      uses FAB-HEALTH-SPINE;
    }
  }
}
