submodule Cisco-IOS-XR-feature-agent-oper-sub1 {
  belongs-to Cisco-IOS-XR-feature-agent-oper {
    prefix Cisco-IOS-XR-feature-agent-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR feature-agent package operational data.
     
     Copyright (c) 2013-2021 by Cisco Systems, Inc.
     All rights reserved.";

  revision 2021-06-16 {
    description
      "Fixed user permission";
    semver:module-version "1.0.0";
  }
  revision 2021-03-25 {
    description
      "IOS XR 7.05.01 version";
  }
  revision 2019-04-05 {
    description
      "Establish semantic version baseline.";
  }
  revision 2015-11-09 {
    description
      "IOS XR 6.0 revision.";
  }

  typedef Feature-capability-vc {
    type enumeration {
      enum "unknown" {
        description
          "Unknown";
      }
      enum "supported" {
        description
          "Boolean feature supported";
      }
      enum "unsupported" {
        description
          "Boolean feature unsupported";
      }
      enum "uint32" {
        description
          "Integer feature with uint32 support value";
      }
      enum "not-packaged" {
        description
          "Feature not packaged";
      }
      enum "no-data" {
        description
          "No data on feature support";
      }
      enum "no-data-for-optional-feature" {
        description
          "No feature support value data for the optional
           feature";
      }
      enum "unexpected-type" {
        description
          "Feature support value type mismatch with the
           definition";
      }
      enum "unexpected-value" {
        description
          "Feature support value from an unpackaged
           feature";
      }
      enum "unexpected-runtime-value" {
        description
          "Feature support value at runtime for a compile
           time feature";
      }
      enum "no-card" {
        description
          "Node scope feature with value on card not in
           inventory";
      }
      enum "unexpected" {
        description
          "Feature support value unexpected on card in its
           card class";
      }
      enum "unexpected-use" {
        description
          "Feature use value unexpected on card in its
           card class";
      }
      enum "not-relevant" {
        description
          "Feature support value not relevant on card";
      }
      enum "inconsistent" {
        description
          "Support value inconsistent";
      }
    }
    description
      "Feature capability vc";
  }

  typedef Feature {
    type enumeration {
      enum "unknown" {
        description
          "Unknown";
      }
      enum "boolean" {
        description
          "Boolean";
      }
      enum "integer" {
        description
          "Integer";
      }
    }
    description
      "Feature";
  }

  typedef Feature-scope {
    type enumeration {
      enum "unknown" {
        description
          "Unknown";
      }
      enum "system" {
        description
          "System";
      }
      enum "node" {
        description
          "Node";
      }
    }
    description
      "Feature scope";
  }

  grouping FEATURE-NODE {
    description
      "Per node feature information";
    container node-capability {
      description
        "Support value";
      uses FEATURE-CAPABILITY-SV;
    }
    leaf node-name {
      type string;
      description
        "Node name";
    }
  }

  grouping FEATURE-NS-CAPABILITY {
    description
      "Node scope capability";
    list nodes {
      description
        "Nodes";
      uses FEATURE-NODE;
    }
  }

  grouping FEATURE-INTEGER-SV {
    description
      "Integer feature support value";
    leaf classification {
      type Feature-capability-vc;
      description
        "Classification";
    }
    leaf value {
      when "../classification = 'uint32'" {
        description
          "../Classification = 'Uint32'";
      }
      type uint32;
      description
        "Integer Support Value";
    }
  }

  grouping FEATURE-CAPABILITY-SV {
    description
      "Feature support value";
    container integer-value {
      when "../type = 'integer'" {
        description
          "../Type = 'Integer'";
      }
      description
        "Integer Support value";
      uses FEATURE-INTEGER-SV;
    }
    leaf type {
      type Feature;
      description
        "Type";
    }
    leaf classification {
      when "../type = 'boolean'" {
        description
          "../Type = 'Boolean'";
      }
      type Feature-capability-vc;
      description
        "Classification";
    }
  }

  grouping FEATURE-CAPABILITY {
    description
      "Feature Capability";
    container system-capability {
      when "../scope = 'system'" {
        description
          "../Scope = 'System'";
      }
      description
        "Capability if system scope";
      uses FEATURE-CAPABILITY-SV;
    }
    container nodes-capability {
      when "../scope = 'node'" {
        description
          "../Scope = 'Node'";
      }
      description
        "Capability if node scope";
      uses FEATURE-NS-CAPABILITY;
    }
    leaf scope {
      type Feature-scope;
      description
        "Scope";
    }
  }

  grouping FEATURE {
    description
      "Feature";
    container capability {
      description
        "Feature Capability";
      uses FEATURE-CAPABILITY;
    }
    leaf name {
      type string;
      description
        "Feature name";
    }
    leaf description {
      type string;
      description
        "Feature description";
    }
    leaf parent-id {
      type string;
      description
        "ID of feature's parent";
    }
    leaf in-use {
      type boolean;
      description
        "Feature In Use";
    }
  }
}
