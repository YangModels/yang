module Cisco-IOS-XR-um-if-nve-cfg {
  namespace "http://cisco.com/ns/yang/Cisco-IOS-XR-um-if-nve-cfg";
  prefix um-if-nve-cfg;

  import Cisco-IOS-XR-types {
    prefix xr;
  }
  import ietf-inet-types {
    prefix inet;
  }
  import Cisco-IOS-XR-um-interface-cfg {
    prefix a1;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR if-nve package configuration.
     
     This YANG module augments the
     modules with configuration data.
     
     Copyright (c) 2021 by Cisco Systems, Inc.
     All rights reserved.";

  revision 2021-06-29 {
    description
      "Initial release";
    semver:module-version "1.0.0";
  }

  grouping IF-BODY {
    leaf source-interface {
      type xr:Interface-name;
      description
        "Configure source interface for Network Virtualization Endpoint";
    }
    container anycast {
      description
        "Configure anycast mode parameters for this VTEP";
      leaf source-interface {
        type xr:Interface-name;
        description
          "Configure source interface for the anycast mode";
      }
      leaf sync-group {
        type inet:ipv4-address-no-zone;
        must "../source-interface";
        description
          "Assign a BiDir multicast group for sync between anycast gateways";
      }
    }
    container member {
      description
        "Configure NVE member(s)";
      container vni {
        description
          "Configure member VxLAN Network Identfier";
        list vni-range {
          key "vni-start vni-end";
          description
            "Start of VNI range";
          leaf vni-start {
            type uint32 {
              range "1..16777215" {
                description
                  "Start of VNI range";
              }
            }
            description
              "Start of VNI range";
          }
          leaf vni-end {
            type uint32 {
              range "1..16777215" {
                description
                  "End of VNI range";
              }
            }
            description
              "End of VNI range";
          }
          container mcast-group {
            description
              "associate a multicast core group with VxLAN segment(s)";
            leaf start-address {
              type inet:ipv4-address-no-zone;
              must "../end-address";
              description
                "Start of mcast IP range";
            }
            leaf end-address {
              type inet:ipv4-address-no-zone;
              must "../start-address";
              description
                "End of mcast IP range";
            }
          }
          leaf vrf {
            type xr:Cisco-ios-xr-string {
              length "1..800" {
                description
                  "VRF name";
              }
            }
            description
              "Associate a VRF with VxLAN segment";
          }
          container host-reachability {
            description
              "Configure the control protocol for VxLAN tunnel endpoint reachability";
            container protocol {
              description
                "Configure the control protocol for VxLAN tunnel endpoint reachability";
              container bgp {
                presence "Indicates a bgp node is configured.";
                description
                  "Use BGP EVPN for VxLAN tunnel endpoint reachability";
              }
            }
          }
          container suppress-unknown-unicast-flooding {
            presence "Indicates a suppress-unknown-unicast-flooding node is configured.";
            description
              "Configure the suppression of unknown unicast flooding";
          }
          container load-balance {
            description
              "Configure load balance mode";
            container per-evi {
              presence "Indicates a per-evi node is configured.";
              description
                "Configure per-evi load balance mode (default is per-flow)";
            }
          }
        }
      }
    }
    container overlay-encapsulation {
      description
        "Configure encapsulation for Network Virtualization Endpoint";
      container vxlan {
        must "not(../soft-gre)";
        presence "Indicates a vxlan node is configured.";
        description
          "Configure VxLAN encapsulation for Network Virtualization Endpoint";
      }
      container soft-gre {
        must "not(../vxlan)";
        presence "Indicates a soft-gre node is configured.";
        description
          "Configure Soft GRE encapsulation for Network Virtualization Endpoint";
      }
    }
    container vxlan-udp-port {
      description
        "Configure UDP port number in VxLAN encapsulation";
      container port-4789 {
        must "not(../port-48879)";
        presence "Indicates a port-4789 node is configured.";
        description
          "IETF defined UDP port number for VxLAN";
      }
      container port-48879 {
        must "not(../port-4789)";
        presence "Indicates a port-48879 node is configured.";
        description
          "UDP port number for iVxLAN";
      }
    }
    container redundancy {
      presence "Indicates a redundancy node is configured.";
      description
        "Redundancy";
      container backbone {
        description
          "Configure ICCP backbone";
        container vxlan {
          presence "Indicates a vxlan node is configured.";
          description
            "ICCP VXLAN backbone";
          container iccp {
            description
              "Inter-Chassis Communication Protocol";
            leaf group {
              type uint32 {
                range "1..4294967295" {
                  description
                    "Enter group number";
                }
              }
              description
                "Configure ICCP group number";
            }
          }
        }
        container mpls {
          presence "Indicates a mpls node is configured.";
          description
            "ICCP MPLS backbone";
          container iccp {
            description
              "Inter-Chassis Communication Protocol";
            leaf group {
              type uint32 {
                range "1..4294967295" {
                  description
                    "Enter group number";
                }
              }
              description
                "Configure ICCP group number";
            }
          }
        }
      }
    }
    container ingress-replication {
      description
        "Configure ingress replication for VxLAN tunnel endpoint";
      container protocol {
        description
          "Configure the control protocol for VxLAN tunnel endpoint ingress replication";
        container bgp {
          presence "Indicates a bgp node is configured.";
          description
            "Use BGP EVPN for VxLAN tunnel endpoint ingress replication";
        }
      }
    }
  }

  augment "/a1:interfaces/a1:interface" {
    uses IF-BODY;
  }
  augment "/a1:interfaces/a1:interface-preconfigure" {
    uses IF-BODY;
  }
}
