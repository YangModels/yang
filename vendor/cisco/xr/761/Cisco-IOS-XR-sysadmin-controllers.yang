module Cisco-IOS-XR-sysadmin-controllers {
  namespace "http://www.cisco.com/ns/yang/Cisco-IOS-XR-sysadmin-controllers";
  prefix calvados_controllers;

  import Cisco-IOS-XR-sysadmin-fabric {
    prefix fabric;
  }
  import gaspp {
    prefix gaspp;
  }
  import fit {
    prefix fit;
  }
  import Cisco-IOS-XR-sysadmin-ethsw-esdma-cli {
    prefix esdma;
  }
  import ccc {
    prefix ccc;
  }
  import slice_control {
    prefix slice_control;
  }
  import zen {
    prefix zen;
  }
  import cisco-semver {
    prefix semver;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains a collection of YANG
     definitions for Cisco IOS-XR SysAdmin configuration.
     
     This module defines the top level container for
     all hardware devices managed in Sysadmin.
     
     Copyright (c) 2011-2020 by Cisco Systems, Inc.
     All rights reserved.";

  revision 2019-04-15 {
    description
      "Establish semantic version baseline.";
    semver:module-version "1.0.0";
  }
  revision 2017-01-31 {
    description
      "Changed the namespace and module name";
  }
  revision 2012-06-06 {
    description
      "Switched esdma_cli from being included as a yang file,
        to being imported. This allows esdma_cli to also be used
        by other top level modules for clear commands.";
  }
  revision 2012-01-20 {
    description
      "Added gaspp commands";
  }
  revision 2011-07-29 {
    description
      "Initial revision";
  }

  container gaspp {
    uses gaspp:gaspp;
  }
  container set {
    container controller {
      uses fit:fit-grp;
    }
  }
  container controller {
    uses fabric:fabric;
    uses gaspp:gaspp;
    uses slice_control:slice_control;
    uses zen:zen-grp;
    uses ccc:ccc-grp;
    container switch {
      uses esdma:switch;
    }
    uses fabric:fabric_action_cmds;
  }
}
