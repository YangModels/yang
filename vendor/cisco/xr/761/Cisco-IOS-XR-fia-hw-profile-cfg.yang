module Cisco-IOS-XR-fia-hw-profile-cfg {
  namespace "http://cisco.com/ns/yang/Cisco-IOS-XR-fia-hw-profile-cfg";
  prefix fia-hw-profile-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR fia-hw-profile package configuration.
     
     This module contains definitions
     for the following management objects:
       hw-module-profile-config: none
       hw-module-profile-config-npu: none
       hw-module-profile-config-oversubscription: none
       hw-module-profile-config-tcam: none
     
     Copyright (c) 2013-2022 by Cisco Systems, Inc.
     All rights reserved.";

  revision 2022-01-10 {
    description
      "Schema updated for qos nif prd allocation CLI.
       2021-11-09
         Add SRv6 L2/L3 config separation to encapsulation config. Add policy-map option to l3-traffic.
       2021-10-28
         Schema updated for qos stats push model CLI.";
    semver:module-version "5.0.0";
  }
  revision 2021-10-19 {
    description
      "Added functionality for L2PT extended protocol set
       2021-08-26
          Schema updated for support for match on ipv4/ipv6 destination address in L2 QOS database.
       2021-07-27
          Added functionality to disable Urpf
       2021-07-22
          Schema updated for Enabling and Disabling eTCAM LPTS profile CLI.
       2021-07-19
          Schema updated LoadBalanceProfile datatype changed to enum.
       2021-06-24
          Schema updated for QoS physical hqos profile CLI.
       2021-06-01
          Schema updated for ISIS/ARP priority";
    semver:module-version "4.0.0";
  }
  revision 2021-05-12 {
    description
      "Schema updated for sync between sysdb and schema for all platforms.
       2021-05-07
           Schema updated for QoS IPv6 short ETM profile CLI.
       2021-02-04
           Schema updated for native mode CLI.
       2020-09-18
           New leaf to specify routing profile as core
       2020-08-14
           SRV6 leaf deprecated and replaced by SRv6 Mode leaf
       2020-07-27
           Schema updated.
       2020-07-16
           Schema added.";
    semver:module-version "3.0.0";
  }
  revision 2020-04-30 {
    description
      "ACL UDK config changes: Added Common-ACL, replaced ProtType with NextHdr and Precedence with TraffClass
       2020-04-22
         SRV6 leaf deprecated and replaced by SRv6 Mode leaf
       2020-01-07
         Schema added.
       2020-01-05
         MGBL Sync config missmatch.";
    semver:module-version "2.0.0";
  }
  revision 2019-04-05 {
    description
      "Establish semantic version baseline.";
    semver:module-version "1.1.0";
  }
  revision 2016-06-22 {
    description
      "Schema added.";
  }
  revision 2015-11-09 {
    description
      "IOS XR 6.0 revision.";
  }

  typedef Data-plane {
    type enumeration {
      enum "all-dp" {
        value 0;
        description
          "All dataplanes";
      }
    }
    description
      "Data plane";
  }

  typedef Load-balance-profile {
    type enumeration {
      enum "layer2" {
        value 1;
        description
          "Layer 2 optimized";
      }
      enum "ip-tunnel" {
        value 2;
        description
          "IP tunnel optimized";
      }
      enum "mpls-safe-speculative-parsing" {
        value 3;
        description
          "MPLS safe Speculative parsing";
      }
      enum "gtp" {
        value 4;
        description
          "GTP optimized";
      }
      enum "l3-only" {
        value 5;
        description
          "L3 Header only Hash";
      }
      enum "gtp-mpls" {
        value 6;
        description
          "GTP over MPLS optimized hash";
      }
      enum "pppoe" {
        value 7;
        description
          "PPPoE session based optimized hash and Reload
           is required for this option";
      }
    }
    description
      "Load balance profile";
  }

  typedef Srv6-traffic-class-l2 {
    type enumeration {
      enum "propagate" {
        value 2;
        description
          "Propagate traffic-class from incoming
           packet/frame";
      }
      enum "value" {
        value 3;
        description
          "Set traffic-class value";
      }
    }
    description
      "Srv6 traffic class l2";
  }

  typedef Srv6-mode {
    type enumeration {
      enum "base" {
        value 3;
        description
          "SRv6 base mode";
      }
      enum "micro-segment-f3216" {
        value 12;
        description
          "SRv6 32-bit block and 16-bit IDs";
      }
    }
    description
      "Srv6 mode";
  }

  typedef Plane-rack {
    type uint32 {
      range "0..15";
    }
    description
      "Plane rack";
  }

  typedef Router-role {
    type enumeration {
      enum "core" {
        value 3;
        description
          "Core router";
      }
    }
    description
      "Router role";
  }

  typedef Srv6-traffic-class-value {
    type uint32 {
      range "0..255";
    }
    description
      "Srv6 traffic class value";
  }

  typedef Qos-classmap-size {
    type enumeration {
      enum "max-classmap-size-2" {
        value 2;
        description
          "QOS classmap size 2";
      }
      enum "max-classmap-size-4" {
        value 4;
        description
          "QOS classmap size 4";
      }
      enum "max-classmap-size-8" {
        value 8;
        description
          "QOS classmap size 8";
      }
      enum "max-classmap-size-16" {
        value 16;
        description
          "QOS classmap size 16";
      }
      enum "base" {
        value 32;
        description
          "QOS default classmap size 32";
      }
    }
    description
      "Qos classmap size";
  }

  typedef Srv6-traffic-class-l3 {
    type enumeration {
      enum "propagate" {
        value 2;
        description
          "Propagate traffic-class from incoming packet";
      }
      enum "value" {
        value 3;
        description
          "Set traffic-class value";
      }
      enum "policy-map" {
        value 4;
        description
          "Set traffic-class by policy-map";
      }
    }
    description
      "Srv6 traffic class l3";
  }

  container hw-module-profile-config {
    description
      "none";
    container irb {
      description
        "Configure irb mod.";
      leaf mode-l3l2 {
        type uint32;
        description
          "irb mode L3-L2";
      }
      leaf mode-l2l3 {
        type uint32;
        description
          "irb mode L2-L3";
      }
    }
    container profile {
      description
        "Configure profile.";
      container routing {
        description
          "Configure the node's routing profile";
        container data-planes {
          description
            "Configure the routing profile for a specific
             dataplane";
          list data-plane {
            key "dataplane";
            description
              "Configure the dataplane type";
            leaf role {
              type Router-role;
              description
                "Configure the node's routing role";
            }
            leaf dataplane {
              type Data-plane;
              description
                "Dataplane type";
            }
          }
        }
      }
      container netflow {
        description
          "Configure Netflow profile.";
        container sflow-netflow-locations {
          description
            "none";
          list sflow-netflow-location {
            key "location-string";
            description
              "none";
            leaf location-string {
              type xr:Cisco-ios-xr-string;
              description
                "Location of NETFLOW config";
            }
            list sflow-netflow-location-leaf {
              key "location-id";
              description
                "none";
              leaf location-id {
                type uint32;
                description
                  "Location ID";
              }
              leaf enable-val {
                type uint32;
                mandatory true;
                description
                  "If Enabled set value to 65535";
              }
            }
          }
        }
        container ipfix-location-all {
          description
            "IPFIX315 Location All";
          leaf ipfix-location-all-leaf {
            type uint32;
            description
              "If Enabled set value to 65535";
          }
        }
        container sflow-location-all {
          description
            "SFLOW Location All";
          leaf sflow-location-all-leaf {
            type uint32;
            description
              "If Enabled set value to 65535";
          }
        }
        container fpc-netflow-locations {
          description
            "none";
          list fpc-netflow-location {
            key "location-string";
            description
              "none";
            leaf location-string {
              type xr:Cisco-ios-xr-string;
              description
                "Location of NETFLOW config";
            }
            list fpc-netflow-location-leaf {
              key "location-id";
              description
                "none";
              leaf location-id {
                type uint32;
                description
                  "Location ID";
              }
              leaf enable-val {
                type uint32;
                mandatory true;
                description
                  "If Enabled set value to 65535";
              }
            }
          }
        }
        container ipfix-netflow-locations {
          description
            "none";
          list ipfix-netflow-location {
            key "location-string";
            description
              "none";
            leaf location-string {
              type xr:Cisco-ios-xr-string;
              description
                "Location of NETFLOW config";
            }
            list ipfix-netflow-location-leaf {
              key "location-id";
              description
                "none";
              leaf location-id {
                type uint32;
                description
                  "Location ID";
              }
              leaf enable-val {
                type uint32;
                mandatory true;
                description
                  "If Enabled set value to 65535";
              }
            }
          }
        }
        container fpc-location-all {
          description
            "FPC Location All";
          leaf fpc-location-all-leaf {
            type uint32;
            description
              "If Enabled set value to 65535";
          }
        }
      }
      container flowspec-table {
        description
          "Configure Flowspec profile.";
        container flowspecs {
          description
            "Configure v6 enable on Flowspec profile.";
          list flowspec {
            key "location-string location-id";
            description
              "none";
            leaf location-string {
              type xr:Cisco-ios-xr-string;
              description
                "Location of FLOWSPEC config";
            }
            leaf location-id {
              type uint32;
              description
                "Location ID hex to Decimal 65535";
            }
            leaf enable-val {
              type uint32;
              mandatory true;
              description
                "If Enabled set value to 1";
            }
          }
        }
      }
      container md-bprofile {
        description
          "Configure MDB profile.";
        leaf md-bprofile-type {
          type uint32;
          description
            "Configure MDB profile type";
        }
      }
      container bundle-hash {
        description
          "Configure Bundle Hash related parameters";
        container hash-index-locations {
          description
            "Bundle hash polynomial config";
          list hash-index-location {
            key "node-name";
            description
              "Bundle hash polynomial config location";
            leaf node-name {
              type xr:Cisco-ios-xr-string;
              description
                "NodeName";
            }
            list hash-index-location-leaf {
              key "location";
              description
                "Bundle hash polynomial config location leaf";
              leaf hash-index-location-leaf {
                type uint32;
                mandatory true;
                description
                  "Hash Index Location Leaf";
              }
              leaf location {
                type uint32;
                description
                  "Location";
              }
            }
          }
        }
        leaf per-pkt-round-robin {
          type boolean;
          description
            "bundlehash global per_pkt_round_robin mode";
        }
        leaf ignore-ing-port {
          type boolean;
          description
            "bundlehash ignore_ingress_port flag";
        }
      }
      container bgp-mp-pic {
        description
          "Configure bgp-mp-pic";
        leaf enable {
          type boolean;
          description
            "Enabled or disabled";
        }
      }
      container load-balance {
        description
          "Configure load balance parameters";
        leaf load-balance-profile {
          type Load-balance-profile;
          description
            "Configure load balance parameters";
        }
      }
      container stats {
        description
          "Configure stats";
        container stats-profile-modes {
          description
            "Configure stats for qos-enhanced, acl-permit
             and ingress-sr";
          list stats-profile-mode {
            key "counter-profile";
            description
              "Stats mode";
            leaf mode {
              type uint32;
              mandatory true;
              description
                "Stats Mode";
            }
            leaf counter-profile {
              type uint32;
              description
                "none";
            }
          }
        }
      }
      container segment-routing {
        description
          "Configure Segment Routing profile.";
        container srv6 {
          description
            "Configure SRv6 profile.";
          container encapsulation {
            description
              "Configure encapsulation related parameters";
            container traffic-l3 {
              description
                "Configure encapsulation related parameters
                 for l3-traffic type";
              container traffic-class-l3 {
                presence "Contains mandatory nodes that used to set default values";
                description
                  "Configure traffic-class field of SRv6 IPv6
                   header";
                leaf type {
                  type Srv6-traffic-class-l3;
                  description
                    "Traffic-class type";
                }
                leaf value {
                  type Srv6-traffic-class-value;
                  mandatory true;
                  description
                    "Traffic-class value";
                }
              }
            }
            container traffic-l2 {
              description
                "Configure encapsulation related parameters
                 for l2-traffic type";
              container traffic-class-l2 {
                presence "Contains mandatory nodes that used to set default values";
                description
                  "Configure traffic-class field of SRv6 IPv6
                   header";
                leaf type {
                  type Srv6-traffic-class-l2;
                  description
                    "Traffic-class type";
                }
                leaf value {
                  type Srv6-traffic-class-value;
                  mandatory true;
                  description
                    "Traffic-class value";
                }
              }
            }
          }
          leaf mode {
            type Srv6-mode;
            description
              "Enable SRv6 mode/profile";
          }
        }
      }
      container profile-acl {
        description
          "Configure acl profile";
        container acl-ingress-compress-enable-locations {
          description
            "ingress compress enable";
          list acl-ingress-compress-enable-location {
            key "location-string";
            description
              "none";
            leaf location-string {
              type xr:Cisco-ios-xr-string;
              description
                "Location of ACL config";
            }
            list acl-ingress-compress-enable-location-leaf {
              key "location-id";
              description
                "none";
              leaf location-id {
                type uint32;
                description
                  "Location ID";
              }
              leaf enable-val {
                type uint32;
                mandatory true;
                description
                  "If Enabled set value to 65535";
              }
            }
          }
        }
        container acl-ingress-compress-enable-location-all {
          description
            "ingress compress enable location all";
          leaf acl-ingress-compress-enable-location-all-leaf {
            type uint32;
            description
              "ingress compress enable location all";
          }
        }
        leaf egress {
          type boolean;
          description
            "Enabled or disabled";
        }
        leaf ipv6-ext-hdr {
          type boolean;
          description
            "IPv6 Extension Hdr Permit";
        }
      }
      container span-l2-filter {
        description
          "Configure span l2 traffic filter profile for
           DNS packet mirror filtering";
        leaf span-l2-filter-enable {
          type boolean;
          description
            "Enabled or disabled";
        }
      }
      container sr-policies {
        description
          "Configure IPV6 NULL label autopush for SR
           policy.";
        list sr-policy {
          key "null-label-autopush";
          description
            "none";
          leaf null-label-autopush {
            type xr:Cisco-ios-xr-string;
            description
              "none";
          }
          leaf enable-val {
            type uint32;
            mandatory true;
            description
              "If Enabled set value to 1";
          }
        }
      }
      container bundle-scale {
        description
          "Configure Bundle profile.";
        leaf trunk-size {
          type uint32;
          description
            "Configure Max Trunk Size";
        }
      }
      container offload {
        description
          "Configure offload profile for NCS5501-SE";
        leaf offload-profile {
          type uint32;
          description
            "Configure offload profile for NCS5501-SE";
        }
      }
      container igp-dlb {
        description
          "configure igp_dlb";
        leaf enable {
          type boolean;
          description
            "fib dlb level-1 value";
        }
      }
      container qos {
        description
          "Configure profile.";
        container hqos-enable-all {
          description
            "Configure Hqos profile";
          leaf hqos-enable {
            type uint32;
            description
              " Hqos profile value";
          }
        }
        container ingress-model-root-def {
          description
            "Configure Ingress Model Default";
          leaf ingress-model-leaf-def {
            type uint32;
            description
              "Ingress Model Default";
          }
        }
        container ipv6-short-etm-profile {
          description
            "Configure IPv6 short ETM profile";
          leaf ipv6-short-etm-profile-leaf {
            type boolean;
            description
              "IPv6 short ETM profile value";
          }
        }
        container ingress-models {
          description
            "Configure Ingress Model Root";
          list ingress-model {
            key "node-name";
            description
              "Configure Ingress Model";
            leaf node-name {
              type xr:Cisco-ios-xr-string;
              description
                "NodeName";
            }
            list ingress-model-leaf {
              key "location";
              description
                "Configure Ingress Model Leaf";
              leaf ingress-model-leaf {
                type uint32;
                mandatory true;
                description
                  "IngressModelLeaf";
              }
              leaf location {
                type uint32;
                description
                  "Location";
              }
            }
          }
        }
        container class-maps-root-def {
          description
            "Configure Class Maps Default";
          leaf class-map-size-def {
            type uint32;
            description
              "Class Map Size Default";
          }
        }
        container ecn-marking-stats-all {
          description
            "ecn marking stats value";
          leaf ecn-marking-stats {
            type uint32;
            description
              "EcnMarkingStats";
          }
        }
        container physical-hqos-enable-all {
          description
            "Configure physical intf Hqos profile";
          leaf physical-hqos-enable {
            type uint32;
            description
              " Physical Hqos profile value (enable:1)";
          }
        }
        container class-maps {
          description
            "Configure Class Map Root";
          list class-map {
            key "node-name";
            description
              "Configure Class Maps";
            leaf node-name {
              type xr:Cisco-ios-xr-string;
              description
                "NodeName";
            }
            list class-map-size {
              key "location";
              description
                "Class Map Size";
              leaf class-map-size {
                type Qos-classmap-size;
                mandatory true;
                description
                  "ClassMapSize";
              }
              leaf location {
                type uint32;
                description
                  "Location";
              }
            }
          }
        }
        container wred-stats-enable-all {
          description
            "wred stats enable";
          leaf wred-stats-enable {
            type uint32;
            description
              "WredStatsEnable";
          }
        }
        leaf qos-stats-push-model-enable {
          type uint32;
          description
            " Qos stats push model profile value";
        }
        leaf qos-nif-high-prio-fifo-reserve-percent {
          type uint32 {
            range "0..100";
          }
          units "percentage";
          description
            "Percentage to reserve NIF FIFO for High
             Priority packets";
        }
      }
      container oam {
        description
          "Configure oam sat profile.";
        leaf cfm-maid-enable {
          type boolean;
          description
            "Oam CFM Maid enable value";
        }
        leaf sat-enable {
          type boolean;
          description
            "Oam SAT enable value";
        }
      }
    }
    container storm-control-combine-policer-bw {
      description
        "Configure strorm control profile.";
      leaf enable {
        type boolean;
        description
          "Enabled or disabled";
      }
    }
    container fib-scale {
      description
        "Configure Fib for Scale for noTcam LC.";
      container ipv6-unicast-scale-no-tcam {
        description
          "IPv6 table for NOTCAM LC Scale.";
        container scale-ipv6-no-tcam {
          description
            "Scale for IPv6 table for NoTCAM LC.";
          leaf internet-optimized-ipv6-no-tcam {
            type string;
            description
              "Internet-optimized Scale for IPv6 table for
               NoTCAM LC.";
          }
        }
      }
      container ipv4-unicast-scale-no-tcam {
        description
          "IPv4 table for NOTCAM LC Scale.";
        container scale-ipv4-no-tcam {
          description
            "Scale for IPv4 table for NoTCAM LC.";
          leaf optimized-ipv4-no-tcam {
            type string;
            description
              "Optimized Scale for IPv4 table for NoTCAM LC.";
          }
        }
      }
    }
    container fib-table {
      description
        "Configure FIB profile.";
      container service-over-rsvptes {
        description
          "Recycle traffic for BGP services going over
           RSVP TE transport";
        list service-over-rsvpte {
          key "service-over-rsvpte";
          description
            "none";
          leaf service-over-rsvpte {
            type xr:Cisco-ios-xr-string;
            description
              "none";
          }
          leaf enable-val {
            type uint32;
            mandatory true;
            description
              "If Enabled set value to 1";
          }
        }
      }
      container urpf {
        description
          "Configure Urpf disable";
        leaf urpf-disable {
          type boolean;
          description
            "Enabled or disabled";
        }
      }
    }
    container orchestrated-linecard-reload {
      description
        "Configure OLR.";
      container plane-table-entries {
        description
          "Plane type";
        list plane-table-entry {
          key "plane-name";
          description
            "Plane : A or B";
          container rack-table-entries {
            description
              "Rack Information";
            list rack-table-entry {
              key "rack-num";
              description
                "Rack Number";
              leaf nodes-list {
                type string;
                description
                  "Please enter linecards separated via comma
                   eg 0,3,6,11,13";
              }
              leaf rack-num {
                type Plane-rack;
                description
                  "Rack Number";
              }
            }
          }
          leaf plane-name {
            type xr:Cisco-ios-xr-string;
            description
              "Plane Name";
          }
        }
      }
    }
    container vrrp-scale {
      description
        "Configure vrrpscale profile.";
      leaf enable {
        type boolean;
        description
          "vrrpscale profile value";
      }
    }
    container multicast {
      description
        "Configure multicast properties.";
      leaf mode-multicast-l3l2 {
        type uint32;
        description
          "access pw enable with irb mode Mcast L3-L2";
      }
    }
    container qosqppb {
      description
        "Configure profile.";
      container ipv6-scale {
        description
          "Configure IPv6 destination short profile";
        leaf ipv6-short {
          type boolean;
          description
            "ipv6 short profile value";
        }
      }
      leaf conform-aware-policer {
        type boolean;
        description
          "Configure Conform Aware Policer mode";
      }
      leaf gre-exp-cls {
        type boolean;
        description
          "Enable EXP classification for MPLSoGRE";
      }
      leaf l2-match-destination-address-ipv4-ipv6 {
        type boolean;
        description
          "Enable L2 match dest address feature";
      }
      leaf arp-isis-priority {
        type boolean;
        description
          "Enable ARP/ISIS priority";
      }
    }
    container gue {
      description
        "Configure gue udp port";
      container udp {
        description
          "Configure udp port number";
        leaf ipv4 {
          type uint32 {
            range "0..64000";
          }
          description
            "Configure udp dest port for ipv4, 0 will set
             to default";
        }
        leaf mpls {
          type uint32 {
            range "0..64000";
          }
          description
            "Configure udp dest port for mpls, , 0 will set
             to default";
        }
        leaf ipv6 {
          type uint32 {
            range "0..64000";
          }
          description
            "Configure udp dest port for ipv6, 0 will set
             to default";
        }
      }
    }
  }
  container hw-module-profile-config-npu {
    description
      "none";
    container profile-npu {
      description
        "Configure profile.";
      container npu-native-mode-enable {
        description
          "Configure NPU to work in Native Mode.";
        leaf enable {
          type boolean;
          description
            "NPU Native Mode Enable value";
        }
      }
    }
  }
  container hw-module-profile-config-oversubscription {
    description
      "none";
    container oversub-interfaces {
      description
        "Configure Oversubscription.";
      list oversub-interface {
        key "interface-name";
        description
          "Oversubscription Interface.";
        leaf interface-name {
          type xr:Cisco-ios-xr-string;
          description
            "InterfaceName";
        }
        list cos-value {
          key "cosvalue";
          description
            "Configured cos";
          leaf enable {
            type uint32;
            description
              "Enabled/Disabled";
          }
          leaf cosvalue {
            type uint32;
            description
              "cosvalue";
          }
        }
      }
    }
  }
  container hw-module-profile-config-tcam {
    description
      "none";
    container tcam {
      description
        "Configure Tcam.";
      container fib-tcam-scale {
        description
          "Configure Fib scale for Tcam.";
        container ipv4-unicast-scale {
          description
            "IPv4 table for TCAM LC Scale.";
          leaf ipv4-scale {
            type boolean;
            description
              "Scale for IPv4 table for TCAM LC.";
          }
        }
      }
    }
    container profile-tcam {
      description
        "Configure Tcam profile.";
      container tcam-table {
        description
          "Configure profile for TCAM LC cards";
        container fib-table {
          description
            "FIB table for TCAM LC cards";
          container ipv4-address {
            description
              "IPv4 table for TCAM LC cards";
            container ipv4-unicast {
              description
                "Unicast table for TCAM LC cards";
              container ipv4-unicast-prefix-lengths {
                description
                  "IPv4 Unicast prefix ";
                list ipv4-unicast-prefix-length {
                  key "prefix-length";
                  description
                    "IPv4 Unicast prefix length";
                  leaf ipv4-unicast-prefix-percent {
                    type string;
                    units "percentage";
                    description
                      "curve out percentage of TCAM table
                       entries";
                  }
                  leaf prefix-length {
                    type uint32 {
                      range "0..32";
                    }
                    description
                      "prefix length";
                  }
                }
              }
              leaf ipv4-unicast-percent {
                type uint32 {
                  range "0..100";
                }
                units "percentage";
                description
                  "curve out percentage of TCAM table entries";
              }
            }
          }
          container ipv6-address {
            description
              "IPv6 table for TCAM LC cards";
            container ipv6-unicast {
              description
                "Unicast table for TCAM LC cards";
              container ipv6-unicast-prefix-lengths {
                description
                  "IPv6 Unicast prefix ";
                list ipv6-unicast-prefix-length {
                  key "prefix-length";
                  description
                    "IPv6 Unicast prefix length";
                  leaf ipv6-unicast-prefix-percent {
                    type string;
                    units "percentage";
                    description
                      "curve out percentage of TCAM table
                       entries";
                  }
                  leaf prefix-length {
                    type uint32 {
                      range "0..128";
                    }
                    description
                      "prefix length";
                  }
                }
              }
              leaf ipv6-unicast-percent {
                type uint32 {
                  range "0..100";
                }
                units "percentage";
                description
                  "curve out percentage of TCAM table entries";
              }
            }
          }
        }
        container acl-prefix {
          description
            "ACL table to configure";
          leaf acl-prefix-percent {
            type uint32 {
              range "0..100";
            }
            units "percentage";
            description
              "Percent to configure";
          }
        }
        leaf lpts-internal {
          type boolean;
          description
            "Switch to internal TCAM";
        }
      }
      container profile-tcam-key {
        description
          "Configure Tcam Profile";
        container key-format {
          description
            "none";
          container key-format-acl-table {
            description
              "Configure acl profile";
            container ipv6-acl-tables {
              description
                "Configure ipv6 acl profile";
              list ipv6-acl-table {
                key "location-string location-id";
                description
                  "Configure format for ipv6 acl profile";
                leaf location-string {
                  type xr:Cisco-ios-xr-string;
                  description
                    "Location string (all) if for all LCs";
                }
                leaf location-id {
                  type uint32;
                  description
                    "Location ID hex to Decimal 0xffff for all";
                }
                leaf source-addr {
                  type uint32;
                  description
                    "Source Address";
                }
                leaf source-port {
                  type uint32;
                  description
                    "Source Port";
                }
                leaf destination-addr {
                  type uint32;
                  description
                    "Destination Address";
                }
                leaf dest-port {
                  type uint32;
                  description
                    "Destination Port";
                }
                leaf next-hdr {
                  type uint32;
                  description
                    "Next Header Type";
                }
                leaf tcp-flag {
                  type uint32;
                  description
                    "TCP Flags";
                }
                leaf payload-len {
                  type uint32;
                  description
                    "Payload Length";
                }
                leaf traff-class {
                  type uint32;
                  description
                    "Traffic Class";
                }
                leaf frag-bit {
                  type uint32;
                  description
                    "Fragment Bit";
                }
                leaf udf1 {
                  type string;
                  description
                    "UDF name";
                }
                leaf udf2 {
                  type string;
                  description
                    "UDF name";
                }
                leaf udf3 {
                  type string;
                  description
                    "UDF name";
                }
                leaf udf4 {
                  type string;
                  description
                    "UDF name";
                }
                leaf udf5 {
                  type string;
                  description
                    "UDF name";
                }
                leaf udf6 {
                  type string;
                  description
                    "UDF name";
                }
                leaf udf7 {
                  type string;
                  description
                    "UDF name";
                }
                leaf udf8 {
                  type string;
                  description
                    "UDF name";
                }
                leaf en-capture {
                  type uint32;
                  description
                    "Enable Capture";
                }
                leaf en-ttl {
                  type uint32;
                  description
                    "Enable Setting TTL";
                }
                leaf en-match {
                  type uint32;
                  description
                    "Enable Matching TTL";
                }
                leaf en-share-acl {
                  type uint32;
                  description
                    "Enable Non Shared Interface ACL";
                }
                leaf common-acl {
                  type uint32;
                  description
                    "Enable Common-ACL";
                }
              }
            }
            container ipv4-acl-tables {
              description
                "Configure ipv4 acl profile";
              list ipv4-acl-table {
                key "location-string location-id";
                description
                  "Configure format for ipv4 acl profile";
                leaf location-string {
                  type xr:Cisco-ios-xr-string;
                  description
                    "Location string (all) if for all LCs";
                }
                leaf location-id {
                  type uint32;
                  description
                    "Location ID hex to Decimal 0xffff for all";
                }
                leaf source-addr {
                  type uint32;
                  description
                    "Source Address";
                }
                leaf destination-addr {
                  type uint32;
                  description
                    "Destination Address";
                }
                leaf source-port {
                  type uint32;
                  description
                    "Source Port";
                }
                leaf dest-port {
                  type uint32;
                  description
                    "Destination Port";
                }
                leaf prot-type {
                  type uint32;
                  description
                    "Protocol Type";
                }
                leaf tcp-flag {
                  type uint32;
                  description
                    "TCP Flags";
                }
                leaf pack-len {
                  type uint32;
                  description
                    "Packet Length";
                }
                leaf frag-bit {
                  type uint32;
                  description
                    "Fragment Bit";
                }
                leaf precedence {
                  type uint32;
                  description
                    "Precedence";
                }
                leaf port-range {
                  type uint32;
                  description
                    "PortRange";
                }
                leaf udf1 {
                  type string;
                  description
                    "UDF name";
                }
                leaf udf2 {
                  type string;
                  description
                    "UDF name";
                }
                leaf udf3 {
                  type string;
                  description
                    "UDF name";
                }
                leaf udf4 {
                  type string;
                  description
                    "UDF name";
                }
                leaf udf5 {
                  type string;
                  description
                    "UDF name";
                }
                leaf udf6 {
                  type string;
                  description
                    "UDF name";
                }
                leaf udf7 {
                  type string;
                  description
                    "UDF name";
                }
                leaf udf8 {
                  type string;
                  description
                    "UDF name";
                }
                leaf en-capture {
                  type uint32;
                  description
                    "Enable Capture";
                }
                leaf en-ttl {
                  type uint32;
                  description
                    "Enable Setting TTL";
                }
                leaf en-match {
                  type uint32;
                  description
                    "Enable Matching TTL";
                }
                leaf en-share-acl {
                  type uint32;
                  description
                    "Enable Non Shared Interface ACL";
                }
                leaf common-acl {
                  type uint32;
                  description
                    "Enable Common-ACL";
                }
              }
            }
          }
        }
      }
    }
  }
}
