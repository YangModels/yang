module Cisco-IOS-XR-um-ssm-cfg {
  namespace "http://cisco.com/ns/yang/Cisco-IOS-XR-um-ssm-cfg";
  prefix um-ssm-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ssm package configuration.
     
     This YANG module augments the
     modules with configuration data.
     
     Copyright (c) 2020-2021 by Cisco Systems, Inc.
     All rights reserved.";

  revision 2021-01-18 {
    description
      "Initial release";
    semver:module-version "1.0.0";
  }

  container ssm {
    description
      "service availability specific commands";
    container monitor {
      description
        "enabling/disabling monitoring at a SDR scope";
      container service {
        description
          "service availability";
        container disable {
          presence "Indicates a disable node is configured.";
          description
            "stop";
        }
      }
    }
  }
}
