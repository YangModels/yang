module Cisco-IOS-XR-install-augmented-act {
  namespace "http://cisco.com/ns/yang/Cisco-IOS-XR-install-augmented-act";
  prefix install-augmented-act;

  import cisco-semver {
    prefix semver;
  }
  import Cisco-IOS-XR-types {
    prefix csc;
  }
  import Cisco-IOS-XR-install-act {
    prefix install-act;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a augmented collection of YANG definitions for Cisco
     IOS-XR install actions, and should be used along with
     Cisco-IOS-XR-install-act.yang
     
     Copyright (c) 2016-2022 by Cisco Systems, Inc.
     All rights reserved.";

  revision 2021-09-28 {
    description
      "RFC 6020 section 12 and RFC 8407 sections 4.13,4.14 compliance
       2021-09-21
         Addition of force flag to package-abort";
    semver:module-version "3.3.0";
  }
  revision 2021-01-14 {
    description
      "Addition of force flag";
    semver:module-version "3.2.0";
  }
  revision 2020-08-03 {
    description
      "Modified tasks for the RPC operations.";
    semver:module-version "3.1.0";
  }
  revision 2020-03-06 {
    description
      "Removal of the install-reload-failed-nodes RPC
       2019-11-05
         Addition of INST-AUGMENTED-OP-ID-TYPE for the return type of action RPCs";
    semver:module-version "3.0.0";
  }
  revision 2019-10-03 {
    description
      "Move apply type enum to Cisco-IOS-XR-install-act.yang
       2019-10-01
         Made changes to be RFC6087 compliant
       2019-09-19
         Allow user to indicate apply-type at the beginning of an operation.";
    semver:module-version "2.0.0";
  }
  revision 2019-04-05 {
    description
      "Establish semantic version baseline.";
    semver:module-version "1.0.0";
  }
  revision 2018-10-05 {
    description
      "IOS XR 7.0.1 revision.";
  }

  typedef abort-type {
    type enumeration {
      enum "latest" {
        description
          "Abort the latest packaging operation";
      }
      enum "all-since-apply" {
        description
          "Abort all packaging operations since the last apply";
      }
    }
    description
      "abort type";
  }

  grouping INST-AUGMENTED-OP-ID-TYPE {
    description
      "Return type for triggered actions";
    leaf op-id {
      type string;
      description
        "operation id of the triggered action";
    }
  }

  rpc install-package-add {
    description
      "Add all packages in a specified source, or the given list of packages";
    input {
      container packages {
        description
          "List of packages to add, or empty to add all packages";
        leaf-list packagename {
          type string;
          description
            "package name";
        }
      }
      leaf source-type {
        type install-act:packages-source-type;
        default "any-configured-repository";
        description
          "Type of source used to obtain the packages";
      }
      leaf source {
        type string;
        description
          "Path to the location of the packages.  If source-type is
           'any-configured-repository' this field is unused, and if
           source-type is 'configured-repository' this should be the
           name of the repository to use.";
      }
      leaf force {
        type boolean;
        default "false";
        description
          "Ignore non-critical errors";
      }
    }
    output {
      uses INST-AUGMENTED-OP-ID-TYPE;
    }
    csc:xr-task "pkg-mgmt";
  }
  rpc install-package-remove {
    description
      "Remove the given list of packages";
    input {
      container packages {
        description
          "List of packages to remove";
        leaf-list packagename {
          type string;
          description
            "package name";
        }
      }
      leaf force {
        type boolean;
        default "false";
        description
          "Ignore non-critical errors";
      }
    }
    output {
      uses INST-AUGMENTED-OP-ID-TYPE;
    }
    csc:xr-task "pkg-mgmt";
  }
  rpc install-package-upgrade {
    description
      "Upgrade all packages, or the given list of packages";
    input {
      container packages {
        description
          "List of packages to upgrade, or empty to upgrade all packages";
        leaf-list packagename {
          type string;
          description
            "package name";
        }
      }
      leaf source-type {
        type install-act:packages-source-type;
        default "any-configured-repository";
        description
          "Type of source used to obtain the packages";
      }
      leaf source {
        type string;
        description
          "Path to the location of the packages.  If source-type is
           'any-configured-repository' this field is unused, and if
           source-type is 'configured-repository' this should be the
           name of the repository to use.";
      }
      leaf force {
        type boolean;
        default "false";
        description
          "Ignore non-critical errors";
      }
    }
    output {
      uses INST-AUGMENTED-OP-ID-TYPE;
    }
    csc:xr-task "pkg-mgmt";
  }
  rpc install-package-downgrade {
    description
      "Downgrade all packages in a specified source, or the given list of
       packages";
    input {
      container packages {
        description
          "List of packages to downgrade, or empty to downgrade all packages
           in a specified source";
        leaf-list packagename {
          type string;
          description
            "package name";
        }
      }
      leaf source-type {
        type install-act:packages-source-type;
        default "any-configured-repository";
        description
          "Type of source used to obtain the packages";
      }
      leaf source {
        type string;
        description
          "Path to the location of the packages.  If source-type is
           'any-configured-repository' this field is unused, and if
           source-type is 'configured-repository' this should be the
           name of the repository to use.";
      }
      leaf force {
        type boolean;
        default "false";
        description
          "Ignore non-critical errors";
      }
    }
    output {
      uses INST-AUGMENTED-OP-ID-TYPE;
    }
    csc:xr-task "pkg-mgmt";
  }
  rpc install-package-replace {
    description
      "Replace the current installed software";
    input {
      leaf config {
        type install-act:config-type;
        description
          "Action to take on any configuration present in the ISO";
      }
      leaf source-type {
        type install-act:replace-source-type;
        default "local";
        description
          "Type of source used to obtain the ISO";
      }
      leaf source {
        type string;
        mandatory true;
        description
          "Path to the location of the ISO";
      }
      leaf file {
        type string;
        mandatory true;
        description
          "Name of the ISO to install";
      }
      leaf force {
        type boolean;
        default "false";
        description
          "Ignore non-critical errors";
      }
    }
    output {
      uses INST-AUGMENTED-OP-ID-TYPE;
    }
    csc:xr-task "pkg-mgmt";
  }
  rpc install-package-rollback {
    description
      "Rollback the installed software to a previous revision";
    input {
      leaf transaction-id {
        type uint32;
        mandatory true;
        description
          "Transaction ID to rollback to";
      }
      leaf force {
        type boolean;
        default "false";
        description
          "Ignore non-critical errors";
      }
    }
    output {
      uses INST-AUGMENTED-OP-ID-TYPE;
    }
    csc:xr-task "pkg-mgmt";
  }
  rpc install-rollback {
    description
      "Rollback the installed software to a previous revision and apply the change";
    input {
      leaf transaction-id {
        type uint32;
        mandatory true;
        description
          "Transaction ID to rollback to";
      }
      leaf commit {
        type boolean;
        default "false";
        description
          "Commit at the end of the rollback operation, if the
           software is successfully applied";
      }
      leaf description {
        type string;
        description
          "Description to be stored for the transaction ID";
      }
      leaf activation-type {
        type install-act:apply-type;
        default "least-impactful";
        description
          "Activate the software using the specified apply type";
      }
      leaf force {
        type boolean;
        default "false";
        description
          "Ignore non-critical errors";
      }
    }
    output {
      uses INST-AUGMENTED-OP-ID-TYPE;
    }
    csc:xr-task "pkg-mgmt";
  }
  rpc install-apply {
    description
      "Apply atomic operation by restarting processes or reloading";
    input {
      leaf apply-method {
        type install-act:apply-type;
        mandatory true;
        description
          "Method of applying atomic operation";
      }
      leaf force {
        type boolean;
        default "false";
        description
          "Ignore non-critical errors";
      }
    }
    output {
      uses INST-AUGMENTED-OP-ID-TYPE;
    }
    csc:xr-task "pkg-mgmt";
  }
  rpc install-package-abort {
    description
      "Abort the specified packaging operation(s)";
    input {
      leaf abort-type {
        type abort-type;
        mandatory true;
        description
          "Which packaging operations to abort";
      }
      leaf force {
        type boolean;
        default "false";
        description
          "Ignore non-critical errors";
      }
    }
    output {
      uses INST-AUGMENTED-OP-ID-TYPE;
    }
    csc:xr-task "pkg-mgmt";
  }
  rpc install-label {
    description
      "Label a transaction ID with a description";
    input {
      leaf transaction-id {
        type uint32;
        description
          "Transaction ID to be labelled";
      }
      leaf description {
        type string;
        description
          "Description to be stored for the transaction ID";
      }
    }
  }
  rpc install-clear-rollback {
    description
      "Remove specified rollback points to save disk space";
    input {
      leaf transaction-id {
        type uint32;
        description
          "Transaction ID corresponding to the rollback point to be removed";
      }
      leaf number-of-oldest {
        type uint32;
        description
          "The number of oldest rollback points to be removed";
      }
    }
    csc:xr-task "pkg-mgmt";
  }
}
