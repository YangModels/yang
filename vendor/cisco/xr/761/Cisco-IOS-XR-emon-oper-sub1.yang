submodule Cisco-IOS-XR-emon-oper-sub1 {
  belongs-to Cisco-IOS-XR-emon-oper {
    prefix Cisco-IOS-XR-emon-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR emon package operational data.
     
     Copyright (c) 2013-2019 by Cisco Systems, Inc.
     All rights reserved.";

  revision 2019-04-05 {
    description
      "Establish semantic version baseline.";
    semver:module-version "1.0.0";
  }
  revision 2019-03-08 {
    description
      "and entry for show controller switch bridge";
  }
  revision 2019-03-01 {
    description
      "Rename esdma-oper to switch-oper, esdma-emon-oper to emon-oper";
  }
  revision 2019-02-07 {
    description
      "Rework clear and set operations.";
  }
  revision 2015-11-09 {
    description
      "IOS XR 6.0 revision.";
  }

  grouping ESDMA-SHOW-EMON-PATH-ENTRY {
    description
      "show ethernet EMON path entry";
    leaf path-name {
      type string {
        length "0..64";
      }
      description
        "Path name";
    }
    leaf tx-hb-packets {
      type uint64;
      description
        "Tx heartbeat packets";
    }
    leaf tx-hb-resp-packets {
      type uint64;
      description
        "Tx heartbeat response packets";
    }
    leaf rx-hb-packets {
      type uint64;
      description
        "Rx heartbeat packets";
    }
    leaf rx-hb-resp-packets {
      type uint64;
      description
        "Rx heartbeat response packets";
    }
    leaf rx-hb-resp-packet-misses {
      type uint64;
      description
        "Rx heartbeat response packet misses";
    }
    leaf rx-emon-stop-packets {
      type uint64;
      description
        "Rx EMON stop packets";
    }
    leaf rx-emon-fdb-flush-packets {
      type uint64;
      description
        "Rx EMON FDB flush packets";
    }
    leaf tx-emon-fdb-flush-packets {
      type uint64;
      description
        "Tx EMON FDB flush packets";
    }
  }

  grouping ESDMA-SHOW-EMON-CARD-ENTRY {
    description
      "show ethernet EMON card entry";
    leaf remote-card {
      type string {
        length "0..16";
      }
      description
        "Remote card name";
    }
    list emon-path-entry {
      description
        "EMON path entry";
      uses ESDMA-SHOW-EMON-PATH-ENTRY;
    }
  }

  grouping ESDMA-SHOW-EMON-STATS-INFO {
    description
      "show ethernet EMON statistics info";
    leaf local-card {
      type string {
        length "0..16";
      }
      description
        "Local card name";
    }
    list emon-card-entry {
      description
        "EMON card entry";
      uses ESDMA-SHOW-EMON-CARD-ENTRY;
    }
  }
}
