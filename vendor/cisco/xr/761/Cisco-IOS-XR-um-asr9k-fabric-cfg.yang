module Cisco-IOS-XR-um-asr9k-fabric-cfg {
  namespace "http://cisco.com/ns/yang/Cisco-IOS-XR-um-asr9k-fabric-cfg";
  prefix um-asr9k-fabric-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR asr9k-fabric package configuration.
     
     This YANG module augments the
     modules with configuration data.
     
     Copyright (c) 2020 by Cisco Systems, Inc.
     All rights reserved.";

  revision 2020-06-25 {
    description
      "Initial release";
    semver:module-version "1.0.0";
  }

  feature classic-admin-config {
    description
      "Classic admin configuration supported";
  }

  container admin {
    if-feature "classic-admin-config";
    description
      "Admin configuration";
    container fabric {
      description
        "Configure Fabric";
      container enable {
        description
          "Enable fabric operation mode";
        container mode {
          description
            "Choose mode";
          container highbandwidth {
            must "not(../a99-highbandwidth)";
            presence "Indicates a highbandwidth node is configured.";
            description
              "High bandwidth cards only";
          }
          container a99-highbandwidth {
            must "not(../highbandwidth)";
            presence "Indicates a a99-highbandwidth node is configured.";
            description
              "A99 High bandwidth cards only";
          }
        }
      }
    }
  }
}
