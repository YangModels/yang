module Cisco-IOS-XR-olc-act {
  namespace "http://cisco.com/ns/yang/Cisco-IOS-XR-olc-act";
  prefix olc-act;

  import cisco-semver {
    prefix semver;
  }
  import Cisco-IOS-XR-types {
    prefix csc;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR olc-act package configuration.
     
     Copyright (c) 2013-2023 by Cisco Systems, Inc.
     All rights reserved.";

  revision 2023-06-19 {
    description
      "Added APC correction command";
  }
  revision 2023-05-12 {
    description
      "Added Otdr Raman Turn Up commands";
  }
  revision 2022-10-10 {
    description
      "Added BFR Initialize command";
  }
  revision 2022-06-22 {
    description
      "Added Gain Estimator commands";
  }
  revision 2021-11-19 {
    description
      "First revision, establish semantic version baseline";
    semver:module-version "1.0.0";
  }

  typedef ApcDirection {
    type enumeration {
      enum "Tx" {
        value 0;
        description
          "Tx Direction";
      }
      enum "Rx" {
        value 1;
        description
          "Rx Direction";
      }
    }
    description
      "APC direction type";
  }

  rpc start-raman-tuning {
    description
      "Start Raman Tuning";
    input {
      leaf controller {
        type string;
        description
          "Controller name in Ots  R/S/I/P format";
      }
    }
    csc:xr-task "root-lr";
    csc:cli-command "olc start-raman-tuning controller <controller>";
  }
  rpc start-gain-estimation {
    description
      "Start gain estimator";
    input {
      leaf controller {
        type string;
        description
          "Controller name in Ots R/S/I/P format";
      }
    }
    csc:xr-task "root-lr";
    csc:cli-command "olc start-gain-estimation controller <controller>";
  }
  rpc bfr-initialize {
    description
      "Initialize Band Failure and Recovery State Machine";
    input {
      leaf controller {
        type string;
        description
          "Controller name in Ots R/S/I/P format";
      }
    }
    csc:xr-task "root-lr";
    csc:cli-command "olc bfr-initialize controller <controller>";
  }
  rpc start-raman-turn-up {
    description
      "Start Raman Turn up";
    input {
      leaf controller {
        type string;
        description
          "Controller name in Ots R/S/I/P format";
      }
    }
    csc:xr-task "root-lr";
    csc:cli-command "olc start-raman-turn-up controller <controller>";
  }
  rpc force-raman-turn-up {
    description
      "Force Raman Turn up";
    input {
      leaf controller {
        type string;
        description
          "Controller name in Ots R/S/I/P format";
      }
    }
    csc:xr-task "root-lr";
    csc:cli-command "olc force-raman-turn-up controller <controller>";
  }
  rpc start-apc-correction {
    description
      "Start APC correction";
    input {
      leaf controller {
        type string;
        description
          "Controller name in Ots R/S/I/P format";
      }
      leaf direction {
        type ApcDirection;
        description
          "Tx/Rx direction";
      }
    }
    csc:xr-task "root-lr";
    csc:cli-command "olc start-apc-correction controller <controller> <direction>";
  }
  rpc alc-start-proc {
    description
      "Start ALC procedure";
    input {
      leaf controller {
        type string;
        description
          "Controller name in Ots R/S/I/P format";
      }
    }
    csc:xr-task "root-lr";
    csc:cli-command "olc alc-start controller <controller>";
  }
  rpc alc-terminate-proc {
    description
      "Stop ALC procedure";
    input {
      leaf controller {
        type string;
        description
          "Controller name in Ots R/S/I/P format";
      }
    }
    csc:xr-task "root-lr";
    csc:cli-command "olc alc-terminate controller <controller>";
  }
}
