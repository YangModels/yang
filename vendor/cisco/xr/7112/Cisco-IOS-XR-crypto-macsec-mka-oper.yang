module Cisco-IOS-XR-crypto-macsec-mka-oper {
  namespace "http://cisco.com/ns/yang/Cisco-IOS-XR-crypto-macsec-mka-oper";
  prefix crypto-macsec-mka-oper;

  import Cisco-IOS-XR-types {
    prefix xr;
  }
  import cisco-semver {
    prefix semver;
  }
  include Cisco-IOS-XR-crypto-macsec-mka-oper-sub1 {
    revision-date 2023-07-11;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR crypto-macsec-mka package operational data.
     
     This module contains definitions
     for the following management objects:
       macsec: Macsec operational data
     
     Copyright (c) 2013-2023 by Cisco Systems, Inc.
     All rights reserved.";

  revision 2023-07-11 {
    description
      "Added a detailed container along with Principal Actor and Traffic Status to Interface Info
       2023-05-19
         Added Policies Container for operational MACSec Policy info
       2022-04-28
         Added global MKPDU validation error stat
       2022-02-08
         Added Standby Container for MKA operational info";
    semver:module-version "3.0.0";
  }
  revision 2021-05-13 {
    description
      "Changed the latest SAK data field to last SAK
       2021-05-12
          Removed unwanted fields in CA bag for stats";
    semver:module-version "2.0.0";
  }
  revision 2021-04-15 {
    description
      "Modified to display session stats
       2021-02-17
           Modified to display port power status
       2021-01-19
           show_mka.bag dormant entry remove
       2020-08-24
           MKA PPK";
    semver:module-version "2.0.0";
  }
  revision 2019-05-27 {
    description
      "MKA ISSU";
    semver:module-version "1.1.0";
  }
  revision 2019-04-05 {
    description
      "MKA ISSU";
    semver:module-version "1.1.0";
  }
  revision 2015-11-09 {
    description
      "IOS XR 6.0 revision.";
  }

  container macsec {
    config false;
    description
      "Macsec operational data";
    container policies {
      description
        "List of MACSec Policies";
      list policy {
        key "name";
        description
          "MACSec Policy";
        container detail {
          description
            "MACsec Policy Detail";
          uses MKA-EDM-POLICY;
        }
        leaf name {
          type xr:Cisco-ios-xr-string {
            length "1..16";
          }
          description
            "Name of the Policy of maximum length 16";
        }
      }
    }
    container standby {
      description
        "MACsec Operational Data from Standby";
      container mka {
        description
          "MKA Operational info";
        container interfaces {
          description
            "MACsec enabled Interfaces";
          list interface {
            key "name";
            description
              "MKA Data for the Interface";
            container statistics {
              description
                "MKA Statistics Data";
              uses MKA-INTF-STATISTICS;
            }
            container info {
              description
                "MKA Interface Summary Data";
              uses MKA-INTERFACE-INFO;
            }
            container session {
              description
                "MKA Session Data";
              uses MKA-SESSION;
            }
            leaf name {
              type xr:Interface-name;
              description
                "Interface Name";
            }
          }
        }
      }
    }
    container mka {
      description
        "MKA Data";
      container interfaces {
        description
          "MKA Data";
        list interface {
          key "name";
          description
            "MKA Data for the Interface";
          container session {
            description
              "MKA Session Data";
            uses MKA-SESSION;
          }
          container statistics {
            description
              "MKA Statistics Data";
            uses MKA-INTF-STATISTICS;
          }
          container info {
            description
              "MKA Interface Summary Data";
            uses MKA-INTERFACE-INFO;
          }
          leaf name {
            type xr:Interface-name;
            description
              "Interface Name";
          }
        }
      }
    }
  }
}
