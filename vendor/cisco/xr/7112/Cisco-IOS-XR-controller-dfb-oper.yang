module Cisco-IOS-XR-controller-dfb-oper {
  namespace "http://cisco.com/ns/yang/Cisco-IOS-XR-controller-dfb-oper";
  prefix controller-dfb-oper;

  import Cisco-IOS-XR-types {
    prefix xr;
  }
  import cisco-semver {
    prefix semver;
  }
  include Cisco-IOS-XR-controller-dfb-oper-sub1 {
    revision-date 2023-09-08;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR controller-dfb package operational data.
     
     This module contains definitions
     for the following management objects:
       dfb-oper: Dfb operational data
     
     Copyright (c) 2013-2023 by Cisco Systems, Inc.
     All rights reserved.";

  revision 2023-09-08 {
    description
      "Added OSNR support for DFB controllers";
    semver:module-version "1.0.0";
  }
  revision 2020-10-16 {
    description
      "New Oper Model Added for Dfb Controller";
  }
  revision 2019-04-05 {
    description
      "Establish semantic version baseline.";
  }
  revision 2015-11-09 {
    description
      "IOS XR 6.0 revision.";
  }

  container dfb-oper {
    config false;
    description
      "Dfb operational data";
    container dfb-ports {
      description
        "All Dfb Port operational data";
      list dfb-port {
        key "name";
        description
          "Dfb operational data";
        container dfb-info {
          description
            "Dfb operational data";
          uses DFB-EDM-INFO;
        }
        leaf name {
          type xr:Interface-name;
          description
            "Port name";
        }
      }
    }
  }
}
