module Cisco-IOS-XR-infra-statsd-cfg {
  namespace "http://cisco.com/ns/yang/Cisco-IOS-XR-infra-statsd-cfg";
  prefix infra-statsd-cfg;

  import cisco-semver {
    prefix semver;
  }
  import Cisco-IOS-XR-ifmgr-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR infra-statsd package configuration.
     
     This module contains definitions
     for the following management objects:
       statistics: Global statistics configuration
     
     This YANG module augments the
       Cisco-IOS-XR-ifmgr-cfg
     module with configuration data.
     
     Copyright (c) 2013-2019 by Cisco Systems, Inc.
     All rights reserved.";

  revision 2019-04-05 {
    description
      "Establish semantic version baseline.";
    semver:module-version "1.0.1";
  }
  revision 2017-05-01 {
    description
      "Fixing backward compatibility error in module.";
  }
  revision 2015-11-09 {
    description
      "IOS XR 6.0 revision.";
  }

  augment "/a1:interface-configurations/a1:interface-configuration" {
    description
      "This augment extends the configuration data of
       'Cisco-IOS-XR-ifmgr-cfg'";
    container statistics {
      description
        "Per-interface statistics configuration";
      leaf load-interval {
        type uint32 {
          range "0..600";
        }
        default "300";
        description
          "Specify interval for load calculation for an
           interface";
      }
    }
  }
  container statistics {
    description
      "Global statistics configuration";
    container period {
      description
        "Collection period for statistics polling";
      container service-accounting {
        description
          "Collection polling period for service
           accounting collectors";
        leaf polling-period {
          type uint32 {
            range "30..3600";
          }
          must "not(../polling-disable)";
          description
            "Collection polling period for service
             accounting collectors";
        }
        leaf polling-disable {
          type empty;
          must "not(../polling-period)";
          description
            "Disable periodic statistics polling for
             service accounting collectors";
        }
      }
    }
  }
}
