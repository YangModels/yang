submodule Cisco-IOS-XR-infra-xtc-oper-sub2 {
  belongs-to Cisco-IOS-XR-infra-xtc-oper {
    prefix Cisco-IOS-XR-infra-xtc-oper;
  }

  import cisco-semver {
    prefix semver;
  }
  include Cisco-IOS-XR-infra-xtc-oper-sub1 {
    revision-date 2023-07-26;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR infra-xtc package operational data.
     
     Copyright (c) 2013-2023 by Cisco Systems, Inc.
     All rights reserved.";

  revision 2023-07-26 {
    description
      "Added protection type to BWoD sub-delegation.
       2023-07-04
         Add CPATH Name to cmn bag to display it using show pce lsp private command.
       2023-06-20
         Display override rule override for SID protection-type constraint.
       2023-05-04
         Display Flex-Algo information for P2MP policies.
       2023-04-27
         Add override rule override pcep advertise admin down when no path configure.
       2023-04-06
         Add a field to differentiate SRv6 path in path work group
       2023-03-30
         Changed work group operational data to use an ID based system as the key instead of a complex set of attributes.
       2023-03-21
         Added SID-algo in override rule
       2023-03-09
         Added protection type for path work group
       2023-03-06
         Updated PM CPath info and PM Stats bag
       2023-02-27
         Added fields to differentiate IPV4 or IPV6 TREESID policies
       2023-01-24
         Added fields for Flex-algo ASLA attributes on IPv4 and IPv6 links
       2023-01-18
         Updated description of flex-algo leaf to SID algorithm in cspf-sr-mpls.
       2022-11-11
         Added distribute-ls policy operational data.
       2022-10-20
         Added initiated tunnel operational information including PCE-INITIATED-TUN-BAG grouping.
       2022-09-01
         Added field to display p2mp rest initiated treeSID.
       2022-07-29
         changed default value of initial-verify-startup timer from 120 seconds to 180 seconds.
       2022-07-11
         Added leaves for blocked reoptimization and adjacency SID only
       2022-06-28
         Added weight outputs to srv6 nexthop and lsp sls.
       2022-06-02
         Removed prefix-metric entry from the topology node.
       2022-05-13
         TreeSID PCE HA, added few fields on oper commands
       2022-04-29
         Added some field in oper bag for Dynamic CS policies
       2022-04-26
         TreeSID PCE HA, oper enhancements
       2022-03-09
         Pce-sr-sid enum updated to add unknown-srv6sid element
       2022-03-03
         Modified description for override rules related leaves
       2022-03-03
         Added capability-srv6 in brief-pcep-information container
       2022-02-24
         Added PCE-BWOD-BEST-CLIENT-BAG and PCE-BWOD-SUB-DELEGATION-BAG grouping.
       2022-01-28
         Added maximum-delay in PCE-LSP-DETAIL-INFO grouping.
       2022-01-27
         Adding performance-statistics class
       2022-01-17
         Change the type of extended-value leaf from leaf-list to list.
       2022-01-14
         Added support for metric bounds for CSPF
       2022-01-10
         Added sid-algorithm and sid-algorithm-set in PCE-SIBLING-SYNCED-LSP-BAG grouping. Added sid-algorithm and sid-algorithm-set in PCE-LSP-DETAIL-INFO grouping.
       2022-01-07
         Added SID algorithm constraint to LSP.
       2021-12-14
         Moving algorithm and computation time in the path query results object
       2021-11-21
         Added prefix-metric entry in the topology node.
       2021-11-09
         Added unreliable flag and update drop count in topology summary bag.
       2021-10-21
         Adding algorithm and computation time to path query results
       2021-10-08
         Added support for override rules";
    semver:module-version "5.0.0";
  }
  revision 2021-09-28 {
    description
      "Added protection type set in candidate path constraints.
       2021-08-27
          Added binding-sid to pce sibling synced lsp.
       2021-06-21
          un-hide cspf-srv6 option in cspf srv6 path calculation.
       2021-05-26
          Added keys to topology-summary list.";
    semver:module-version "4.0.0";
  }
  revision 2021-04-22 {
    description
      "Added TE metric field for Flex-algo ASLA.
       2021-04-08
           Change protection type from integer to enum.
       2021-03-31
           Added new enumeration Api-peer-stats-info-oper. Changed type of type in API-PEER-STATS-INFO to use Api-peer-stats-info-oper. This is a non backward compatible change.
       2021-03-04
           Added MSD list per topology link. Added SRLB list per topology node.
       2021-01-29
           Updated SRv6 Endpoint function from int to enum.
       2020-09-16
           Adding operational nodes for new features path invalidation drop protected and unprotected path Operational nodes for PCE segment-routing traffic-eng policy
       2020-09-01
           Added uB6SID field in the LSP object
       2020-08-18
           Added SRv6 LSP details fields in the LSP object
       2020-07-13
           Added NodeID fields in the uN SID object in the IPv6 topology.
       2020-04-20
           Added fields in the PCE IPv6 link object.";
    semver:module-version "3.0.0";
  }
  revision 2020-03-17 {
    description
      "Add flex-algo related operational nodes. Updated description of statistics-nodes. Add SR-PAG related operational nodes. Add PCE authentication related operational nodes.
       2020-02-03
         Added TCP AuthenticationOption related operational model. Implemented show pce authentication. Added classes AuthenticationKeyTable and AuthenticationKey.
       2019-11-07
         Adding leaf preference, leaf interface-name, and leaf profile-id to support a new HTTP API bindpoint for sibling PCEs.
       2019-10-09
         Adding enum sr-flex-algo-prefix-sid, enum pce-cspf-flex-algo-definition-mistmatch, leaf flex-algo-prefix-sids, list sr-flex-algo, and container flex-algos to support Flex-algo info.";
    semver:module-version "2.0.0";
  }
  revision 2019-10-02 {
    description
      "Added REST peer statistic information.
       2019-09-27
         Implement new show pce lsp and show pce initiated tunnels commands for Optima";
    semver:module-version "1.1.0";
  }
  revision 2019-04-05 {
    description
      "Establish semantic version baseline.";
    semver:module-version "1.0.0";
  }
  revision 2017-09-07 {
    description
      "Fixed type translation error.";
  }
  revision 2017-08-24 {
    description
      "Added C flag to pcep flags.";
  }
  revision 2017-06-26 {
    description
      "Change identifiers to be more readable.";
  }
  revision 2017-05-01 {
    description
      "Fixing backward compatibility error in module.";
  }
  revision 2016-05-31 {
    description
      "Revision description string.";
  }
  revision 2015-11-09 {
    description
      "IOS XR 6.0 revision.";
  }

  grouping PCE-AFFINITY-TUN {
    description
      "PCE Affinity";
    leaf affinity-exclude-any {
      type uint32;
      description
        "Affinity exclude any";
    }
    leaf affinity-include-any {
      type uint32;
      description
        "Affinity include any";
    }
    leaf affinity-include-all {
      type uint32;
      description
        "Affinity include all";
    }
  }

  grouping PCE-HOP-DETAIL {
    description
      "Hop details";
    container hop-local-address {
      description
        "Hop local address";
      uses PCE-IP-ADDR-TYPE;
    }
    container hop-remote-address {
      description
        "Hop remote address";
      uses PCE-IP-ADDR-TYPE;
    }
    leaf label {
      type uint32;
      description
        "MPLS label";
    }
    leaf sid-type {
      type uint8;
      description
        "Sid type";
    }
    leaf local-interface-index {
      type uint32;
      description
        "Local interface index";
    }
    leaf remote-interface-index {
      type uint32;
      description
        "Remote interface index";
    }
  }

  grouping PCE-INITIATED-TUN-BAG {
    description
      "PCE INITIATED TUNNEL BAG";
    container pcc-address-xr {
      description
        "PCC address";
      uses PCE-IP-ADDR-TYPE;
    }
    container source-address {
      description
        "Source address";
      uses PCE-IP-ADDR-TYPE;
    }
    container destination-address {
      description
        "Destination address";
      uses PCE-IP-ADDR-TYPE;
    }
    container affinity {
      description
        "Affinity";
      uses PCE-AFFINITY-TUN;
    }
    container association-ipv4 {
      description
        "Association IPv4 address";
      uses PCE-IP-ADDR-TYPE;
    }
    container association-source {
      description
        "Association IPv4 source address";
      uses PCE-IP-ADDR-TYPE;
    }
    container disjointness {
      description
        "Disjointness info";
      uses PCE-ASSO-INFO;
    }
    leaf symbolic-name {
      type string;
      description
        "Symbolic Name";
    }
    leaf setup-type {
      type uint8;
      description
        "Setup type";
    }
    leaf color {
      type uint32;
      description
        "Color";
    }
    leaf preference {
      type uint32;
      description
        "Preference";
    }
    leaf binding-label {
      type uint32;
      description
        "Binding label";
    }
    leaf hop-computed-time {
      type uint32;
      description
        "Hop list computed time";
    }
    leaf metric-type {
      type uint32;
      description
        "Metric type";
    }
    leaf metric-value {
      type uint32;
      description
        "Metric value";
    }
    leaf srpid {
      type uint32;
      description
        "Stateful request parameter ID";
    }
    leaf tunnel-initiated-by {
      type uint32;
      description
        "Creator";
    }
    leaf association-id {
      type uint16;
      description
        "Association ID";
    }
    leaf autoroute {
      type boolean;
      description
        "Deprecated";
    }
    leaf xtc-controlled {
      type boolean;
      description
        "Allow reoptimizations by xtc";
    }
    leaf is-created-by-exec {
      type boolean;
      description
        "Created from exec cli";
    }
    leaf protected {
      type boolean;
      description
        "Protected status";
    }
    leaf sid-algorithm-set {
      type boolean;
      description
        "Flag to indicate if SID algorithm is set";
    }
    leaf sid-algorithm {
      type uint8;
      description
        "SID algorithm value. Applicable if
         SIDAlgorithmSet is set";
    }
    list hop {
      description
        "Hop array";
      uses PCE-HOP-DETAIL;
    }
  }
}
