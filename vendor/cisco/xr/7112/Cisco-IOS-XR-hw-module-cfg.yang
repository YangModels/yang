module Cisco-IOS-XR-hw-module-cfg {
  namespace "http://cisco.com/ns/yang/Cisco-IOS-XR-hw-module-cfg";
  prefix hw-module-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR hw-module package configuration.
     
     This module contains definitions
     for the following management objects:
       wait-ejector-close: Enable waiting for ejector close on all
         cards
       hw-module: Hardware module information
     
     Copyright (c) 2013-2023 by Cisco Systems, Inc.
     All rights reserved.";

  revision 2023-05-29 {
    description
      "Sysdb path and parent class change for wait ejector close leaf.
       2022-02-24
         Addition of wait ejector close leaf.";
    semver:module-version "3.1.0";
  }
  revision 2020-05-27 {
    description
      "Addition of attention-led and auto-reset-disable leaves to eXR model.";
    semver:module-version "3.0.0";
  }
  revision 2019-10-15 {
    description
      "IOS XR 7.0.12 revision.";
    semver:module-version "2.0.0";
  }
  revision 2019-04-05 {
    description
      "Establish semantic version baseline.";
    semver:module-version "1.0.0";
  }
  revision 2015-11-09 {
    description
      "IOS XR 6.0 revision.";
  }

  typedef Admin-state {
    type enumeration {
      enum "unshut" {
        value 0;
        description
          "Power On";
      }
      enum "shut" {
        value 1;
        description
          "Power Off";
      }
    }
    description
      "Admin state";
  }

  leaf wait-ejector-close {
    type boolean;
    default "true";
    description
      "Enable waiting for ejector close on all cards";
  }
  container hw-module {
    description
      "Hardware module information";
    container nodes {
      description
        "List of nodes";
      list node {
        key "location";
        description
          "Node object";
        container config {
          must "attention-led or admin-state or auto-reset-disable" {
            error-message "Hw-module config containers cannot be empty";
            description
              "At least one configuration parameter must be set";
          }
          description
            "Configuration data for hw-module";
          leaf auto-reset-disable {
            type boolean;
            description
              "Do not automatically reset the hw-module on
               failure";
          }
          leaf attention-led {
            type boolean;
            description
              "Enable hw-module attention LED (Blue)";
          }
          leaf admin-state {
            type Admin-state;
            description
              "Set the admin state of the hw-module";
          }
        }
        leaf location {
          type string;
          description
            "Location string";
        }
      }
    }
  }
}
