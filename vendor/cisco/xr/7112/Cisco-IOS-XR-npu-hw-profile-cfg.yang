module Cisco-IOS-XR-npu-hw-profile-cfg {
  namespace "http://cisco.com/ns/yang/Cisco-IOS-XR-npu-hw-profile-cfg";
  prefix npu-hw-profile-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR npu-hw-profile package configuration.
     
     This module contains definitions
     for the following management objects:
       macsec-hw-module: Macsec Related HW Module configs, Reload
         Card after config
       npu-hw-module-profile-config: none
     
     Copyright (c) 2013-2023 by Cisco Systems, Inc.
     All rights reserved.";

  revision 2023-11-13 {
    description
      "Enum added for npu-pktlosswin leaf
       2023-10-11
         Yang Schema added for qos high-water-marks
       2023-02-10
         Yang Schema added for IPv6 Shortening in hw-module config.
       2023-01-26
         Yang Schema added for gue underlay hash profile in hw-module config.
       2022-11-22
         Yang Schema updated for route scale lpm tcam-banks
       2022-11-14
         Yang Schema added for bgplu-over-rsvpte
       2022-09-30
         Yang Schema updated to add LDPoTE scale/label knobs
       2022-09-27
         Yang Schema added for pbr vrfredirect in hw-module config.
       2022-09-08
         Yang Schema updated for route scale lpm tcam-banks
       2022-09-01
         Yang Schema added for flowspec ipv6 packet length in hw-module config.
       2022-08-25
         Yang Schema added for vxlan ipv6 tunnel scale
       2022-07-07
         Yang Schema added for route scale lpm high
       2022-04-28
         Yang Schema added for l2 high scale
       2022-04-25
         Yang Schema added for npu compatibility
       2022-04-06
         Yang Schema added for vxlan-dc-leaf
       2022-02-11
         Yang Schema added for configuring CBF forward-class-list
       2021-12-11
         Yang Schema added for route scale high for IPV6 connected-prefix";
    semver:module-version "2.0.0";
  }
  revision 2021-08-15 {
    description
      "Yang Schema updated to make fair-4/fair-8 options visible
       2021-06-28
          Yang Schema updated to accept a range of values for lpts entry counters
       2021-04-30
          Yang Schema added for bd flush convergence
       2021-03-04
          Yang Schema added for pifib entry counters
       2021-02-16
          Yang Schema added for cbf";
    semver:module-version "1.1.0";
  }
  revision 2021-01-26 {
    description
      "Added CEF profile for punting ip-redirect";
    semver:module-version "1.0.0";
  }
  revision 2021-01-11 {
    description
      "Added profile CEF IPv6 hop-limit punt";
  }
  revision 2020-11-13 {
    description
      "Yang Schema removed block for NPU power profile in hw-module config.";
  }
  revision 2020-11-09 {
    description
      "Yang Schema fixed for npu config hw module cli - power profile model.";
  }
  revision 2020-09-29 {
    description
      "Yang Schema added for l2-qos-mode";
  }
  revision 2020-09-01 {
    description
      "Yang Schema added new VoQ modes.";
  }
  revision 2020-07-30 {
    description
      "Yang Schema added for npu-power-optimize";
  }
  revision 2020-06-04 {
    description
      "Yang Schema added for ttl mode of ip tunnel";
  }
  revision 2020-05-27 {
    description
      "Yang Schema added Macsec Related Yang Config Model.";
  }
  revision 2020-04-03 {
    description
      "Yang Schema added for label stats";
  }
  revision 2020-02-05 {
    description
      "Yang Schema updated for reorganized cli knobs.";
  }
  revision 2020-01-22 {
    description
      "Yang Schema added for bw-threshold.";
  }
  revision 2019-12-23 {
    description
      "Yang Schema adde for VoQ and Counter Sharing modes.";
  }
  revision 2019-10-14 {
    description
      "Yang Schema fixed for npu config hw module cli.";
  }
  revision 2019-04-05 {
    description
      "Establish semantic version baseline.";
  }
  revision 2015-11-09 {
    description
      "IOS XR 6.0 revision.";
  }

  typedef Npu-compatibility-mode {
    type enumeration {
      enum "q200" {
        value 2;
        description
          "Q200 asic";
      }
    }
    description
      "Npu compatibility mode";
  }

  typedef Ipv6-hop-limit-action {
    type enumeration {
      enum "punt" {
        value 1;
        description
          "IPv6 hop-limit punt";
      }
    }
    description
      "Ipv6 hop limit action";
  }

  typedef Npu-pkt-loss-win-mode {
    type enumeration {
      enum "3min" {
        value 1;
        description
          "3Min mode";
      }
      enum "5min" {
        value 2;
        description
          "5Min mode";
      }
    }
    description
      "Npu pkt loss win mode";
  }

  typedef Qos-voq-mode {
    type enumeration {
      enum "fair-4" {
        value 2;
        description
          "fair-4 VoQ Mode";
      }
      enum "fair-8" {
        value 3;
        description
          "fair-8 VoQ Mode";
      }
      enum "4" {
        value 4;
        description
          "4 VoQ Mode";
      }
      enum "8" {
        value 8;
        description
          "8 VoQ Mode";
      }
    }
    description
      "Qos voq mode";
  }

  container macsec-hw-module {
    description
      "Macsec Related HW Module configs, Reload Card
       after config";
    container fips-post-location-tables {
      description
        "Enable macsec-fips-post";
      list fips-post-location-table {
        key "location-string";
        description
          "none";
        leaf fips-post-location {
          type string;
          description
            "Macsec FIPS";
        }
        leaf location-string {
          type xr:Cisco-ios-xr-string;
          description
            "Location of MacsecFipsPost config or all";
        }
      }
    }
    container macsec-mode-location-tables {
      description
        "Enable macsec-mode";
      list macsec-mode-location-table {
        key "location-string";
        description
          "none";
        leaf macsec-mode-location {
          type string;
          description
            "Macsec Mode";
        }
        leaf location-string {
          type xr:Cisco-ios-xr-string;
          description
            "Location of MacSecMode config or all";
        }
      }
    }
  }
  container npu-hw-module-profile-config {
    description
      "none";
    container profile {
      description
        "Configure profile.";
      container qos {
        description
          "Configure qos profile";
        leaf l2-mode {
          type uint32 {
            range "2..3";
          }
          description
            "value either 2 or 3 (for L2 or L3 mode)";
        }
        leaf voq-mode {
          type Qos-voq-mode;
          description
            "voq mode to configure";
        }
      }
      container flowspec {
        description
          "Configure flowspec parameters";
        leaf ipv6-packet-len {
          type empty;
          description
            "Enable flowspec for ipv6 packet length
             classification";
        }
      }
      container gue {
        description
          "Configure gue udp port";
        leaf underlay-hash {
          type empty;
          description
            "Enable GUE underlay hash feature";
        }
        leaf destport {
          type uint32 {
            range "1000..64000";
          }
          description
            "Configure udp destination port for
             ipv4/ipv6/mpls payloads";
        }
      }
      container tcam-table {
        description
          "Configure profile for TCAM LC cards";
        container fib-table {
          description
            "FIB table for TCAM LC cards";
          container ipv6-address {
            description
              "IPv6 table for TCAM LC cards";
            container ipv6-unicast {
              description
                "Unicast table for TCAM LC cards";
              leaf ipv6-unicast-percent {
                type uint32 {
                  range "0..100";
                }
                units "percentage";
                description
                  "curve out percentage of TCAM table entries";
              }
            }
          }
          container ipv4-address {
            description
              "IPv4 table for TCAM LC cards";
            container ipv4-unicast {
              description
                "Unicast table for TCAM LC cards";
              leaf ipv4-unicast-percent {
                type uint32 {
                  range "0..100";
                }
                units "percentage";
                description
                  "curve out percentage of TCAM table entries";
              }
            }
          }
        }
        container acl-table {
          description
            "ACL table for TCAM LC cards";
          leaf acl-percent {
            type uint32 {
              range "0..100";
            }
            units "percentage";
            description
              "curve out percentage of TCAM table entries";
          }
        }
      }
      container netflow {
        description
          "Configure Netflow profile.";
        container ipfix-netflow-locations {
          description
            "none";
          list ipfix-netflow-location {
            key "location-string";
            description
              "none";
            leaf location-string {
              type xr:Cisco-ios-xr-string;
              description
                "Location of NETFLOW config";
            }
            list ipfix-netflow-location-leaf {
              key "location-id";
              description
                "none";
              leaf location-id {
                type uint32;
                description
                  "Location ID";
              }
              leaf enable-val {
                type uint32;
                mandatory true;
                description
                  "If Enabled set value to 65535";
              }
            }
          }
        }
        container ipfix-location-all {
          description
            "IPFIX315 Location All";
          leaf ipfix-location-all-leaf {
            type uint32;
            description
              "If Enabled set value to 65535";
          }
        }
      }
      container route {
        description
          "route";
        container scale {
          description
            "scale";
          container lpm {
            description
              "lpm";
            container wide-entries {
              description
                "IPv6 wide entries";
              leaf shortened {
                type empty;
                description
                  "Change shortening";
              }
            }
            leaf tcam-banks {
              type empty;
              description
                "Enable profile scale lpm tcam-banks";
            }
          }
          container ipv6-unicast {
            description
              "ipv6 unicast";
            container connected-prefix {
              description
                "connected prefix";
              leaf high {
                type empty;
                description
                  "Enable profile ipv6-unicast
                   connected-prefix high";
              }
            }
          }
          container hbm-algo {
            description
              "hbm algo";
            leaf hbm-hi-hbm {
              type empty;
              description
                "Change hbm-hit-hbm";
            }
            leaf hbm-chronograph {
              type empty;
              description
                "Change hbm-chronograph";
            }
            leaf hbm-hi-sram {
              type empty;
              description
                "Change hbm-hit-sram";
            }
          }
        }
      }
      container npu {
        description
          "Configure npu ";
        container buffer-extended-locs {
          description
            "Configure buffer-extended ";
          list buffer-extended-loc {
            key "location-string";
            description
              "none";
            leaf bandwidth-congestion-protect {
              type empty;
              description
                "Disable device congestion protect";
            }
            leaf buffer-extended-congestion-detection {
              type empty;
              description
                "Enable buffer-extended-congestion-detection";
            }
            leaf location-string {
              type xr:Cisco-ios-xr-string;
              description
                "Location of buffer-extended config or all";
            }
          }
        }
      }
      container stats {
        description
          "Configure statistics profile";
        leaf voq-sharing-counters {
          type uint32 {
            range "1..4";
          }
          description
            "Configure number of voqs (1, 2, 4) sharing
             counters";
        }
      }
      container l2fib {
        description
          "Configure l2fib profiles";
        leaf data-center {
          type empty;
          description
            "Data center mode";
        }
        leaf pw-stats {
          type uint32;
          description
            "If enabled, set value to 1";
        }
        leaf bd-flush-conv {
          type empty;
          description
            "BD flush convergence mode";
        }
        leaf high-scale {
          type boolean;
          description
            "TRUE if enabled, FALSE if disabled";
        }
      }
      container cef-forwarding {
        description
          "Configure cef profiles";
        container te-tunnel {
          description
            "Configure te-tunnel profile";
          leaf label-over-te-counter {
            type uint32;
            description
              "Configure label counters instead of TE
               counters";
          }
          leaf high-scale-ldpote {
            type uint32;
            description
              "Configure te-tunnel highscale with ldp over
               te feature and disable sr over srte";
          }
          leaf high-scale {
            type uint32;
            description
              "Configure te-tunnel highscale and disable ldp
               over te feature";
          }
        }
        container cef-stats {
          description
            "Configure feature level stats";
          container label {
            description
              "Configure label stats";
            container app-default {
              description
                "Applies to - LDP and SR";
              leaf dynamic {
                type uint32;
                description
                  "If enabled, set value to 1";
              }
            }
          }
        }
        container ttl {
          description
            "Configure ttl profile";
          container tunnel-ip {
            description
              "Configure tunnel-ip ttl mode";
            leaf decrement {
              type uint32;
              description
                "Configure tunnel-ip ttl decrement attribute";
            }
          }
        }
        container ipv6 {
          description
            "IPv6";
          leaf hop-limit {
            type Ipv6-hop-limit-action;
            description
              "IPv6 hop-limit 0 packets";
          }
        }
        container lpts-xr {
          description
            "Enable lpts pifib per-entry counters";
          leaf pifib-entry-counters {
            type uint32 {
              range "256..512";
            }
            description
              "Configure number of counters";
          }
        }
        container vxlan {
          description
            "VXLAN";
          leaf ipv6-tnl-scale {
            type empty;
            description
              "Enable profile CEF VXLAN IPV6-TNL-SCALE";
          }
        }
        container lpts {
          description
            "LPTS";
          leaf acl {
            type empty;
            description
              "Enable profile CEF LPTS ACL";
          }
        }
        leaf bgplu-over-rsvpte {
          type uint32;
          description
            "Enable BGPLU over RSVPTE feature";
        }
        leaf sropt {
          type uint32 {
            range "0..1";
          }
          description
            "Configure SROPT feature";
        }
        leaf cbf {
          type empty;
          description
            "Enable cbf feature";
        }
        leaf unipath-surpf {
          type empty;
          description
            "Configure unipath surpf feature";
        }
        leaf forward-class-list {
          type uint32 {
            range "0..7";
          }
          default "0";
          description
            "forward class list";
        }
        leaf bgplu {
          type uint32;
          description
            "If Enabled set value to 1";
        }
        leaf dark-bandwidth {
          type uint32 {
            range "0..1";
          }
          description
            "Configure dark-bandwidth feature";
        }
        leaf ip-redirect {
          type uint32 {
            range "0..1";
          }
          description
            "value either 0 or 1";
        }
      }
      container pbr {
        description
          "Configure pbr parameters";
        leaf vrf-redirect {
          type empty;
          description
            "Enable vrf-redirect";
        }
      }
      leaf npu-pktlosswin {
        type Npu-pkt-loss-win-mode;
        description
          "Configure packet loss duration for raising
           syslog";
      }
      leaf bw-threshold {
        type string;
        units "percentage";
        description
          "Configure fabric BW";
      }
      leaf npu-compatibility {
        type Npu-compatibility-mode;
        description
          "Configure npu compatibility mode for chassis";
      }
    }
  }
}
