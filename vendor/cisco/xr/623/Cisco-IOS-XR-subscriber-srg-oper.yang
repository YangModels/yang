module Cisco-IOS-XR-subscriber-srg-oper {
  namespace "http://cisco.com/ns/yang/Cisco-IOS-XR-subscriber-srg-oper";
  prefix subscriber-srg-oper;

  import Cisco-IOS-XR-types {
    prefix xr;
  }
  include Cisco-IOS-XR-subscriber-srg-oper-sub1 {
    revision-date 2015-11-09;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR subscriber-srg package operational data.
     
     This module contains definitions
     for the following management objects:
       subscriber-redundancy-manager: Subscriber Redundancy Manager
         information
       subscriber-redundancy-agent: subscriber redundancy agent
     
     Copyright (c) 2013-2016 by Cisco Systems, Inc.
     All rights reserved.";

  revision 2015-11-09 {
    description
      "IOS XR 6.0 revision.";
  }

  container subscriber-redundancy-manager {
    config false;
    description
      "Subscriber Redundancy Manager information";
    container groups {
      description
        "Subscriber Redundancy Manager group table";
      list group {
        key "group";
        description
          "Subscriber redundancy manager group";
        leaf group {
          type xr:Cisco-ios-xr-string;
          description
            "Group";
        }
        uses SRG-SHOW-MGR-GROUP-ENTRY;
      }
    }
    container summary {
      description
        "Subscriber redundancy manager summary";
      uses SRG-SHOW-MGR-SUMMARY;
    }
    container interfaces {
      description
        "Subscriber Redundancy Manager interface table";
      list interface {
        key "interface";
        description
          "Subscriber redundancy manager interface";
        leaf interface {
          type xr:Cisco-ios-xr-string;
          description
            "Interface";
        }
        uses SRG-SHOW-MGR-INTF-ENTRY;
      }
    }
  }
  container subscriber-redundancy-agent {
    config false;
    description
      "subscriber redundancy agent";
    container nodes {
      description
        "List of nodes for which subscriber data is
         collected";
      list node {
        key "node-name";
        description
          "Subscriber data for a particular node";
        container group-id-xr {
          description
            "Data for particular subscriber group session";
          list group-id {
            key "group-id";
            description
              "Group id for subscriber group session";
            leaf group-id {
              type xr:Cisco-ios-xr-string;
              description
                "GroupId";
            }
            uses SRG-SHOW-SESSION-ENTRY;
          }
        }
        container interfaces {
          description
            "List of interfaces";
          list interface {
            key "interface";
            description
              "Specify interface name";
            leaf interface {
              type xr:Interface-name;
              description
                "Interface";
            }
            uses SRG-SHOW-AGT-INTF-ENTRY;
          }
        }
        container group-summaries {
          description
            "Subscriber data for a particular node";
          list group-summary {
            key "group-id";
            description
              "Subscriber redundancy agent group summary";
            leaf group-id {
              type xr:Cisco-ios-xr-string;
              description
                "GroupId";
            }
            uses SRG-AGT-SHOW-GROUP-LIST-ENTRY;
          }
        }
        container group-ids {
          description
            "Data for particular subscriber group ";
          list group-id {
            key "group-id";
            description
              "Group id for subscriber group";
            leaf group-id {
              type xr:Cisco-ios-xr-string;
              description
                "Group Id";
            }
            uses SRG-SHOW-GROUP-ENTRY;
          }
        }
        leaf node-name {
          type xr:Node-id;
          description
            "Node name";
        }
      }
    }
  }
}
