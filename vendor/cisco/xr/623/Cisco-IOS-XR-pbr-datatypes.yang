module Cisco-IOS-XR-pbr-datatypes {
  namespace "http://cisco.com/ns/yang/Cisco-IOS-XR-pbr-datatypes";
  prefix pbr-datatypes;

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of generally useful
     derived YANG data types.
     
     Copyright (c) 2013-2016 by Cisco Systems, Inc.
     All rights reserved.";

  revision 2015-11-09 {
    description
      "IOS XR 6.0 revision.";
  }

  typedef Vservice-nsh-path-id-range {
    type uint32 {
      range "1..16777215";
    }
    description
      "Vservice nsh path id range";
  }

  typedef Vservice-nsh-service-index-range {
    type uint32 {
      range "1..255";
    }
    description
      "Vservice nsh service index range";
  }
}
