module Cisco-IOS-XR-platform-pifib-oper {
  namespace "http://cisco.com/ns/yang/Cisco-IOS-XR-platform-pifib-oper";
  prefix platform-pifib-oper;

  import Cisco-IOS-XR-types {
    prefix xr;
  }
  import Cisco-IOS-XR-lpts-pre-ifib-oper {
    prefix a1;
  }
  include Cisco-IOS-XR-platform-pifib-oper-sub1 {
    revision-date 2016-02-22;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR platform-pifib package operational data.
     
     This YANG module augments the
       Cisco-IOS-XR-lpts-pre-ifib-oper
     module with state data.
     
     Copyright (c) 2013-2016 by Cisco Systems, Inc.
     All rights reserved.";

  revision 2016-02-22 {
    description
      "Initial revision.";
  }
  revision 2015-11-09 {
    description
      "IOS XR 6.0 revision.";
  }

  typedef Usage-address-family {
    type enumeration {
      enum "ipv4" {
        value 0;
        description
          "Ipv4 af";
      }
      enum "ipv6" {
        value 1;
        description
          "Ipv6 af";
      }
    }
    description
      "Usage address family";
  }

  augment "/a1:lpts-pifib/a1:nodes/a1:node" {
    description
      "This augment extends the operational data of
       'Cisco-IOS-XR-lpts-pre-ifib-oper'";
    container hardware {
      description
        "Hardware specific";
      container usage-entries {
        description
          "Usage Table options";
        list usage-entry {
          key "region-id";
          description
            "Usage details";
          leaf region-id {
            type Usage-address-family;
            description
              "Region ID";
          }
          uses PL-PIFIB-SHOW-USAGE;
        }
      }
      container police {
        description
          "Police details";
        uses PL-PIFIB-SHOW-POLICE;
      }
      container static-police {
        description
          "Static Police details";
        uses PL-PIFIB-SHOW-STATIC-POLICE;
      }
      container bfd {
        description
          "Bfd details";
        uses PL-PIFIB-SHOW-BFD-DISC-ENTRY;
      }
      container statistics {
        description
          "Hardware Entry type";
        uses PL-PIFIB-SHOW-STATS;
      }
      container index-entries {
        description
          "Hardware Entry options";
        list index-entry {
          key "index";
          description
            "Entry options";
          leaf index {
            type int32;
            description
              "Index";
          }
          uses PL-PIFIB-SHOW-ENTRY;
        }
      }
    }
  }
}
