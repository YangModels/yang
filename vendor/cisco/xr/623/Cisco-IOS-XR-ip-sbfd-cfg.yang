module Cisco-IOS-XR-ip-sbfd-cfg {
  namespace "http://cisco.com/ns/yang/Cisco-IOS-XR-ip-sbfd-cfg";
  prefix ip-sbfd-cfg;

  import ietf-inet-types {
    prefix inet;
  }
  import Cisco-IOS-XR-types {
    prefix xr;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ip-sbfd package configuration.
     
     This module contains definitions
     for the following management objects:
       sbfd: SBFD Configuration ,Seamless-BFD is method for detecting
         faultsbetween two different nodes in a network
     
     Copyright (c) 2013-2016 by Cisco Systems, Inc.
     All rights reserved.";

  revision 2015-11-09 {
    description
      "IOS XR 6.0 revision.";
  }

  grouping REMOTE-DISCRIMINATOR {
    description
      "Common node of ipv4-address, ipv6-address";
    list remote-discriminator {
      key "remote-discriminator";
      description
        "Remote Discriminator value";
      leaf remote-discriminator {
        type uint32 {
          range "1..4294967295";
        }
        description
          "Remote Discriminator Value";
      }
    }
  }

  container sbfd {
    description
      "SBFD Configuration ,Seamless-BFD is method for
       detecting faultsbetween two different nodes in a
       network";
    container remote-target {
      description
        "configure remote target";
      container ipv4-addresses {
        description
          "ipv4 address as target";
        list ipv4-address {
          key "address";
          description
            "IP Address Value for RemoteDiscriminatorTable";
          leaf address {
            type inet:ipv4-address-no-zone;
            description
              " IPv4 address";
          }
          uses REMOTE-DISCRIMINATOR;
        }
      }
      container ipv6-addresses {
        description
          "ipv6 address as target";
        list ipv6-address {
          key "address";
          description
            "IP Address Value for RemoteDiscriminatorTable";
          leaf address {
            type inet:ipv6-address-no-zone;
            description
              " IPv6 adddress";
          }
          uses REMOTE-DISCRIMINATOR;
        }
      }
    }
    container local-discriminator {
      description
        "Configure local discriminator";
      container intf-discriminators {
        description
          "Configure local discriminator from interface
           address";
        list intf-discriminator {
          key "interface-name";
          description
            "interface address as discriminator";
          leaf interface-name {
            type xr:Interface-name;
            description
              "Interface Name";
          }
        }
      }
      container dynamic-discriminators {
        description
          "Configure local discriminator dynamically";
        list dynamic-discriminator {
          key "discriminator";
          description
            "Local discriminator value";
          leaf discriminator {
            type uint32 {
              range "0..1";
            }
            description
              "Dynamic discriminator value";
          }
        }
      }
      container ipv4-discriminators {
        description
          "Configure local discriminator as an ipv4
           address";
        list ipv4-discriminator {
          key "address";
          description
            "ipv4 address as discriminator";
          leaf address {
            type inet:ip-address-no-zone;
            description
              " IPv4 address";
          }
        }
      }
      container val32-discriminators {
        description
          "Configure local discriminator as an integer";
        list val32-discriminator {
          key "discriminator";
          description
            "Local discriminator value";
          leaf discriminator {
            type uint32 {
              range "1..4294967295";
            }
            description
              "Local discriminator value";
          }
        }
      }
    }
  }
}
