module Cisco-IOS-XR-wd-cfg {
  namespace "http://cisco.com/ns/yang/Cisco-IOS-XR-wd-cfg";
  prefix wd-cfg;

  import Cisco-IOS-XR-types {
    prefix xr;
  }
  import Cisco-IOS-XR-config-mda-cfg {
    prefix node;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR wd package configuration.
     
     This module contains definitions
     for the following management objects:
       watchdog: watchdog
     
     This YANG module augments the
       Cisco-IOS-XR-config-mda-cfg
     module with configuration data.
     
     Copyright (c) 2013-2016 by Cisco Systems, Inc.
     All rights reserved.";

  revision 2015-11-09 {
    description
      "IOS XR 6.0 revision.";
  }
  revision 2015-10-12 {
    description
      "Descriptions updated.";
  }

  grouping NODE-CFG {
    description
      "active/preconfigured nodes configuration";
    container watchdog-node-threshold {
      description
        "Watchdog threshold configuration";
      container memory-threshold {
        description
          "Memory thresholds";
        leaf minor {
          type uint32 {
            range "5..40";
          }
          description
            "Threshold, Range(5, 40)";
        }
        leaf severe {
          type uint32 {
            range "4..40";
          }
          description
            "Threshold, Range(4, minor)";
        }
        leaf critical {
          type uint32 {
            range "3..40";
          }
          description
            "Threshold, Range(3, severe)";
        }
      }
    }
  }

  augment "/node:active-nodes/node:active-node" {
    description
      "This augment extends active nodes configuration";
    uses NODE-CFG;
  }
  augment "/node:preconfigured-nodes/node:preconfigured-node" {
    description
      "This augment extends preconfigured nodes
       configuration";
    uses NODE-CFG;
  }
  container watchdog {
    description
      "watchdog";
    container threshold-memory {
      description
        "Memory thresholds";
      leaf minor {
        type uint32 {
          range "5..40";
        }
        description
          "Threshold, Range(5, 40)";
      }
      leaf severe {
        type uint32 {
          range "4..40";
        }
        description
          "Threshold, Range(4, minor)";
      }
      leaf critical {
        type uint32 {
          range "3..40";
        }
        description
          "Threshold, Range(3, severe)";
      }
    }
    leaf threshold-memory-switchover {
      type uint32 {
        range "2..4";
      }
      description
        "switchover the RP at configured memory state";
    }
    leaf restart-deadlock-disable {
      type empty;
      description
        "Disable watchdog restart deadlock";
    }
    leaf monitor-qnet-timeout {
      type uint32 {
        range "10..3600";
      }
      units "second";
      description
        "Watchdog monitor transport qnet timeout";
    }
    leaf monitor-cpuhog-timeout {
      type uint32 {
        range "10..3600";
      }
      units "second";
      description
        "Watchdog monitor cpu-hog persistent timeout
         configuration";
    }
    leaf monitor-procnto-timeout {
      type uint32 {
        range "60..3600";
      }
      units "second";
      description
        "Watchdog monitor procnto timeout configuration";
    }
    leaf overload-notification {
      type empty;
      description
        "Disable critical event notification";
    }
    leaf restart-cpuhog-disable {
      type empty;
      description
        "Disable watchdog restart cpu-hog";
    }
    leaf restart-memoryhog-disable {
      type empty;
      description
        "Disable watchdog restart memory-hog";
    }
    leaf overload-throttle-timeout {
      type uint32 {
        range "5..120";
      }
      units "second";
      description
        "Watchdog overload throttle timeout configuration";
    }
  }
}
