submodule Cisco-IOS-XR-tty-server-oper-sub4 {
  belongs-to Cisco-IOS-XR-tty-server-oper {
    prefix Cisco-IOS-XR-tty-server-oper;
  }

  import Cisco-IOS-XR-types {
    prefix xr;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR tty-server package operational data.
     
     Copyright (c) 2013-2016 by Cisco Systems, Inc.
     All rights reserved.";

  revision 2015-07-30 {
    description
      "Descriptions updated.";
  }
  revision 2015-01-07 {
    description
      "IOS XR 5.3.1 revision.";
  }

  grouping TTY-GENERAL-STATS {
    description
      "TTY Server general statistics";
    leaf terminal-length {
      type uint32;
      description
        "Terminal length";
    }
    leaf terminal-width {
      type uint32;
      description
        "Line width";
    }
    leaf async-interface {
      type boolean;
      description
        "Usable as async interface";
    }
    leaf flow-control-start-character {
      type int8;
      description
        "Software flow control start char";
    }
    leaf flow-control-stop-character {
      type int8;
      description
        "Software flow control stop char";
    }
    leaf domain-lookup-enabled {
      type boolean;
      description
        "DNS resolution enabled";
    }
    leaf motd-banner-enabled {
      type boolean;
      description
        "MOTD banner enabled";
    }
    leaf private-flag {
      type boolean;
      description
        "TTY private flag";
    }
    leaf terminal-type {
      type string;
      description
        "Terminal type";
    }
    leaf absolute-timeout {
      type uint32;
      description
        "Absolute timeout period";
    }
    leaf idle-time {
      type uint32;
      description
        "TTY idle time";
    }
  }
}
