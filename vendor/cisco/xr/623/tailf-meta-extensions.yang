submodule tailf-meta-extensions {

  belongs-to tailf-common {
    prefix tailf;
  }

  organization "Tail-f Systems";

  description
    "This submodule defines Tail-f YANG meta extensions statements.";

  revision 2010-08-19 {
    description
      "Released as part of ConfD-3.3.1.

       Added tailf:snmp-identifier.";
  }

  revision 2010-03-18 {
    description
      "Released as part of ConfD-3.2.";
  }

  /*
   * Types used to describe the extension statements' arguments.
   */

  typedef identifier {
    type string {
      pattern "[A-Za-z_][A-Za-z0-9_-]*";
    }
  }

  typedef snmp-identifier {
    type string {
      pattern "[A-Za-z_][A-Za-z0-9_-]*(:[A-Za-z_][A-Za-z0-9_-]*)*";
    }
  }

  typedef tailf-oid {
    type string {
      pattern "(([0-1](\.[1-3]?[0-9]))"
            + "|(2.(0|([1-9]\d*)))"
            + "|([A-Za-z_][A-Za-z0-9_-]*))?"
            + "(\.(0|([1-9]\d*)))+";
    }
  }

  /*
   * Descriptive meta extensions
   */

  extension use-in {
    argument name;
    description
      "Specifies in which statements a particular extension statement can be
      used.";
  }

  extension substatement {
    argument name;
    description
      "Specifies which statements can occur as substatement to the
      given statement.";
  }

  extension arg-type {
    tailf:substatement "type";
    description
      "Specifies the type of the argument.";
  }

}
