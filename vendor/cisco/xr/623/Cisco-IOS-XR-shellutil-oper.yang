module Cisco-IOS-XR-shellutil-oper {
  namespace "http://cisco.com/ns/yang/Cisco-IOS-XR-shellutil-oper";
  prefix shellutil-oper;

  import Cisco-IOS-XR-types {
    prefix xr;
  }
  include Cisco-IOS-XR-shellutil-oper-sub1 {
    revision-date 2015-01-07;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR shellutil package operational data.
     
     This module contains definitions
     for the following management objects:
       system-time: System time information
     
     Copyright (c) 2013-2016 by Cisco Systems, Inc.
     All rights reserved.";

  revision 2015-01-07 {
    description
      "IOS XR 5.3.1 revision.";
  }

  container system-time {
    config false;
    description
      "System time information";
    container clock {
      description
        "System clock information";
      uses TIME-DATE;
    }
    container uptime {
      description
        "System uptime information";
      uses SYSTEM-UPTIME;
    }
  }
}
