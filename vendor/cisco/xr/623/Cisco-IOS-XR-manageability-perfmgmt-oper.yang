module Cisco-IOS-XR-manageability-perfmgmt-oper {
  namespace "http://cisco.com/ns/yang/Cisco-IOS-XR-manageability-perfmgmt-oper";
  prefix manageability-perfmgmt-oper;

  import ietf-inet-types {
    prefix inet;
  }
  import Cisco-IOS-XR-types {
    prefix xr;
  }
  include Cisco-IOS-XR-manageability-perfmgmt-oper-sub1 {
    revision-date 2015-11-09;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR manageability-perfmgmt package operational data.
     
     This module contains definitions
     for the following management objects:
       perf-mgmt: Performance Management agent operational data
     
     Copyright (c) 2013-2016 by Cisco Systems, Inc.
     All rights reserved.";

  revision 2015-11-09 {
    description
      "IOS XR 6.0 revision.";
  }

  typedef Pm-process-id {
    type int32;
    description
      "Pm process id";
  }

  typedef Pm-sample-id {
    type int32;
    description
      "Pm sample id";
  }

  grouping MPLS {
    description
      "Common node of periodic, monitor";
    container mpls {
      description
        "Collected MPLS data";
      container ldp-neighbors {
        description
          "LDP neighbors for which statistics are
           collected";
        list ldp-neighbor {
          key "nbr";
          description
            "Samples for a particular LDP neighbor";
          container samples {
            description
              "Samples for a particular LDP neighbor";
            list sample {
              key "sample-id";
              description
                "LDP neighbor statistics sample";
              leaf sample-id {
                type Pm-sample-id;
                description
                  "Sample ID";
              }
              uses PM-MPLS-LDP-BAG;
            }
          }
          leaf nbr {
            type inet:ipv4-address-no-zone;
            description
              "Neighbor Address";
          }
        }
      }
    }
  }

  grouping INTERFACE {
    description
      "Common node of periodic, monitor";
    container interface {
      description
        "Collected Interface data";
      container generic-counter-interfaces {
        description
          "Interfaces for which Generic Counters are
           collected";
        list generic-counter-interface {
          key "interface-name";
          description
            "Samples for a particular interface";
          container samples {
            description
              "Generic Counter samples for an interface";
            list sample {
              key "sample-id";
              description
                "Generic Counters sample";
              leaf sample-id {
                type Pm-sample-id;
                description
                  "Sample ID";
              }
              uses PM-INTERFACE-GENERIC-BAG;
            }
          }
          leaf interface-name {
            type xr:Interface-name;
            description
              "Interface Name";
          }
        }
      }
      container basic-counter-interfaces {
        description
          "Interfaces for which Basic Counters are
           collected";
        list basic-counter-interface {
          key "interface-name";
          description
            "Samples for a particular interface";
          container samples {
            description
              "Basic Counter samples for an interface";
            list sample {
              key "sample-id";
              description
                "Basic Counters sample";
              leaf sample-id {
                type Pm-sample-id;
                description
                  "Sample ID";
              }
              uses PM-INTERFACE-BASIC-STATS;
            }
          }
          leaf interface-name {
            type xr:Interface-name;
            description
              "Interface Name";
          }
        }
      }
      container data-rate-interfaces {
        description
          "Interfaces for which Data Rates are collected";
        list data-rate-interface {
          key "interface-name";
          description
            "Samples for a particular interface";
          container samples {
            description
              "Data Rate samples for an interface";
            list sample {
              key "sample-id";
              description
                "Data Rates sample";
              leaf sample-id {
                type Pm-sample-id;
                description
                  "Sample ID";
              }
              uses PM-INTERFACE-DATARATE-BAG;
            }
          }
          leaf interface-name {
            type xr:Interface-name;
            description
              "Interface Name";
          }
        }
      }
    }
  }

  grouping NODE-TABLE {
    description
      "Common node of periodic, monitor";
    container nodes {
      description
        "Nodes for which data is collected";
      list node {
        key "node-id";
        description
          "Node Instance";
        container sample-xr {
          description
            "Node CPU data";
          list sample {
            key "sample-id";
            description
              "Node CPU data sample";
            leaf sample-id {
              type Pm-sample-id;
              description
                "Sample ID";
            }
            uses PM-NODE-CPU-BAG;
          }
        }
        container processes {
          description
            "Processes data";
          list process {
            key "process-id";
            description
              "Process data";
            container samples {
              description
                "Process data";
              list sample {
                key "sample-id";
                description
                  "Process data sample";
                leaf sample-id {
                  type Pm-sample-id;
                  description
                    "Sample ID";
                }
                uses PM-NODE-PROCESS-BAG;
              }
            }
            leaf process-id {
              type Pm-process-id;
              description
                "Process ID";
            }
          }
        }
        container samples {
          description
            "Node Memory data";
          list sample {
            key "sample-id";
            description
              "Node Memory data sample";
            leaf sample-id {
              type Pm-sample-id;
              description
                "Sample ID";
            }
            uses PM-NODE-MEM-BAG;
          }
        }
        leaf node-id {
          type xr:Node-id;
          description
            "Node ID";
        }
      }
    }
  }

  grouping OSPF {
    description
      "Common node of periodic, monitor";
    container ospf {
      description
        "Collected OSPF data";
      container ospfv2-protocol-instances {
        description
          "OSPF v2 instances for which protocol statistics
           are collected";
        list ospfv2-protocol-instance {
          key "instance-name";
          description
            "Protocol samples for a particular OSPF v2
             instance";
          container samples {
            description
              "Sample Table for an OSPV v2 instance";
            list sample {
              key "sample-id";
              description
                "Generic Counters sample";
              leaf sample-id {
                type Pm-sample-id;
                description
                  "Sample ID";
              }
              uses PM-OSPF-V2PROTO-BAG;
            }
          }
          leaf instance-name {
            type xr:Cisco-ios-xr-string;
            description
              "OSPF Instance Name";
          }
        }
      }
      container ospfv3-protocol-instances {
        description
          "OSPF v3 instances for which protocol statistics
           are collected";
        list ospfv3-protocol-instance {
          key "instance-name";
          description
            "Protocol samples for a particular OSPF v3
             instance";
          container samples {
            description
              "Sample Table for an OSPV v3 instance";
            list sample {
              key "sample-id";
              description
                "Generic Counters sample";
              leaf sample-id {
                type Pm-sample-id;
                description
                  "Sample ID";
              }
              uses PM-OSPF-V3PROTO-BAG;
            }
          }
          leaf instance-name {
            type xr:Cisco-ios-xr-string;
            description
              "OSPF Instance Name";
          }
        }
      }
    }
  }

  grouping BGP {
    description
      "Common node of periodic, monitor";
    container bgp {
      description
        "Collected BGP data";
      container bgp-neighbors {
        description
          "Neighbors for which statistics are collected";
        list bgp-neighbor {
          key "ip-address";
          description
            "Samples for particular neighbor";
          container samples {
            description
              "Sample Table for a BGP neighbor";
            list sample {
              key "sample-id";
              description
                "Neighbor statistics sample";
              leaf sample-id {
                type Pm-sample-id;
                description
                  "Sample ID";
              }
              uses PM-BGP-NBR-BAG;
            }
          }
          leaf ip-address {
            type inet:ipv4-address-no-zone;
            description
              "BGP Neighbor Identifier";
          }
        }
      }
    }
  }

  container perf-mgmt {
    config false;
    description
      "Performance Management agent operational data";
    container periodic {
      description
        "Data from periodic requests";
      uses OSPF;
      uses MPLS;
      uses NODE-TABLE;
      uses BGP;
      uses INTERFACE;
    }
    container monitor {
      description
        "Data from monitor (one history period) requests";
      uses OSPF;
      uses MPLS;
      uses NODE-TABLE;
      uses BGP;
      uses INTERFACE;
    }
  }
}
