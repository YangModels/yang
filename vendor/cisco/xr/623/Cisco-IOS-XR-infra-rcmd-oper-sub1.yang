submodule Cisco-IOS-XR-infra-rcmd-oper-sub1 {
  belongs-to Cisco-IOS-XR-infra-rcmd-oper {
    prefix Cisco-IOS-XR-infra-rcmd-oper;
  }

  import ietf-inet-types {
    prefix inet;
  }
  import Cisco-IOS-XR-types {
    prefix xr;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR infra-rcmd package operational data.
     
     Copyright (c) 2013-2016 by Cisco Systems, Inc.
     All rights reserved.";

  revision 2015-11-09 {
    description
      "IOS XR 6.0 revision.";
  }

  typedef Rcmd-show-inst-state {
    type enumeration {
      enum "unknown" {
        value 0;
        description
          "Unknown state";
      }
      enum "active" {
        value 1;
        description
          "Active state";
      }
      enum "in-active" {
        value 2;
        description
          "InActive state";
      }
      enum "na" {
        value 3;
        description
          "Max state";
      }
    }
    description
      "instance state";
  }

  typedef Rcmd-show-intf-event {
    type enumeration {
      enum "create" {
        value 1;
        description
          "Create";
      }
      enum "delete" {
        value 2;
        description
          "Delete";
      }
      enum "link-up" {
        value 3;
        description
          "LinkUp";
      }
      enum "link-down" {
        value 4;
        description
          "LinkDown";
      }
      enum "primary-address" {
        value 5;
        description
          "PrimaryAddress";
      }
      enum "secondary-address" {
        value 6;
        description
          "SecondaryAddress";
      }
      enum "ipv6-link-local-address" {
        value 7;
        description
          "Ipv6LinkLocalAddress";
      }
      enum "ipv6-global-address" {
        value 8;
        description
          "Ipv6GlobalAddress";
      }
      enum "mtu" {
        value 9;
        description
          "MTU";
      }
      enum "band-width" {
        value 10;
        description
          "BandWidth";
      }
      enum "ldp-sync" {
        value 11;
        description
          "LDPSync";
      }
      enum "forward-reference" {
        value 12;
        description
          "ForwardReference";
      }
      enum "ldp-no-sync" {
        value 13;
        description
          "LDPNoSync";
      }
    }
    description
      "Rcmd show intf event";
  }

  typedef Rcmd-show-comp-id {
    type enumeration {
      enum "ospf" {
        description
          "OSPF component";
      }
      enum "isis" {
        description
          "ISIS component";
      }
      enum "un-known" {
        description
          "Max NA";
      }
    }
    description
      "Component Info";
  }

  typedef Rcmd-show-ldp-conv-state {
    type enumeration {
      enum "not-full" {
        description
          "Not Fully Covered";
      }
      enum "fully-covered" {
        description
          "Fully Covered";
      }
      enum "coverage-above-threshold" {
        description
          "Backup Coverage Above Threshold";
      }
      enum "coverage-below-threshold" {
        description
          "Backup Coverage Below Threshold";
      }
      enum "coverage-flapping" {
        description
          "Backup Coverage is Flappping";
      }
    }
    description
      "LDP Convergence States";
  }

  typedef Rcmd-show-ldp-session-state {
    type enumeration {
      enum "gr-down" {
        description
          "GR Down State";
      }
      enum "gr-converging" {
        description
          "GR Converging State";
      }
      enum "establishing" {
        description
          "Establishing State";
      }
      enum "converging" {
        description
          "Converging State";
      }
      enum "converged" {
        description
          "Converged State";
      }
      enum "retrying" {
        description
          "Retrying State";
      }
      enum "total" {
        description
          "Cumulative Coverage for all the States";
      }
    }
    description
      "LDP Session State";
  }

  typedef Rcmd-protocol-id {
    type enumeration {
      enum "ospf" {
        value 0;
        description
          "OSPF protocol";
      }
      enum "isis" {
        value 1;
        description
          "ISIS Prrotocol";
      }
      enum "na" {
        value 2;
        description
          "Max NA";
      }
    }
    description
      "Protocol Info";
  }

  typedef Rcmd-show-ldp-neighbour-status {
    type enumeration {
      enum "down" {
        description
          "Down State";
      }
      enum "up" {
        description
          "Up State";
      }
    }
    description
      "LDP Adjacency Session Status";
  }

  typedef Rcmd-ldp-event {
    type enumeration {
      enum "neighbor" {
        value 1;
        description
          "Neighbor Event";
      }
      enum "adjacency" {
        value 2;
        description
          "Adjacency Event";
      }
    }
    description
      "Type of LDP Event";
  }

  typedef Rcmd-show-mem {
    type enumeration {
      enum "standard" {
        value 0;
        description
          "Standard type";
      }
      enum "chunk" {
        value 1;
        description
          "Chunk type";
      }
      enum "edm" {
        value 2;
        description
          "EDM type";
      }
      enum "string" {
        value 3;
        description
          "String type";
      }
      enum "static" {
        value 4;
        description
          "Static type";
      }
      enum "unknown" {
        value 5;
        description
          "Unknown type";
      }
    }
    description
      "RCMD Memory Manager type";
  }

  typedef Rcmd-isis-spf {
    type enumeration {
      enum "full" {
        value 0;
        description
          "Full";
      }
      enum "incremental" {
        value 1;
        description
          "Incremental";
      }
      enum "next-hop" {
        value 2;
        description
          "Next hop calculation";
      }
      enum "partial-route" {
        value 3;
        description
          "Partial route calculation";
      }
    }
    description
      "Type of an ISIS SPF run";
  }

  typedef Rcmd-isis-lvl {
    type enumeration {
      enum "l1" {
        value 0;
        description
          "Level 1";
      }
      enum "l2" {
        value 1;
        description
          "Level 2";
      }
    }
    description
      "Type of an ISIS Level";
  }

  typedef Rcmd-bag-enbl-dsbl {
    type enumeration {
      enum "dsbl" {
        value 0;
        description
          "Disabled";
      }
      enum "enbl" {
        value 1;
        description
          "Enabled";
      }
    }
    description
      "status enum";
  }

  typedef Rcmd-show-node {
    type enumeration {
      enum "unknown" {
        value 0;
        description
          "Unknown Type";
      }
      enum "lc" {
        value 1;
        description
          "LC Type";
      }
      enum "rp" {
        value 2;
        description
          "RP Type";
      }
    }
    description
      "Type of Node";
  }

  typedef Rcmd-bool-yes-no {
    type enumeration {
      enum "no" {
        value 0;
        description
          "No";
      }
      enum "yes" {
        value 1;
        description
          "Yes";
      }
    }
    description
      "Boolean enum";
  }

  typedef Rcmd-show-prcs-state {
    type enumeration {
      enum "success" {
        value 0;
        description
          "Success";
      }
      enum "cpu" {
        value 1;
        description
          "Cpu overload";
      }
      enum "memory" {
        value 2;
        description
          "Memory overload";
      }
    }
    description
      "Post Processing Info";
  }

  typedef Rcmd-bag-enable-disable {
    type enumeration {
      enum "disable" {
        value 0;
        description
          "Disabled";
      }
      enum "enable" {
        value 1;
        description
          "Enabled";
      }
    }
    description
      "status enum";
  }

  typedef Rcmd-show-ipfrr-lfa {
    type enumeration {
      enum "none" {
        description
          "No IP Frr LFA Type ";
      }
      enum "local" {
        description
          "IP Frr Local LFA";
      }
      enum "remote" {
        description
          "IP Frr Remote LFA";
      }
    }
    description
      "IP Frr LFA Types";
  }

  typedef Rcmd-show-route-path-change {
    type enumeration {
      enum "primary" {
        value 0;
        description
          "Primary path is changed";
      }
      enum "backup" {
        value 1;
        description
          "Backup path is changed";
      }
    }
    description
      "Type of route change";
  }

  typedef Rcmd-linecard-speed {
    type enumeration {
      enum "other" {
        value 0;
        description
          "Other linecard";
      }
      enum "fastest" {
        value 1;
        description
          "Fastest linecard";
      }
      enum "slowest" {
        value 2;
        description
          "Slowest linecard";
      }
    }
    description
      "Comparative speed of programming on linecard";
  }

  typedef Rcmd-ls-change {
    type enumeration {
      enum "new" {
        value 0;
        description
          "Added";
      }
      enum "delete" {
        value 1;
        description
          "Deleted";
      }
      enum "modify" {
        value 2;
        description
          "Modified";
      }
      enum "noop" {
        value 3;
        description
          "No operation";
      }
    }
    description
      "Type of change";
  }

  typedef Rcmd-lsa {
    type enumeration {
      enum "unknown" {
        value 0;
        description
          "Invalid LSA";
      }
      enum "router" {
        value 1;
        description
          "Router LSA";
      }
      enum "network" {
        value 2;
        description
          "Network LSA";
      }
      enum "summary" {
        value 3;
        description
          "Summary LSA";
      }
      enum "asbr" {
        value 4;
        description
          "ASBR LSA";
      }
      enum "external" {
        value 5;
        description
          "External LSA";
      }
      enum "multicast" {
        value 6;
        description
          "Multicast LSA";
      }
      enum "nssa" {
        value 7;
        description
          "NSSA LSA";
      }
    }
    description
      "Type of LSA";
  }

  typedef Rcmd-spf-state {
    type enumeration {
      enum "complete" {
        value 0;
        description
          "Complete";
      }
      enum "in-complete" {
        value 1;
        description
          "InComplete";
      }
      enum "collecting" {
        value 2;
        description
          "Collecting data";
      }
      enum "no-route-change" {
        value 3;
        description
          "No Route Change";
      }
    }
    description
      "Type of an ISIS Level";
  }

  typedef Rcmd-change {
    type enumeration {
      enum "none" {
        value 0;
        description
          "Invalid";
      }
      enum "add" {
        value 1;
        description
          "Added";
      }
      enum "delete" {
        value 2;
        description
          "Deleted";
      }
      enum "modify" {
        value 3;
        description
          "Modified";
      }
      enum "no-change" {
        value 4;
        description
          "No Change";
      }
    }
    description
      "Type of change";
  }

  typedef Rcmd-show-route {
    type enumeration {
      enum "ospf" {
        description
          "OSPF route init";
      }
      enum "intra" {
        description
          "OSPF Intra route";
      }
      enum "inter" {
        description
          "OSPF Inter route";
      }
      enum "ext-1" {
        description
          "OSPF External Type-1 Route";
      }
      enum "ext-2" {
        description
          "OSPF External Type-2 Route";
      }
      enum "nssa-1" {
        description
          "OSPF NSSA Type-1 Route";
      }
      enum "nssa-2" {
        description
          "OSPF NSSA Type-2 Route";
      }
      enum "isis" {
        description
          "ISIS route init";
      }
      enum "l1-summary" {
        description
          "ISIS L1 Summary";
      }
      enum "l1" {
        description
          "ISIS L1";
      }
      enum "l2-summary" {
        description
          "ISIS L2 Summary";
      }
      enum "l2" {
        description
          "ISIS L2";
      }
      enum "inter-area-summary" {
        description
          "ISIS Inter Area Summary";
      }
      enum "inter-area" {
        description
          "ISIS Inter Area";
      }
      enum "default-attached" {
        description
          "ISIS Default Route Attached";
      }
    }
    description
      "Route Types";
  }

  typedef Rcmd-priority-level {
    type enumeration {
      enum "critical" {
        value 0;
        description
          "Critical";
      }
      enum "high" {
        value 1;
        description
          "High";
      }
      enum "medium" {
        value 2;
        description
          "Medium";
      }
      enum "low" {
        value 3;
        description
          "Low";
      }
    }
    description
      "Level of priority";
  }

  grouping RCMD-SHOW-INSTANCE {
    description
      "Instance Information";
    leaf instance-id {
      type uint32;
      description
        "Instance Id";
    }
    leaf instance-state {
      type Rcmd-show-inst-state;
      description
        "Instance State";
    }
    leaf instance-deleted {
      type Rcmd-bool-yes-no;
      description
        "Instance Deleted";
    }
    leaf fwd-referenced {
      type Rcmd-bool-yes-no;
      description
        "Forward Referenced";
    }
    leaf last-update-time {
      type string;
      description
        "Last Updated Time";
    }
    leaf node-id {
      type uint32;
      description
        "Node Id";
    }
    leaf spf-offset {
      type uint32;
      description
        "SPF Offset";
    }
    leaf total-spf-nos {
      type uint32;
      description
        "Total spf nos";
    }
    leaf arch-spf-run {
      type uint32;
      description
        "spf run can be archived";
    }
    leaf route-change-spf-nos {
      type uint32;
      description
        "Route change spf nos";
    }
    leaf no-route-change-spf-nos {
      type uint32;
      description
        "No Route change spf nos";
    }
    leaf not-interested-spf-nos {
      type uint32;
      description
        "Not Interested SPF nos";
    }
    leaf total-spt-nos {
      type uint32;
      description
        "Total spt nos";
    }
  }

  grouping RCMD-SHOW-INSTANCE-NAME {
    description
      "Instance Name Information";
    leaf name {
      type string;
      description
        "Instance Name";
    }
    leaf last-update-time {
      type string;
      description
        "Last Updated Time";
    }
    leaf total-spf-nos {
      type uint32;
      description
        "Total spf nos";
    }
    leaf route-change-spf-nos {
      type uint32;
      description
        "Route change spf nos";
    }
    leaf no-route-change-spf-nos {
      type uint32;
      description
        "No Route change spf nos";
    }
    leaf not-interested-spf-nos {
      type uint32;
      description
        "Not Interested SPF nos";
    }
    leaf lsp-regeneration-count {
      type uint32;
      description
        "LSP Regen Count";
    }
    leaf lsp-regeneration-serial {
      type uint32;
      description
        "Last Serial";
    }
    leaf arch-spf-event {
      type uint32;
      description
        "Archive SPF event";
    }
    leaf arch-lsp-regeneration {
      type uint32;
      description
        "Archive Lsp regen";
    }
    list instance {
      description
        "Instance Information";
      uses RCMD-SHOW-INSTANCE;
    }
  }

  grouping RCMD-SHOW-PROCESS-INFO {
    description
      "Process Information";
    leaf protocol-id {
      type Rcmd-protocol-id;
      description
        "Protocol id";
    }
    leaf process-name {
      type string;
      description
        "Process Name";
    }
    list instance-name {
      description
        "Instance/VRF Name";
      uses RCMD-SHOW-INSTANCE-NAME;
    }
  }

  grouping RCMD-SHOW-PROCESS {
    description
      "Process Information";
    list process {
      description
        "Process Information";
      uses RCMD-SHOW-PROCESS-INFO;
    }
  }

  grouping RCMD-SHOW-INTF-EVENT {
    description
      "Interface event information";
    leaf sequence-no {
      type uint32;
      description
        "Sequence No";
    }
    leaf interface-name {
      type string;
      description
        "Interface Name";
    }
    leaf component {
      type Rcmd-show-comp-id;
      description
        "Component info";
    }
    leaf event-type {
      type Rcmd-show-intf-event;
      description
        "Event Info";
    }
    leaf event-time {
      type string;
      description
        "Event Time";
    }
    leaf primary-address {
      type inet:ipv4-address;
      description
        "Primary Address";
    }
  }

  grouping RCMD-SHOW-LDP-RLFA-LOG {
    description
      "LDP RLFA Logs information";
    leaf log-time {
      type string;
      description
        "Event Time (eg: Apr 24 13:16:04.961)";
    }
    leaf label-coverage-state {
      type Rcmd-show-ldp-conv-state;
      description
        "Label Coverage State";
    }
    leaf route-count {
      type uint32;
      description
        "Total Route Count";
    }
    leaf remote-label-count {
      type uint32;
      description
        "Remote Label Count";
    }
  }

  grouping RCMD-SHOW-LDP-RLFA-PQ-NODE {
    description
      "LDP Remote Lfa Remote Node information";
    leaf remote-node-id {
      type inet:ipv4-address;
      description
        "Remote Node ID";
    }
    leaf lsr-id {
      type inet:ipv4-address;
      description
        "Label Space Router ID";
    }
    leaf transport-address {
      type inet:ipv4-address;
      description
        "Transport Address";
    }
    leaf in-use-time {
      type string;
      description
        "Inuse time of the Session";
    }
    leaf session-state {
      type Rcmd-show-ldp-session-state;
      description
        "Session State";
    }
    leaf route-count {
      type uint32;
      description
        "Total Route Count";
    }
    leaf path-count {
      type uint32;
      description
        "Total Path Count";
    }
    leaf remote-label-count {
      type uint32;
      description
        "Remote Label Count";
    }
    leaf protected-route-count {
      type uint32;
      description
        "Protected Route Count";
    }
    leaf protected-path-count {
      type uint32;
      description
        "Protected Path Count";
    }
  }

  grouping RCMD-SHOW-LDP-RLFA-STAT {
    description
      "LDP RLFA Session Statistics information";
    leaf session-state {
      type Rcmd-show-ldp-session-state;
      description
        "Session State";
    }
    leaf session-count {
      type uint32;
      description
        "LDP Session Count";
    }
    leaf route-count {
      type uint32;
      description
        "Total Route Count";
    }
    leaf path-count {
      type uint32;
      description
        "Total Path Count";
    }
    leaf remote-label-count {
      type uint32;
      description
        "Remote Label Count";
    }
    leaf protected-route-count {
      type uint32;
      description
        "Protected Route Count";
    }
    leaf protected-path-count {
      type uint32;
      description
        "Protected Path Count";
    }
  }

  grouping RCMD-SHOW-LDP-RLFA-EVENT {
    description
      "LDP RLFA information";
    leaf event-id-xr {
      type uint32;
      description
        "LDP-rLFA Event ID";
    }
    leaf end-of-calculation-time {
      type string;
      description
        "End of IGP LFA Calculation Time (eg: Apr 24 13
         :16:04.961)";
    }
    leaf igp-protocol {
      type Rcmd-protocol-id;
      description
        "IGP Protocol";
    }
    leaf process-name {
      type string;
      description
        "Process Name";
    }
    leaf ipfrr-event-id {
      type uint32;
      description
        "IGP IP-FRR Event ID (ref:
         rcmd_show_ipfrr_event_info(EventID))";
    }
    leaf below-threshold {
      type boolean;
      description
        "Coverage Below Threshold";
    }
    list session-statistic {
      description
        "RLFA Statistics categorized by session state";
      uses RCMD-SHOW-LDP-RLFA-STAT;
    }
    list remote-node {
      description
        "Remote Node Information";
      uses RCMD-SHOW-LDP-RLFA-PQ-NODE;
    }
    list logs {
      description
        "Logs Information";
      uses RCMD-SHOW-LDP-RLFA-LOG;
    }
  }

  grouping RCMD-SHOW-LDP-SESSION-EVENT {
    description
      "LDP Session Event";
    leaf event-id-xr {
      type uint32;
      description
        "Event ID";
    }
    leaf event-type {
      type Rcmd-ldp-event;
      description
        "Type of event";
    }
    leaf event-time {
      type string;
      description
        "Event Time";
    }
    leaf lsr-id {
      type inet:ipv4-address;
      description
        "Label Space Router ID";
    }
    leaf interface-name {
      type string;
      description
        "Interface Name";
    }
    leaf address {
      type inet:ipv4-address;
      description
        "transport address or adjacency address";
    }
    leaf state {
      type Rcmd-show-ldp-neighbour-status;
      description
        "Adjacency Session Status";
    }
  }

  grouping RCMD-SHOW-STRING-MEMORY-INFO {
    description
      "string memory Information";
    leaf size {
      type uint32;
      description
        "Size of the block";
    }
    leaf total {
      type uint32;
      description
        "Total request";
    }
    leaf success {
      type uint32;
      description
        "Cache-hit success";
    }
    leaf failure {
      type uint32;
      description
        "Cache-hit failure";
    }
  }

  grouping RCMD-SHOW-EDM-MEMORY-INFO {
    description
      "edm memory Information";
    leaf size {
      type uint32;
      description
        "Size of the block";
    }
    leaf total {
      type uint32;
      description
        "Total request";
    }
    leaf success {
      type uint32;
      description
        "Cache-hit success";
    }
    leaf failure {
      type uint32;
      description
        "Cache-hit failure";
    }
  }

  grouping RCMD-SHOW-MEMORY-INFO {
    description
      "memory Information";
    leaf structure-name {
      type string;
      description
        "Structure Name";
    }
    leaf size {
      type uint32;
      description
        "Size of the datastructure";
    }
    leaf current-count {
      type uint32;
      description
        "Current Count";
    }
    leaf alloc-fails {
      type uint32;
      description
        "Allocation Fails";
    }
    leaf alloc-count {
      type uint32;
      description
        "Allocated count";
    }
    leaf freed-count {
      type uint32;
      description
        "Freed Count";
    }
    leaf memory-type {
      type Rcmd-show-mem;
      description
        "Memory Type";
    }
  }

  grouping RCMD-SHOW-MEMORY {
    description
      "Memory Information";
    list memory-info {
      description
        "Memory Info";
      uses RCMD-SHOW-MEMORY-INFO;
    }
    list edm-memory-info {
      description
        "Memory Info";
      uses RCMD-SHOW-EDM-MEMORY-INFO;
    }
    list string-memory-info {
      description
        "Memory Info";
      uses RCMD-SHOW-STRING-MEMORY-INFO;
    }
  }

  grouping RCMD-REGEN-LSP-INFO {
    description
      "Regenerated LSP information";
    leaf serial-number-xr {
      type uint32;
      description
        "Serial Number of the session event";
    }
    leaf lsp-id {
      type string;
      description
        "LSP ID";
    }
    leaf sequence-number {
      type uint32;
      description
        "Sequence Number";
    }
    leaf reception-time {
      type string;
      description
        "Reception Time on router (in hh:mm:ss.msec)";
    }
    leaf isis-level {
      type Rcmd-isis-lvl;
      description
        "ISIS Level";
    }
    leaf spf-run-number {
      type uint32;
      description
        "SPF Run Number";
    }
    leaf reason {
      type string;
      description
        "Trigger reasons for LSP regeneration. Example:
         pr^ - periodic, cr^ - clear (Check the
         documentation for the entire list)";
    }
  }

  grouping RCMD-LSP-INFO {
    description
      "LSP information";
    leaf lsp-id {
      type string;
      description
        "LSP ID";
    }
    leaf sequence-number {
      type uint32;
      description
        "Sequence Number";
    }
    leaf change-type {
      type Rcmd-ls-change;
      description
        "Add, Delete, Modify";
    }
    leaf reception-time {
      type string;
      description
        "Reception Time on router (in hh:mm:ss.msec)";
    }
  }

  grouping RCMD-ISIS-SPF-RUN-SUMMARY {
    description
      "SPF summary information";
    leaf topology {
      type uint32;
      description
        "Topology index (multi-topology)";
    }
    leaf isis-level {
      type Rcmd-isis-lvl;
      description
        "ISIS Level";
    }
    leaf type {
      type Rcmd-isis-spf;
      description
        "Type of SPF";
    }
    leaf threshold-exceeded {
      type boolean;
      description
        "Threshold exceeded";
    }
    leaf state {
      type Rcmd-spf-state;
      description
        "SPF state";
    }
    leaf is-data-complete {
      type boolean;
      description
        "Whether the event has all information";
    }
    leaf trigger-time {
      type string;
      description
        "Trigger time (in hh:mm:ss.msec)";
    }
    leaf duration {
      type string;
      description
        "Duration of SPF calculation (in ss.msec)";
    }
    leaf total-lsp-changes {
      type uint16;
      description
        "Total number of LSP changes processed";
    }
    list priority-summary {
      description
        "Convergence information summary on per-priority
         basis";
      uses RCMD-PRIORITY-SUMMARY;
    }
  }

  grouping RCMD-ISIS-SPF-RUN {
    description
      "ISIS SPF run information";
    container spf-summary {
      description
        "SPF summary information";
      uses RCMD-ISIS-SPF-RUN-SUMMARY;
    }
    container node-statistics {
      description
        "SPF Node statistics";
      uses RCMD-STAT;
    }
    leaf start-time {
      type string;
      description
        "Start time (offset from event trigger time in ss
         .msec)";
    }
    leaf wait-time {
      type uint32;
      description
        "Wait time applied at SPF schedule (in msec)";
    }
    leaf reason {
      type string;
      description
        "Trigger reasons for SPF run. Example: pr^ -
         periodic, cr^ - clear (Check the documentation
         for the entire list)";
    }
    list trigger-lsp {
      description
        "Trigger LSP";
      uses RCMD-LSP-INFO;
    }
    list priority {
      description
        "Convergence information on per-priority basis";
      uses RCMD-PRIORITY;
    }
    list lsp-processed {
      description
        "List of LSP changes processed";
      uses RCMD-LSP-INFO;
    }
    list lsp-regenerated {
      description
        "List of LSP regenerated";
      uses RCMD-REGEN-LSP-INFO;
    }
  }

  grouping RCMD-SHOW-NODE-INFO {
    description
      "Node Information";
    leaf node-id {
      type uint32;
      description
        "Node Id";
    }
    leaf node-name {
      type string;
      description
        "Node Name";
    }
    leaf rack-id {
      type uint32;
      description
        "Rack Id";
    }
    leaf last-update-time {
      type string;
      description
        "Last Updated Time";
    }
    leaf fwd-referenced {
      type Rcmd-bool-yes-no;
      description
        "Forward Referenced";
    }
    leaf node-type {
      type Rcmd-show-node;
      description
        "Node Type";
    }
    leaf software-state {
      type uint32;
      description
        "Software State";
    }
    leaf card-state {
      type uint32;
      description
        "Card State";
    }
    leaf node-state {
      type Rcmd-bool-yes-no;
      description
        "Node State";
    }
    leaf status {
      type Rcmd-bag-enbl-dsbl;
      description
        "Status";
    }
    leaf diag-mode {
      type uint32;
      description
        "Diag Mode";
    }
    leaf redundancy-state {
      type uint32;
      description
        "Redundancy State";
    }
  }

  grouping RCMD-SHOW-NODE {
    description
      "Node Information";
    list node-information {
      description
        "Node Info";
      uses RCMD-SHOW-NODE-INFO;
    }
  }

  grouping RCMD-SHOW-LTRACE {
    description
      "Trace Information";
    leaf trace-name {
      type string;
      description
        "Configured Hostname";
    }
    leaf total-stats {
      type uint32;
      description
        "Server Total Status";
    }
    leaf last-run-stats {
      type uint32;
      description
        "Server Last Run Status";
    }
    leaf error-stats {
      type uint32;
      description
        "Server Error Status";
    }
  }

  grouping RCMD-SHOW-SERVER-DETAIL {
    description
      "RCMD server detailed information";
    leaf overload-suspend {
      type uint32;
      description
        "Overload suspend";
    }
    leaf memory-suspend {
      type uint32;
      description
        "Memory Suspend";
    }
    list trace-information {
      description
        "Trace Information";
      uses RCMD-SHOW-LTRACE;
    }
  }

  grouping RCMD-SHOW-CFG-PROTO-PRIO {
    description
      "Priority Level Configuration";
    leaf priority-name {
      type Rcmd-priority-level;
      description
        "Priority Level";
    }
    leaf threshold {
      type uint32;
      description
        "threshold value";
    }
    leaf disable {
      type Rcmd-bool-yes-no;
      description
        "Enable/Disable cfg";
    }
  }

  grouping RCMD-SHOW-CFG-PROTO {
    description
      "Protocol Configuration";
    leaf protocol-name {
      type string;
      description
        "Protocol Name";
    }
    list priority {
      description
        "Priority level configuration";
      uses RCMD-SHOW-CFG-PROTO-PRIO;
    }
  }

  grouping RCMD-SHOW-SERVER {
    description
      "RCMD Server Information";
    leaf host-name {
      type string;
      description
        "Configured Hostname";
    }
    leaf status {
      type Rcmd-bag-enable-disable;
      description
        "Server Status";
    }
    leaf max-events {
      type uint32;
      description
        "Maximum Events";
    }
    leaf event-buffer-size {
      type uint32;
      description
        "Event Buffer Size";
    }
    leaf monitoring-interval {
      type uint32;
      description
        "Configured Monitor Interval";
    }
    leaf next-interval {
      type uint32;
      description
        "Time for next processing";
    }
    leaf max-interface-count {
      type uint32;
      description
        "Max Interface events count";
    }
    leaf interface-count {
      type uint32;
      description
        "Interface events count";
    }
    leaf node-rp-count {
      type uint32;
      description
        "RP count";
    }
    leaf node-lc-count {
      type uint32;
      description
        "LC count";
    }
    leaf diag-node-count {
      type uint32;
      description
        "Diag Node count";
    }
    leaf disabled-node-count {
      type uint32;
      description
        "Disabled Node count";
    }
    leaf in-active-node-count {
      type uint32;
      description
        "Disabled Node count";
    }
    leaf last-process-start-time {
      type string;
      description
        "Last Processing Start Time";
    }
    leaf last-process-duration {
      type string;
      description
        "Last Processing Duration";
    }
    leaf last-process-state {
      type Rcmd-show-prcs-state;
      description
        "Process state";
    }
    leaf process-count {
      type uint32;
      description
        "Post Processing count";
    }
    leaf spf-process-count {
      type uint32;
      description
        "SPF Processing count";
    }
    leaf reports-archive-path {
      type string;
      description
        "Reports Archival Path";
    }
    leaf reports-archive-node {
      type string;
      description
        "Reports Archival Node (Applicable for local
         location)";
    }
    leaf last-archival-status {
      type string;
      description
        "Last Archival Status";
    }
    leaf last-archival-error {
      type string;
      description
        "Last Archival Error";
    }
    leaf last-archival-error-time {
      type string;
      description
        "Last Archival Status";
    }
    leaf archive-count {
      type uint32;
      description
        "Archive Count";
    }
    leaf diagnostics-archive-path {
      type string;
      description
        "Diagnostics Archival Path";
    }
    leaf diagnostics-archive-node {
      type string;
      description
        "Diagnostics Archival Node (Applicable for local
         location)";
    }
    list protocol-config {
      description
        "Protocol level configuration";
      uses RCMD-SHOW-CFG-PROTO;
    }
    list server-detail {
      description
        "Detailed Information";
      uses RCMD-SHOW-SERVER-DETAIL;
    }
  }

  grouping RCMD-SHOW-TYPE357-STATS-INFO {
    description
      "prefix statistics information";
    leaf inter-area-routes {
      type uint32;
      description
        "Total Inter-Area Routes";
    }
    leaf inter-area-added {
      type uint32;
      description
        "Total IA Routes Added";
    }
    leaf inter-area-modified {
      type uint32;
      description
        "Total IA Routes Modified";
    }
    leaf inter-area-deleted {
      type uint32;
      description
        "Total IA Routes Deleted";
    }
    leaf inter-area-critical {
      type uint32;
      description
        "Total IA Routes Critical";
    }
    leaf inter-area-high {
      type uint32;
      description
        "Total IA Routes High";
    }
    leaf inter-area-medium {
      type uint32;
      description
        "Total IA Routes Medium";
    }
    leaf inter-area-low {
      type uint32;
      description
        "Total IA Routes Low";
    }
    leaf external-routes {
      type uint32;
      description
        "Total External Routes";
    }
    leaf external-added {
      type uint32;
      description
        "Total Ext Routes Added";
    }
    leaf external-modified {
      type uint32;
      description
        "Total Ext Routes Modified";
    }
    leaf external-deleted {
      type uint32;
      description
        "Total Ext Routes Deleted";
    }
    leaf external-critical {
      type uint32;
      description
        "Total Ext Routes Critical";
    }
    leaf external-high {
      type uint32;
      description
        "Total Ext Routes High";
    }
    leaf external-medium {
      type uint32;
      description
        "Total Ext Routes Medium";
    }
    leaf external-low {
      type uint32;
      description
        "Total Ext Routes Low";
    }
  }

  grouping RCMD-SHOW-PREFIX-LC-INFO {
    description
      "Linecard timeline details";
    leaf node-name {
      type string;
      description
        "Linecard node name";
    }
    leaf speed {
      type Rcmd-linecard-speed;
      description
        "Relative convergence speed";
    }
    leaf fib-complete {
      type string;
      description
        "Completion point of FIB";
    }
  }

  grouping RCMD-SHOW-PREFIX-TIMELINE {
    description
      "Timeline information details at each component
       level";
    leaf route-origin {
      type string;
      description
        "Route origin (routing protocol)";
    }
    leaf ri-bv4-enter {
      type string;
      description
        "Entry point of IPv4 RIB";
    }
    leaf ri-bv4-exit {
      type string;
      description
        "Exit point from IPv4 RIB to FIBs";
    }
    leaf ri-bv4-redistribute {
      type string;
      description
        "Route Redistribute point from IPv4 RIB to LDP";
    }
    leaf ldp-enter {
      type string;
      description
        "Entry point of LDP";
    }
    leaf ldp-exit {
      type string;
      description
        "Exit point of LDP to LSD";
    }
    leaf lsd-enter {
      type string;
      description
        "Entry point of LSD";
    }
    leaf lsd-exit {
      type string;
      description
        "Exit point of LSD to FIBs";
    }
    list lc-ip {
      description
        "List of Linecards' completion point for IP
         routes";
      uses RCMD-SHOW-PREFIX-LC-INFO;
    }
    list lc-mpls {
      description
        "List of Linecards' completion point for MPLS
         labels";
      uses RCMD-SHOW-PREFIX-LC-INFO;
    }
  }

  grouping RCMD-SHOW-IPFRR-LFA-PATH {
    description
      "IP Frr Path information";
    leaf lfa-type {
      type Rcmd-show-ipfrr-lfa;
      description
        "Type of LFA";
    }
    leaf interface-name {
      type string;
      description
        "Interface Name";
    }
    leaf neighbour-address {
      type inet:ipv4-address;
      description
        "Nexthop Address";
    }
    leaf change-type {
      type Rcmd-change;
      description
        "Event Add/Delete";
    }
    leaf path-metric {
      type uint32;
      description
        "Path Metric";
    }
    leaf remote-node-id {
      type inet:ipv4-address;
      description
        "Remote Node ID, in case of Remote LFA";
    }
  }

  grouping RCMD-SHOW-PREFIX-PATH {
    description
      "Prefix Path information";
    leaf interface-name {
      type string;
      description
        "Interface Name";
    }
    leaf neighbour-address {
      type inet:ipv4-address;
      description
        "Nexthop Address";
    }
    leaf change-type {
      type Rcmd-change;
      description
        "Event Add/Delete";
    }
    leaf path-metric {
      type uint32;
      description
        "Path Metric";
    }
    list lfa-path {
      description
        "Backup Path Informatoin";
      uses RCMD-SHOW-IPFRR-LFA-PATH;
    }
  }

  grouping RCMD-SHOW-PREFIX-EVENT {
    description
      "Event information";
    container ip-convergence-time {
      description
        "Convergence time for IP route programming";
      uses RCMD-TIMESTAMP;
    }
    container mpls-convergence-time {
      description
        "Convergence time for MPLS label programming";
      uses RCMD-TIMESTAMP;
    }
    leaf prefix {
      type inet:ipv4-address;
      description
        "Prefix";
    }
    leaf prefix-lenth {
      type uint32;
      description
        "Prefix length";
    }
    leaf spf-run-no {
      type uint32;
      description
        "Referenced SPF Run No (0 - Not Applicable)";
    }
    leaf ipfrr-event-id {
      type uint32;
      description
        "Referenced IP-FRR Event ID (0 - Not Applicable)";
    }
    leaf threshold-exceeded {
      type boolean;
      description
        "Threshold exceeded";
    }
    leaf priority {
      type Rcmd-priority-level;
      description
        "Event processed priority";
    }
    leaf change-type {
      type Rcmd-change;
      description
        "Event Add/Delete";
    }
    leaf route-type {
      type Rcmd-show-route;
      description
        "Route Type intra/inter/l1/l2";
    }
    leaf route-path-change-type {
      type Rcmd-show-route-path-change;
      description
        "Route Path Change Type";
    }
    leaf cost {
      type uint32;
      description
        "Protocol route cost";
    }
    leaf trigger-time {
      type string;
      description
        "Event trigger time";
    }
    list path {
      description
        "Path information";
      uses RCMD-SHOW-PREFIX-PATH;
    }
    list trigger-lsa {
      description
        "LSA that triggered this event";
      uses RCMD-LSA-INFO;
    }
    list time-line {
      description
        "Timeline information";
      uses RCMD-SHOW-PREFIX-TIMELINE;
    }
    list lsa-processed {
      description
        "List of LSAs processed";
      uses RCMD-LSA-INFO;
    }
  }

  grouping RCMD-IAEXT-PRIORITY-SUMMARY {
    description
      "Priority Summary for Inter-area & external
       calculation";
    container route-statistics {
      description
        "Route statistics";
      uses RCMD-STAT;
    }
    container ip-convergence-time {
      description
        "Convergence time for IP route programming";
      uses RCMD-TIMESTAMP;
    }
    container mpls-convergence-time {
      description
        "Convergence time for MPLS label programming";
      uses RCMD-TIMESTAMP;
    }
    leaf level {
      type Rcmd-priority-level;
      description
        "Critical, High, Medium or Low";
    }
    leaf threshold-exceeded {
      type boolean;
      description
        "Threshold exceeded";
    }
    leaf type3ls-as {
      type uint32;
      description
        "Number of Type 3 LSA";
    }
    leaf type4ls-as {
      type uint32;
      description
        "Number of Type 4 LSA";
    }
    leaf type57ls-as {
      type uint32;
      description
        "Number of Type 5/7 LSA";
    }
  }

  grouping RCMD-IAEXT-PRIORITY {
    description
      "Convergence information for a priority in
       Inter-area and external calculation";
    container priority-summary {
      description
        "Summary of the priority";
      uses RCMD-IAEXT-PRIORITY-SUMMARY;
    }
    list convergence-timeline {
      description
        "Convergence timeline details";
      uses RCMD-TIMELINE;
    }
    list leaf-networks-added {
      description
        "List of Leaf Networks Added";
      uses RCMD-NETWORK;
    }
    list leaf-networks-deleted {
      description
        "List of Leaf Networks Deleted";
      uses RCMD-NETWORK;
    }
  }

  grouping RCMD-OSPF-IAEXT-INFO {
    description
      "Inter-area & external calculation information";
    list priority {
      description
        "Convergence information on a per-priority basis";
      uses RCMD-IAEXT-PRIORITY;
    }
  }

  grouping RCMD-NETWORK {
    description
      "Network";
    leaf address {
      type inet:ipv4-address;
      description
        "IP address";
    }
    leaf net-mask {
      type uint8;
      description
        "Mask";
    }
  }

  grouping RCMD-LC-INFO {
    description
      "Linecard timeline details";
    container fib-complete {
      description
        "Completion point of FIB";
      uses RCMD-TIME;
    }
    leaf node-name {
      type string;
      description
        "Linecard node name";
    }
    leaf speed {
      type Rcmd-linecard-speed;
      description
        "Relative convergence speed";
    }
  }

  grouping RCMD-TIME {
    description
      "The timestamps for each module";
    leaf start-time {
      type string;
      description
        "First route process time relative to event
         trigger time (in ss.msec)";
    }
    leaf end-time {
      type string;
      description
        "Last route process time relative to event
         trigger time (in ss.msec)";
    }
    leaf duration {
      type string;
      description
        "Duration of processing (in ss.msec)";
    }
  }

  grouping RCMD-TIMELINE {
    description
      "Timeline information details at each component
       level";
    container route-origin {
      description
        "Route origin (routing protocol)";
      uses RCMD-TIME;
    }
    container ri-bv4-enter {
      description
        "Entry point of IPv4 RIB";
      uses RCMD-TIME;
    }
    container ri-bv4-exit {
      description
        "Exit point from IPv4 RIB to FIBs";
      uses RCMD-TIME;
    }
    container ri-bv4-redistribute {
      description
        "Route Redistribute point from IPv4 RIB to LDP";
      uses RCMD-TIME;
    }
    container ldp-enter {
      description
        "Entry point of LDP";
      uses RCMD-TIME;
    }
    container ldp-exit {
      description
        "Exit point of LDP to LSD";
      uses RCMD-TIME;
    }
    container lsd-enter {
      description
        "Entry point of LSD";
      uses RCMD-TIME;
    }
    container lsd-exit {
      description
        "Exit point of LSD to FIBs";
      uses RCMD-TIME;
    }
    list lc-ip {
      description
        "List of Linecards' completion point for IP
         routes";
      uses RCMD-LC-INFO;
    }
    list lc-mpls {
      description
        "List of Linecards' completion point for MPLS
         labels";
      uses RCMD-LC-INFO;
    }
  }

  grouping RCMD-PRIORITY {
    description
      "Convergence information for a priority";
    container priority-summary {
      description
        "Summary of the priority";
      uses RCMD-PRIORITY-SUMMARY;
    }
    list convergence-timeline {
      description
        "Convergence timeline details";
      uses RCMD-TIMELINE;
    }
    list leaf-networks-added {
      description
        "List of Leaf Networks Added";
      uses RCMD-NETWORK;
    }
    list leaf-networks-deleted {
      description
        "List of Leaf Networks Deleted";
      uses RCMD-NETWORK;
    }
  }

  grouping RCMD-LSA-INFO {
    description
      "LSA information";
    leaf lsa-id {
      type inet:ipv4-address;
      description
        "LSA ID";
    }
    leaf sequence-number {
      type string;
      description
        "Sequence Number";
    }
    leaf lsa-type {
      type Rcmd-lsa;
      description
        "LSA type";
    }
    leaf origin-router-id {
      type inet:ipv4-address;
      description
        "Originating Router ID";
    }
    leaf change-type {
      type Rcmd-ls-change;
      description
        "Add, Delete, Modify";
    }
    leaf reception-time {
      type string;
      description
        "Reception Time on router (in hh:mm:ss.msec)";
    }
  }

  grouping RCMD-OSPF-SPT-INFO {
    description
      "Dijkstra run information";
    leaf dijkstra-run-number {
      type uint32;
      description
        "Area Dijkstra run number";
    }
    leaf area-id {
      type inet:ipv4-address;
      description
        "Area ID";
    }
    leaf threshold-exceeded {
      type boolean;
      description
        "Threshold exceeded";
    }
    leaf trigger-time {
      type string;
      description
        "Trigger time (in hh:mm:ss.msec)";
    }
    leaf start-time {
      type string;
      description
        "Start time (offset from event trigger time in ss
         .msec)";
    }
    leaf wait-time {
      type uint32;
      description
        "Wait time (offset from event trigger time in ss
         .msec)";
    }
    leaf duration {
      type string;
      description
        "Duration of Dijktra calculation (in ss.msec)";
    }
    list trigger-lsa {
      description
        "LSA that triggered the Dijkstra run";
      uses RCMD-LSA-INFO;
    }
    list priority {
      description
        "Convergence information on per-priority basis";
      uses RCMD-PRIORITY;
    }
    list lsa-processed {
      description
        "List of type 1/2 LSA changes processed";
      uses RCMD-LSA-INFO;
    }
  }

  grouping RCMD-TIMESTAMP {
    description
      "Time range";
    leaf minimum-time {
      type string;
      units "millisecond";
      description
        "Minimum time(in seconds.milliseconds)";
    }
    leaf maximum-time {
      type string;
      units "millisecond";
      description
        "Maximum time(in seconds.milliseconds)";
    }
    leaf slowest-node-name {
      type string;
      description
        "Linecard node name which took the maximum time";
    }
    leaf fastest-node-name {
      type string;
      description
        "Linecard node name which took the minimum time";
    }
  }

  grouping RCMD-SHOW-FRR-STAT {
    description
      "Priority Summary for Frr Statistics";
    leaf total-routes {
      type uint32;
      description
        "Total Number of Routes";
    }
    leaf fully-protected-routes {
      type uint32;
      description
        "Fully Protected Routes";
    }
    leaf partially-protected-routes {
      type uint32;
      description
        "Partially Protected Routes";
    }
    leaf coverage {
      type string;
      units "percentage";
      description
        "Coverage in percentage";
    }
  }

  grouping RCMD-STAT {
    description
      "Statistics";
    leaf adds {
      type uint32;
      description
        "Added";
    }
    leaf deletes {
      type uint32;
      description
        "Deleted";
    }
    leaf modifies {
      type uint32;
      description
        "Modified";
    }
    leaf reachables {
      type uint32;
      description
        "Reachable";
    }
    leaf unreachables {
      type uint32;
      description
        "Unreachable";
    }
    leaf touches {
      type uint32;
      description
        "Touched";
    }
  }

  grouping RCMD-PRIORITY-SUMMARY {
    description
      "Summary of convergence information for a priority";
    container route-statistics {
      description
        "Route statistics";
      uses RCMD-STAT;
    }
    container ip-convergence-time {
      description
        "Convergence time for IP route programming";
      uses RCMD-TIMESTAMP;
    }
    container mpls-convergence-time {
      description
        "Convergence time for MPLS label programming";
      uses RCMD-TIMESTAMP;
    }
    leaf level {
      type Rcmd-priority-level;
      description
        "Critical, High, Medium or Low";
    }
    leaf threshold-exceeded {
      type boolean;
      description
        "Threshold exceeded";
    }
    list frr-statistic {
      description
        "Fast Re-Route Statistics";
      uses RCMD-SHOW-FRR-STAT;
    }
  }

  grouping RCMD-OSPF-SPF-RUN-SUMMARY {
    description
      "SPF summary information";
    leaf state {
      type Rcmd-spf-state;
      description
        "SPF state";
    }
    leaf is-data-complete {
      type boolean;
      description
        "Whether the event has all information";
    }
    leaf threshold-exceeded {
      type boolean;
      description
        "Threshold exceeded";
    }
    leaf trigger-time {
      type string;
      description
        "Trigger time (in hh:mm:ss.msec)";
    }
    leaf start-time {
      type string;
      description
        "Start time (offset from event trigger time in ss
         .msec)";
    }
    leaf duration {
      type string;
      description
        "Duration of complete SPF calculation (in ss
         .msec)";
    }
    leaf total-dijkstra-runs {
      type uint16;
      description
        "Total number of Dijkstra runs";
    }
    leaf total-inter-area-and-external-batches {
      type uint16;
      description
        "Total number of inter-area/external computation
         batches";
    }
    leaf total-type12lsa-changes {
      type uint16;
      description
        "Total number of Type 1/2 LSA changes processed";
    }
    leaf total-type357lsa-changes {
      type uint16;
      description
        "Total number of Type 3/5/7 LSA changes processed";
    }
    list priority-summary {
      description
        "Convergence information summary on per-priority
         basis";
      uses RCMD-PRIORITY-SUMMARY;
    }
  }

  grouping RCMD-OSPF-SPF-RUN {
    description
      "SPF run information";
    container spf-summary {
      description
        "SPF summary information";
      uses RCMD-OSPF-SPF-RUN-SUMMARY;
    }
    list dijkstra-run {
      description
        "List of Dijkstra runs";
      uses RCMD-OSPF-SPT-INFO;
    }
    list inter-area-and-external {
      description
        "Inter-area & external calculation information";
      uses RCMD-OSPF-IAEXT-INFO;
    }
  }

  grouping RCMD-SHOW-PREFIX-INFO {
    description
      "prefix statistics information";
    leaf prefix {
      type inet:ipv4-address;
      description
        "Prefix";
    }
    leaf prefix-lenth {
      type uint32;
      description
        "Prefix length";
    }
    leaf last-event-time {
      type string;
      description
        "Last event trigger time";
    }
    leaf last-priority {
      type Rcmd-priority-level;
      description
        "Last event processed priority";
    }
    leaf last-route-type {
      type Rcmd-show-route;
      description
        "Last event Route Type";
    }
    leaf last-change-type {
      type Rcmd-change;
      description
        "Last event Add/Delete";
    }
    leaf last-cost {
      type uint32;
      description
        "Last Known Cost";
    }
    leaf critical-priority {
      type uint32;
      description
        "No. of times processed under Critical Priority";
    }
    leaf high-priority {
      type uint32;
      description
        "No. of times processed under High Priority";
    }
    leaf medium-priority {
      type uint32;
      description
        "No. of times processed under Medium Priority";
    }
    leaf low-priority {
      type uint32;
      description
        "No. of times processed under Low Priority";
    }
    leaf add-count {
      type uint32;
      description
        "No. of times route gets Added";
    }
    leaf modify-count {
      type uint32;
      description
        "No. of times route gets Deleted";
    }
    leaf delete-count {
      type uint32;
      description
        "No. of times route gets Deleted";
    }
    leaf threshold-exceed-count {
      type uint32;
      description
        "No. of times threshold got exceeded";
    }
  }

  grouping RCMD-SHOW-IPFRR-PATH {
    description
      "IP-Frr Remote Node Primary Path information";
    leaf interface-name {
      type string;
      description
        "Interface Name";
    }
    leaf neighbour-address {
      type inet:ipv4-address;
      description
        "Nexthop Address";
    }
  }

  grouping RCMD-SHOW-IPFRR-RLFA-PQ-NODE {
    description
      "IP-Frr Remote Node information";
    leaf remote-node-id {
      type inet:ipv4-address;
      description
        "Remote-LFA Node ID";
    }
    leaf interface-name {
      type string;
      description
        "Interface Name";
    }
    leaf neighbour-address {
      type inet:ipv4-address;
      description
        "Nexthop Address";
    }
    leaf path-count {
      type uint32;
      description
        "Number of paths protected by this Remote Node";
    }
    leaf in-use-time {
      type string;
      description
        "Inuse time of the Remote Node (eg: Apr 24 13:16
         :04.961)";
    }
    list primary-path {
      description
        "Protected Primary Paths";
      uses RCMD-SHOW-IPFRR-PATH;
    }
  }

  grouping RCMD-SHOW-IPFRR-STATS {
    description
      "IP-Frr statistics information";
    leaf priority {
      type Rcmd-priority-level;
      description
        "Priority";
    }
    leaf total-routes {
      type uint32;
      description
        "Total Number of Routes";
    }
    leaf fully-protected-routes {
      type uint32;
      description
        "Fully Protected Routes";
    }
    leaf partially-protected-routes {
      type uint32;
      description
        "Partially Protected Routes";
    }
    leaf coverage {
      type string;
      units "percentage";
      description
        "Coverage in percentage";
    }
    leaf local-lfa-coverage {
      type string;
      units "percentage";
      description
        "Local LFA Coverage in percentage";
    }
    leaf remote-lfa-coverage {
      type string;
      units "percentage";
      description
        "Remote LFA Coverage in percentage";
    }
    leaf below-threshold {
      type boolean;
      description
        "Covearge is below Configured Threshold";
    }
  }

  grouping RCMD-SHOW-IPFRR-EVENT-INFO {
    description
      "IP-Frr Run information";
    leaf event-id-xr {
      type uint32;
      description
        "IP-Frr Event ID";
    }
    leaf trigger-time {
      type string;
      description
        "Trigger time  (eg: Apr 24 13:16:04.961)";
    }
    leaf trigger-spf-run {
      type uint32;
      description
        "IP-Frr Triggered reference SPF Run Number";
    }
    leaf wait-time {
      type uint32;
      units "millisecond";
      description
        "Waiting Time (in milliseconds)";
    }
    leaf start-time-offset {
      type string;
      units "millisecond";
      description
        "Start Time offset from trigger time (in
         milliseconds)";
    }
    leaf duration {
      type string;
      units "millisecond";
      description
        "Duration for the calculation (in milliseconds)";
    }
    leaf completed-spf-run {
      type uint32;
      description
        "IP-Frr Completed reference SPF Run Number";
    }
    leaf total-routes {
      type uint32;
      description
        "Cumulative Number of Routes for all priorities";
    }
    leaf fully-protected-routes {
      type uint32;
      description
        "Cumulative Number of Fully Protected Routes";
    }
    leaf partially-protected-routes {
      type uint32;
      description
        "Cumulative Number of Partially Protected Routes";
    }
    leaf coverage {
      type string;
      units "percentage";
      description
        "Coverage in percentage for all priorities";
    }
    list ipfrr-statistic {
      description
        "IP-Frr Statistics categorized by priority";
      uses RCMD-SHOW-IPFRR-STATS;
    }
    list remote-node {
      description
        "Remote Node Information";
      uses RCMD-SHOW-IPFRR-RLFA-PQ-NODE;
    }
  }
}
