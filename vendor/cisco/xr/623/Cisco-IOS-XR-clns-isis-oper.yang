module Cisco-IOS-XR-clns-isis-oper {
  namespace "http://cisco.com/ns/yang/Cisco-IOS-XR-clns-isis-oper";
  prefix clns-isis-oper;

  import ietf-inet-types {
    prefix inet;
  }
  import Cisco-IOS-XR-types {
    prefix xr;
  }
  import Cisco-IOS-XR-clns-isis-datatypes {
    prefix dt1;
  }
  include Cisco-IOS-XR-clns-isis-oper-sub2 {
    revision-date 2015-11-09;
  }
  include Cisco-IOS-XR-clns-isis-oper-sub1 {
    revision-date 2015-11-09;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR clns-isis package operational data.
     
     This module contains definitions
     for the following management objects:
       isis: IS-IS operational data
     
     Copyright (c) 2013-2016 by Cisco Systems, Inc.
     All rights reserved.";

  revision 2015-11-09 {
    description
      "IOS XR 6.0 revision.";
  }

  grouping POLICY-MI {
    description
      "Common node of policy-ipv4-active,
       policy-ipv4-backup, policy-ipv6-active,
       policy-ipv6-backup";
    list policy-mi {
      key "mi-id";
      description
        "Mapping Item";
      leaf mi-id {
        type xr:Cisco-ios-xr-string;
        description
          "Mapping Item ID (0, 1, 2, ...)";
      }
      uses SRMS-MI-T-B;
    }
  }

  container isis {
    config false;
    description
      "IS-IS operational data";
    container instances {
      description
        "Per-instance operational data";
      list instance {
        key "instance-name";
        description
          "IS-IS instance";
        container neighbors {
          description
            "Neighbor table";
          list neighbor {
            description
              "A single neighbor router";
            leaf system-id {
              type xr:Osi-system-id;
              description
                "System ID";
            }
            leaf interface-name {
              type xr:Interface-name;
              description
                "Interface name";
            }
            uses ISIS-SH-NBR;
          }
        }
        container host-names {
          description
            "Hostname table";
          list host-name {
            key "system-id";
            description
              "Hostname table entry";
            leaf system-id {
              type xr:Osi-system-id;
              description
                "System ID";
            }
            uses ISIS-SH-HOST;
          }
        }
        container statistics-global {
          description
            "Per-instance statistics";
          uses ISIS-SH-TRAFFIC-GLOBAL;
        }
        container levels {
          description
            "Level table";
          list level {
            key "level";
            description
              "Per-level operational data";
            container adjacency-log {
              description
                "Log of adjacency changes within a single
                 level";
              uses ISIS-SH-ADJ-LOG-STRUC;
            }
            container lsp-table-summary {
              description
                "Summary information for one level's LSP
                 database";
              uses ISIS-SH-LSP-DB-SUMMARY;
            }
            container adjacencies {
              description
                "Adjacency table";
              list adjacency {
                description
                  "A single IS-IS adjacency";
                leaf system-id {
                  type xr:Osi-system-id;
                  description
                    "System ID";
                }
                leaf interface-name {
                  type xr:Interface-name;
                  description
                    "Interface name";
                }
                uses ISIS-SH-ADJ;
              }
            }
            container detailed-lsps {
              description
                "Detailed LSP table. Use to retrieve LSPs
                 with TLV content.";
              list detailed-lsp {
                key "lsp-id";
                description
                  "An IS-IS LSP with detailed TLV data
                   included";
                leaf lsp-id {
                  type xr:Isis-lsp-id;
                  description
                    "LSP ID";
                }
                uses ISIS-SH-LSP;
              }
            }
            container lsps {
              description
                "LSP table";
              list lsp {
                key "lsp-id";
                description
                  "An IS-IS LSP (header information only)";
                leaf lsp-id {
                  type xr:Isis-lsp-id;
                  description
                    "LSP ID";
                }
                uses ISIS-SH-LSP;
              }
            }
            container lsp-log {
              description
                "LSP-log for a single level";
              uses ISIS-SH-LSP-LOG-STRUC;
            }
            container database-log {
              description
                "Database-log for a single level";
              uses ISIS-SH-LSP-DB-LOG-STRUC;
            }
            leaf level {
              type dt1:Isis-internal-level;
              description
                "Level";
            }
          }
        }
        container topologies {
          description
            "Topology table";
          list topology {
            description
              "Per-topology data";
            container frr-summary {
              description
                "FRR summary information for a particular
                 IS-IS topology";
              uses ISIS-SH-FRR-SUMMARY;
            }
            container topology-levels {
              description
                "Per-topology level table";
              list topology-level {
                key "level";
                description
                  "Per-level topology operational data";
                container te-advertisements {
                  description
                    "TE advertisements for a single level and
                     topology. Only available within the IPv4
                     Unicast topology.";
                  uses ISIS-SH-TE-ADV;
                }
                container te-adjacency-log {
                  description
                    "TE adjacency-log for a single level and
                     topology. Only available within the IPv4
                     Unicast topology.";
                  uses ISIS-SH-TE-LOG-STRUC;
                }
                container spf-log {
                  description
                    "Log of route calculations for a single
                     level and topology";
                  uses ISIS-SH-SPF-LOG-STRUC;
                }
                container te-tunnels {
                  description
                    "TE tunnels table. Only available within
                     the IPv4 Unicast topology.";
                  list te-tunnel {
                    description
                      "A single TE tunnel advertized by IS-IS";
                    leaf system-id {
                      type xr:Osi-system-id;
                      description
                        "System ID";
                    }
                    leaf interface-name {
                      type xr:Interface-name;
                      description
                        "Interface name";
                    }
                    uses ISIS-SH-TE-TUNNEL;
                  }
                }
                container ipv4-link-topologies {
                  description
                    "IPv4 IS Topology table";
                  list ipv4-link-topology {
                    key "system-id";
                    description
                      "An IS in an IPv4 Link Topology";
                    leaf system-id {
                      type xr:Osi-system-id;
                      description
                        "System ID";
                    }
                    uses ISIS-SH-IPV4-TOPO-ENTRY;
                  }
                }
                container topology-summary {
                  description
                    "Summary information for a particular IS
                     Topology";
                  uses ISIS-SH-TOPO-SUMMARY;
                }
                container ipv6-link-topologies {
                  description
                    "IPv6 IS Topology table";
                  list ipv6-link-topology {
                    key "system-id";
                    description
                      "An IS in an IPv6 Link Topology";
                    leaf system-id {
                      type xr:Osi-system-id;
                      description
                        "System ID";
                    }
                    uses ISIS-SH-IPV6-TOPO-ENTRY;
                  }
                }
                leaf level {
                  type dt1:Isis-internal-level;
                  description
                    "Level";
                }
              }
            }
            container ipv6-routes {
              description
                "IPv6 local route";
              list ipv6-route {
                description
                  "An IPv6 route known to IS-IS";
                leaf prefix {
                  type inet:ipv6-address-no-zone;
                  description
                    "Prefix";
                }
                leaf prefix-length {
                  type dt1:Isis-ipv6-prefix-length;
                  description
                    "Prefix Length";
                }
                uses ISIS-SH-IPV6-ROUTE;
              }
            }
            container ipv6frr-backups {
              description
                "IPv6 FRR table";
              list ipv6frr-backup {
                description
                  "FRR backup for an IPv6 network";
                leaf prefix {
                  type inet:ipv6-address-no-zone;
                  description
                    "Prefix";
                }
                leaf prefix-length {
                  type dt1:Isis-ipv6-prefix-length;
                  description
                    "Prefix Length";
                }
                uses ISIS-SH-IPV6-ROUTE;
              }
            }
            container ipv4frr-backups {
              description
                "IPv4 FRR table";
              list ipv4frr-backup {
                description
                  "FRR backup for an IPv4 network";
                leaf prefix {
                  type inet:ipv4-address-no-zone;
                  description
                    "Prefix";
                }
                leaf prefix-length {
                  type dt1:Isis-ipv4-prefix-length;
                  description
                    "Prefix Length";
                }
                uses ISIS-SH-IPV4-ROUTE;
              }
            }
            container ipv4-routes {
              description
                "IPv4 local route table";
              list ipv4-route {
                description
                  "An IPv4 route known to IS-IS";
                leaf prefix {
                  type inet:ipv4-address-no-zone;
                  description
                    "Prefix";
                }
                leaf prefix-length {
                  type dt1:Isis-ipv4-prefix-length;
                  description
                    "Prefix Length";
                }
                uses ISIS-SH-IPV4-ROUTE;
              }
            }
            leaf af-name {
              type dt1:Isis-address-family;
              description
                "Address family";
            }
            leaf saf-name {
              type dt1:Isis-sub-address-family;
              description
                "Sub address family";
            }
            leaf topology-name {
              type dt1:Isis-topology-name;
              description
                "Topology Name";
            }
          }
        }
        container nsr-status {
          description
            "NSR Status information";
          uses ISIS-SH-NSR-STATUS-GLOBAL;
        }
        container interfaces {
          description
            "Interface table";
          list interface {
            key "interface-name";
            description
              "Information about one IS-IS interface";
            leaf interface-name {
              type xr:Interface-name;
              description
                "Interface name";
            }
            uses ISIS-SH-IF;
          }
        }
        container checkpoint-adjacencies {
          description
            "Checkpointed adjacency table";
          list checkpoint-adjacency {
            description
              "A checkpointed IS-IS adjacency";
            leaf level {
              type dt1:Isis-internal-level;
              description
                "Level";
            }
            leaf system-id {
              type xr:Osi-system-id;
              description
                "System ID";
            }
            leaf interface-name {
              type xr:Interface-name;
              description
                "Interface name";
            }
            uses ISIS-SH-CHKPT-ADJ;
          }
        }
        container srms {
          description
            "Segment Routing Mapping Server operational
             data";
          container policy {
            description
              "Policy operational data";
            container policy-ipv4 {
              description
                "IPv4 policy operational data";
              container policy-ipv4-active {
                description
                  "IPv4 active policy operational data";
                uses POLICY-MI;
              }
              container policy-ipv4-backup {
                description
                  "IPv4 backup policy operational data";
                uses POLICY-MI;
              }
            }
            container policy-ipv6 {
              description
                "IPv6 policy operational data";
              container policy-ipv6-backup {
                description
                  "IPv6 backup policy operational data";
                uses POLICY-MI;
              }
              container policy-ipv6-active {
                description
                  "IPv6 active policy operational data";
                uses POLICY-MI;
              }
            }
          }
        }
        container error-log {
          description
            "Log of errors and warnings";
          uses ISIS-SH-ERR-LOG-STRUC;
        }
        container checkpoint-interfaces {
          description
            "Checkpointed interface table";
          list checkpoint-interface {
            key "interface-name";
            description
              "Checkpointed information about one IS-IS
               interface";
            leaf interface-name {
              type xr:Interface-name;
              description
                "Interface name";
            }
            uses ISIS-SH-CHKPT-IDB;
          }
        }
        container interface-statistics {
          description
            "Interface statistics table";
          list interface-statistic {
            key "interface-name";
            description
              "Statistics data for one IS-IS interface";
            leaf interface-name {
              type xr:Interface-name;
              description
                "Interface name";
            }
            uses ISIS-SH-TRAFFIC-INTF;
          }
        }
        container protocol {
          description
            "Basic protocol information about an IS-IS
             instance";
          uses ISIS-SH-PROTO;
        }
        container neighbor-summaries {
          description
            "Neighbor-summary table";
          list neighbor-summary {
            key "interface-name";
            description
              "Neighbor-summary data for a single interface";
            leaf interface-name {
              type xr:Interface-name;
              description
                "Interface name";
            }
            uses ISIS-SH-NBR-SUMM;
          }
        }
        container checkpoint-lsps {
          description
            "Checkpointed LSP table";
          list checkpoint-lsp {
            description
              "A checkpointed IS-IS LSP";
            leaf level {
              type dt1:Isis-internal-level;
              description
                "Level";
            }
            leaf lsp-id {
              type xr:Isis-lsp-id;
              description
                "LSP ID";
            }
            uses ISIS-SH-CHKPT-LSP;
          }
        }
        container mesh-groups {
          description
            "Mesh-group information";
          uses ISIS-SH-MESH-GROUPS;
        }
        container nsr-statistics {
          description
            "NSR Statistics information";
          uses ISIS-SH-NSR-STATS-GLOBAL;
        }
        container checkpoint-te-tunnels {
          description
            "Checkpointed TE tunnel table";
          list checkpoint-te-tunnel {
            description
              "A checkpointed TE tunnel";
            leaf level {
              type dt1:Isis-internal-level;
              description
                "Level";
            }
            leaf interface-name {
              type xr:Interface-name;
              description
                "Interface name";
            }
            uses ISIS-SH-CHKPT-TE-TUNNEL;
          }
        }
        leaf instance-name {
          type dt1:Isis-instance-name;
          description
            "Instance identifier";
        }
      }
    }
  }
}
