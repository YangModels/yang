module Cisco-IOS-XR-infra-serg-oper {
  namespace "http://cisco.com/ns/yang/Cisco-IOS-XR-infra-serg-oper";
  prefix infra-serg-oper;

  import Cisco-IOS-XR-types {
    prefix xr;
  }
  include Cisco-IOS-XR-infra-serg-oper-sub2 {
    revision-date 2015-11-09;
  }
  include Cisco-IOS-XR-infra-serg-oper-sub1 {
    revision-date 2015-11-09;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR infra-serg package operational data.
     
     This module contains definitions
     for the following management objects:
       session-redundancy-manager: Session Redundancy Manager
         information
       session-redundancy-agent: session redundancy agent
     
     Copyright (c) 2013-2016 by Cisco Systems, Inc.
     All rights reserved.";

  revision 2015-11-09 {
    description
      "IOS XR 6.0 revision.";
  }

  container session-redundancy-manager {
    config false;
    description
      "Session Redundancy Manager information";
    container interfaces {
      description
        "Subscriber Redundancy Manager interface table";
      list interface {
        key "interface";
        description
          "interface redundancy manager interface";
        leaf interface {
          type xr:Cisco-ios-xr-string;
          description
            "Interface";
        }
        uses SERG-SHOW-MGR-INTF-ENTRY;
      }
    }
    container groups {
      description
        "Session Redundancy Manager group table";
      list group {
        key "group";
        description
          "Session redundancy manager group";
        leaf group {
          type xr:Cisco-ios-xr-string;
          description
            "Group";
        }
        uses SERG-SHOW-MGR-GROUP-ENTRY;
      }
    }
    container summary {
      description
        "Session redundancy manager summary";
      uses SERG-SHOW-MGR-SUMMARY;
    }
  }
  container session-redundancy-agent {
    config false;
    description
      "session redundancy agent";
    container nodes {
      description
        "List of nodes for which session data is
         collected";
      list node {
        key "node-name";
        description
          "Session data for a particular node";
        container group-id-xr {
          description
            "Data for particular subscriber group session";
          list group-id {
            key "group-id";
            description
              "Group id for subscriber group session";
            leaf group-id {
              type xr:Cisco-ios-xr-string;
              description
                "GroupId";
            }
            uses SERG-SHOW-SESSION-ENTRY;
          }
        }
        container client-ids {
          description
            "Stats Client";
          list client-id {
            key "stats-client-id";
            description
              "Specify stats client";
            leaf stats-client-id {
              type int32;
              description
                "Client Id";
            }
            uses SERG-SHOW-AGT-CLIENT-STATISTICS;
          }
        }
        container memory {
          description
            "Show Memory";
          uses SERG-SHOW-MEMORY;
        }
        container group-ids {
          description
            "Data for particular subscriber group ";
          list group-id {
            key "group-id";
            description
              "Group id for subscriber group";
            leaf group-id {
              type xr:Cisco-ios-xr-string;
              description
                "Group Id";
            }
            uses SERG-SHOW-GROUP-ENTRY;
          }
        }
        container interfaces {
          description
            "List of interfaces";
          list interface {
            key "interface";
            description
              "Specify interface name";
            leaf interface {
              type xr:Interface-name;
              description
                "Interface";
            }
            uses SERG-SHOW-AGT-INTF-ENTRY;
          }
        }
        container stats-global {
          description
            "Stats Global";
          uses SERG-SHOW-AGT-STATISTICS;
        }
        container group-summaries {
          description
            "Session data for a particular node";
          list group-summary {
            key "group-id";
            description
              "Session redundancy agent group summary";
            leaf group-id {
              type xr:Cisco-ios-xr-string;
              description
                "GroupId";
            }
            uses SERG-AGT-SHOW-GROUP-LIST-ENTRY;
          }
        }
        leaf node-name {
          type xr:Node-id;
          description
            "Node name";
        }
      }
    }
  }
}
