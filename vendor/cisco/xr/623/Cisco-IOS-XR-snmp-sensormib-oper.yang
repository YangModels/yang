module Cisco-IOS-XR-snmp-sensormib-oper {
  namespace "http://cisco.com/ns/yang/Cisco-IOS-XR-snmp-sensormib-oper";
  prefix snmp-sensormib-oper;

  import Cisco-IOS-XR-types {
    prefix xr;
  }
  import Cisco-IOS-XR-snmp-agent-oper {
    prefix a1;
  }
  include Cisco-IOS-XR-snmp-sensormib-oper-sub2 {
    revision-date 2015-11-09;
  }
  include Cisco-IOS-XR-snmp-sensormib-oper-sub1 {
    revision-date 2015-11-09;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR snmp-sensormib package operational data.
     
     This YANG module augments the
       Cisco-IOS-XR-snmp-agent-oper
     module with state data.
     
     Copyright (c) 2013-2016 by Cisco Systems, Inc.
     All rights reserved.";

  revision 2015-11-09 {
    description
      "IOS XR 6.0 revision.";
  }

  augment "/a1:snmp" {
    description
      "This augment extends the operational data of
       'Cisco-IOS-XR-snmp-agent-oper'";
    container sensor-mib {
      description
        "SNMP sensor MIB information";
      container physical-indexes {
        description
          "List of physical index table for threshold
           value";
        list physical-index {
          key "index";
          description
            "Threshold value for physical index";
          container threshold-indexes {
            description
              "List of threshold index";
            list threshold-index {
              description
                "Threshold value for threshold index";
              leaf phy-index {
                type xr:Cisco-ios-xr-string;
                description
                  "Physical Index";
              }
              leaf thre-index {
                type xr:Cisco-ios-xr-string;
                description
                  "Threshold index";
              }
              uses ENVMON-THRESHOLD-INFO;
            }
          }
          leaf index {
            type xr:Cisco-ios-xr-string;
            description
              "Physical index";
          }
        }
      }
      container ent-phy-indexes {
        description
          "List of physical index ";
        list ent-phy-index {
          key "index";
          description
            "Sensor value for physical index";
          leaf index {
            type xr:Cisco-ios-xr-string;
            description
              "Physical index";
          }
          uses SNMP-SENSOR-INFO-XML;
        }
      }
    }
  }
}
