submodule Cisco-IOS-XR-ip-iep-oper-sub1 {
  belongs-to Cisco-IOS-XR-ip-iep-oper {
    prefix Cisco-IOS-XR-ip-iep-oper;
  }

  import ietf-inet-types {
    prefix inet;
  }
  import Cisco-IOS-XR-types {
    prefix xr;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR ip-iep package operational data.
     
     Copyright (c) 2013-2016 by Cisco Systems, Inc.
     All rights reserved.";

  revision 2015-11-09 {
    description
      "IOS XR 6.0 revision.";
  }

  typedef Iep-hop {
    type enumeration {
      enum "strict" {
        description
          "Hop type is strict";
      }
      enum "loose" {
        description
          "Hop type is loose";
      }
    }
    description
      "Hop types of the next-address configured";
  }

  typedef Iep-address {
    type enumeration {
      enum "next" {
        description
          "Address type is next";
      }
      enum "exclude" {
        description
          "Address type is exclude";
      }
      enum "exclude-srlg" {
        description
          "Address type is exclude SRLG";
      }
    }
    description
      "Address types";
  }

  typedef Iep-status {
    type enumeration {
      enum "enabled" {
        description
          "Status is enabled";
      }
      enum "disabled" {
        description
          "Status is disabled";
      }
    }
    description
      "Status of the path";
  }

  grouping IEP-IP-ADDRESS-ENTRY {
    description
      "IP address configured in the explicit path";
    leaf index {
      type uint32;
      description
        "Index number at which the path entry is inserted
         or modified";
    }
    leaf if-index {
      type uint32;
      description
        "Interface Index of the path";
    }
    leaf address-type {
      type Iep-address;
      description
        "Specifies the address type";
    }
    leaf hop-type {
      type Iep-hop;
      description
        "Specifies the next unicast address in the path
         as a strict or loose hop";
    }
    leaf address {
      type inet:ipv4-address;
      description
        "IPv4 unicast address";
    }
    leaf mpls-label {
      type uint32;
      description
        "MPLS label";
    }
  }

  grouping IEP-EXPLICIT-PATH {
    description
      "Explicit path details";
    leaf status {
      type Iep-status;
      description
        "Status of the path";
    }
    list address {
      description
        "List of IP addresses configured in the explicit
         path";
      uses IEP-IP-ADDRESS-ENTRY;
    }
  }
}
