submodule Cisco-IOS-XR-icpe-infra-oper-sub2 {
  belongs-to Cisco-IOS-XR-icpe-infra-oper {
    prefix Cisco-IOS-XR-icpe-infra-oper;
  }

  import Cisco-IOS-XR-types {
    prefix xr;
  }
  include Cisco-IOS-XR-icpe-infra-oper-sub3 {
    revision-date 2015-11-09;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR icpe-infra package operational data.
     
     Copyright (c) 2013-2016 by Cisco Systems, Inc.
     All rights reserved.";

  revision 2015-11-09 {
    description
      "IOS XR 6.0 revision.";
  }

  typedef Icpe-install-pkg-supp {
    type enumeration {
      enum "icpe-install-pkg-supp-unknown" {
        description
          "Unknown";
      }
      enum "icpe-install-pkg-supp-not-supported" {
        description
          "Not supported";
      }
      enum "icpe-install-pkg-supp-supported" {
        description
          "Supported";
      }
    }
    description
      "Icpe install pkg supp";
  }

  grouping ICPE-OPER-SAT-PACKAGE-INFORMATION-TYPE {
    description
      "Satellite Software Package Information";
    container install-package-info {
      description
        "Package Data on this Satellite";
      uses ICPE-OPER-PACKAGE-INFO-TYPE;
    }
    leaf satellite-id-xr {
      type uint16;
      description
        "Satellite ID";
    }
    leaf package-support {
      type Icpe-install-pkg-supp;
      description
        "Package support";
    }
  }
}
