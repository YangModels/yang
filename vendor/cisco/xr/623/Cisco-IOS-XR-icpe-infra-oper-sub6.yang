submodule Cisco-IOS-XR-icpe-infra-oper-sub6 {
  belongs-to Cisco-IOS-XR-icpe-infra-oper {
    prefix Cisco-IOS-XR-icpe-infra-oper;
  }

  import ietf-yang-types {
    prefix yang;
  }
  import Cisco-IOS-XR-types {
    prefix xr;
  }
  include Cisco-IOS-XR-icpe-infra-oper-sub3 {
    revision-date 2015-11-09;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR icpe-infra package operational data.
     
     Copyright (c) 2013-2016 by Cisco Systems, Inc.
     All rights reserved.";

  revision 2015-11-09 {
    description
      "IOS XR 6.0 revision.";
  }

  typedef Icpe-oper-topo-remote-source {
    type enumeration {
      enum "icpe-oper-topo-remote-source-unknown" {
        description
          "Unknown";
      }
      enum "icpe-oper-topo-remote-source-remote-icl-id" {
        description
          "Remote ICL ID";
      }
      enum "icpe-oper-topo-remote-source-remote-satellite-mac" {
        description
          "Remote satellite MAC";
      }
      enum "icpe-oper-topo-remote-source-remote-host-mac" {
        description
          "Remote host MAC";
      }
      enum "icpe-oper-topo-remote-source-direct-satellite" {
        description
          "Direct satellite";
      }
      enum "icpe-oper-topo-remote-source-direct-host" {
        description
          "Direct host";
      }
    }
    description
      "Icpe oper topo remote source";
  }

  grouping ICPE-OPER-TOPO-REMOTE-SFL-TYPE {
    description
      "ICPE OPER TOPO REMOTE SFL TYPE";
    leaf mac-address {
      type yang:mac-address;
      description
        "MAC address";
    }
    leaf source {
      type Icpe-oper-topo-remote-source;
      description
        "Source";
    }
    leaf remote-is-satellite {
      type boolean;
      description
        "Remote is satellite";
    }
    leaf remote-is-local-host {
      type boolean;
      description
        "Remote is local host";
    }
    leaf icl-id {
      type uint32;
      description
        "ICL ID";
    }
    leaf interface-handle {
      type xr:Interface-name;
      description
        "Interface handle";
    }
    leaf interface-name {
      type Xr-yang-string;
      description
        "Interface name";
    }
  }

  grouping ICPE-OPER-TOPO-LOCAL-SFL-TYPE {
    description
      "ICPE OPER TOPO LOCAL SFL TYPE";
    leaf icl-id {
      type uint32;
      description
        "ICL ID";
    }
    leaf interface-name {
      type Xr-yang-string;
      description
        "Interface name";
    }
    leaf display-name {
      type Xr-yang-string;
      description
        "Display name";
    }
    leaf redundant {
      type boolean;
      description
        "Redundant";
    }
    leaf active {
      type boolean;
      description
        "Active";
    }
    leaf obsolete {
      type boolean;
      description
        "Obsolete";
    }
    list remote-device {
      description
        "Remote Device table";
      uses ICPE-OPER-TOPO-REMOTE-SFL-TYPE;
    }
  }

  grouping ICPE-OPER-TOPO-SATTUN-TYPE {
    description
      "ICPE OPER TOPO SATTUN TYPE";
    leaf mac-address {
      type yang:mac-address;
      description
        "MAC address";
    }
    leaf configured {
      type boolean;
      description
        "Configured";
    }
    leaf num-hops {
      type uint16;
      description
        "Num hops";
    }
    leaf type {
      type Xr-yang-string;
      description
        "Type";
    }
    leaf satellite-id {
      type uint32;
      description
        "Satellite ID";
    }
    leaf received-serial-number {
      type Xr-yang-string;
      description
        "Received serial number";
    }
    leaf received-serial-number-present {
      type boolean;
      description
        "Received serial number present";
    }
    leaf vlan-id {
      type uint16;
      description
        "VLAN ID";
    }
    leaf display-name {
      type Xr-yang-string;
      description
        "Display name";
    }
    leaf conflict-reason {
      type Icpe-oper-conflict;
      description
        "Conflict reason";
    }
    leaf conflict-context {
      type Xr-yang-string;
      description
        "Conflict context";
    }
    list fabric-link {
      description
        "Local Satellite Fabric Link table";
      uses ICPE-OPER-TOPO-LOCAL-SFL-TYPE;
    }
  }

  grouping ICPE-OPER-TOPO-DSFL-TYPE {
    description
      "ICPE OPER TOPO DSFL TYPE";
    leaf interface-name {
      type Xr-yang-string;
      description
        "Interface name";
    }
    leaf interface-handle {
      type xr:Interface-name;
      description
        "Interface handle";
    }
    leaf discovery-running {
      type boolean;
      description
        "Discovery running";
    }
  }

  grouping ICPE-OPER-TOPO-CSFL-TYPE {
    description
      "Satellite Topology Information";
    leaf interface-name-xr {
      type string {
        length "0..64";
      }
      description
        "Interface name";
    }
    leaf interface-handle {
      type xr:Interface-name;
      description
        "Interface handle";
    }
    leaf redundancy-iccp-group {
      type uint32;
      description
        "Redundancy ICCP group";
    }
    leaf is-physical {
      type boolean;
      description
        "Is physical";
    }
    leaf ring-whole {
      type boolean;
      description
        "Ring whole";
    }
    list discovered-link {
      description
        "Discovered Links table";
      uses ICPE-OPER-TOPO-DSFL-TYPE;
    }
    list satellite {
      description
        "Satellite table";
      uses ICPE-OPER-TOPO-SATTUN-TYPE;
    }
  }
}
