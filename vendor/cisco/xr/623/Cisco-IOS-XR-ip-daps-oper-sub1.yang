submodule Cisco-IOS-XR-ip-daps-oper-sub1 {
  belongs-to Cisco-IOS-XR-ip-daps-oper {
    prefix Cisco-IOS-XR-ip-daps-oper;
  }

  import ietf-inet-types {
    prefix inet;
  }
  import Cisco-IOS-XR-types {
    prefix xr;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR ip-daps package operational data.
     
     Copyright (c) 2013-2016 by Cisco Systems, Inc.
     All rights reserved.";

  revision 2015-11-09 {
    description
      "IOS XR 6.0 revision.";
  }

  typedef Daps-client {
    type enumeration {
      enum "none" {
        value 0;
        description
          "Client type is None";
      }
      enum "ppp" {
        value 1;
        description
          "Client type is PPP";
      }
      enum "dhcp" {
        value 2;
        description
          "Client type is DHCP";
      }
      enum "dhcpv6" {
        value 4;
        description
          "Client type is DHCPv6";
      }
      enum "ipv6nd" {
        value 5;
        description
          "Client type is IPv6ND";
      }
    }
    description
      "DAPS client types";
  }

  typedef Ipv6-addr {
    type inet:ipv6-address;
    description
      "Ipv6 addr";
  }

  typedef Ip-addr {
    type enumeration {
      enum "ipv4" {
        value 2;
        description
          "IPv4 address";
      }
      enum "ipv6" {
        value 10;
        description
          "IPv6 address";
      }
    }
    description
      "Address type";
  }

  grouping DAPS-VRF-POOL-INFO {
    description
      "VRF pool information";
    leaf pool-name {
      type string {
        length "0..64";
      }
      description
        "Pool name";
    }
    leaf vrf-name {
      type string {
        length "0..64";
      }
      description
        "VRF name";
    }
    leaf used {
      type uint32;
      description
        "Used allocations";
    }
    leaf excluded {
      type uint32;
      description
        "Excluded allocations";
    }
    leaf free {
      type uint32;
      description
        "Free allocations";
    }
    leaf total {
      type uint32;
      description
        "Total allocations";
    }
  }

  grouping DAPS-VRF-ALLOCATION-SUMMARY {
    description
      "VRF allocation summary";
    leaf used {
      type uint32;
      description
        "Used allocations";
    }
    leaf excluded {
      type uint32;
      description
        "Excluded allocations";
    }
    leaf free {
      type uint32;
      description
        "Free allocations";
    }
    leaf total {
      type uint32;
      description
        "Total allocations";
    }
    leaf high-utilization-threshold {
      type uint8;
      units "percentage";
      description
        "High utilization threshold in percentage";
    }
    leaf low-utilization-threshold {
      type uint8;
      units "percentage";
      description
        "Low utilization threshold in percentage";
    }
    leaf utilization {
      type uint8;
      units "percentage";
      description
        "Current utilization in percentage";
    }
  }

  grouping DAPS-VRF-INFO {
    description
      " VRF information";
    container allocation-summary {
      description
        "Allocation summary";
      uses DAPS-VRF-ALLOCATION-SUMMARY;
    }
    list pools {
      description
        "Pools data";
      uses DAPS-VRF-POOL-INFO;
    }
  }

  grouping IP-DAPS-SHOW-POOL-TOTAL-UTIL {
    description
      "IP DAPS pool total utilization";
    leaf total-utilization-high-mark {
      type uint8;
      description
        "High utilization mark";
    }
    leaf total-utilization-low-mark {
      type uint8;
      description
        "Low utilization mark";
    }
    leaf current-total-utilization {
      type uint8;
      description
        "Current utilization";
    }
  }

  grouping IP-DAPS-SHOW-POOL-CFG {
    description
      "IP DAPS pool configuration";
    leaf pool-name {
      type string {
        length "0..64";
      }
      description
        "Pool name";
    }
    leaf pool-id {
      type uint32;
      description
        "Pool ID for MIBS";
    }
    leaf vrf-name {
      type string {
        length "0..64";
      }
      description
        "VRF name";
    }
    leaf pool-scope {
      type string {
        length "0..64";
      }
      description
        "Pool Scope";
    }
    leaf pool-prefix-length {
      type uint32;
      description
        "Prefix length";
    }
    leaf high-utilization-mark {
      type uint8;
      description
        "High utilization mark";
    }
    leaf low-utilization-mark {
      type uint8;
      description
        "Low utilization mark";
    }
    leaf current-utilization {
      type uint8;
      description
        "Current utilization";
    }
    leaf utilization-high-count {
      type uint32;
      description
        "Number of times High utilization threshold was
         crossed";
    }
    leaf utilization-low-count {
      type uint32;
      description
        "Number of times Low utilization threshold was
         crossed";
    }
  }

  grouping DAPS-POOL-IN-USE-ADDRESS {
    description
      "In-use address data";
    container address {
      description
        "Client address";
      uses IP-ADDR-ST;
    }
    leaf client-type {
      type Daps-client;
      description
        "Client type";
    }
  }

  grouping DAPS-POOL-RANGE {
    description
      "Pool address range data";
    container start-address {
      description
        "Range start";
      uses IP-ADDR-ST;
    }
    container end-address {
      description
        "Range end";
      uses IP-ADDR-ST;
    }
    leaf used {
      type uint32;
      description
        "Used allocations";
    }
    leaf excluded {
      type uint32;
      description
        "Excluded allocations";
    }
    leaf free {
      type uint32;
      description
        "Free allocations";
    }
  }

  grouping DAPS-POOL-THRESHOLD {
    description
      "Pool threshold information";
    leaf threshold {
      type uint32;
      units "percentage";
      description
        "Threshold in percentage";
    }
    leaf triggers {
      type uint32;
      description
        "Number of Triggers";
    }
    leaf time-last-crossed {
      type string;
      description
        "Last time at which threshold crossed in DDD MMM
         DD HH:MM:SS YYYY format eg: Tue Apr 11 21:30:47
         2011";
    }
  }

  grouping DAPS-POOL-ALLOCATIONS {
    description
      "Pool allocations data";
    container high-threshold {
      description
        "High threshold data";
      uses DAPS-POOL-THRESHOLD;
    }
    container low-threshold {
      description
        "Low threshold data";
      uses DAPS-POOL-THRESHOLD;
    }
    leaf vrf-name {
      type string {
        length "0..64";
      }
      description
        "VRF name";
    }
    leaf used {
      type uint32;
      description
        "Used allocations";
    }
    leaf excluded {
      type uint32;
      description
        "Excluded allocations";
    }
    leaf free {
      type uint32;
      description
        "Free allocations";
    }
    leaf total {
      type uint32;
      description
        "Total allocations";
    }
    leaf utilization {
      type uint32;
      units "percentage";
      description
        "Current utilization in percentage";
    }
  }

  grouping DAPS-POOL-DETAIL {
    description
      "Pool data";
    container pool-allocations {
      description
        "Pool allocations";
      uses DAPS-POOL-ALLOCATIONS;
    }
    list address-range {
      description
        "Address ranges";
      uses DAPS-POOL-RANGE;
    }
    list in-use-address {
      description
        "In-use addresses";
      uses DAPS-POOL-IN-USE-ADDRESS;
    }
  }

  grouping IP-ADDR-UN {
    description
      "Daps Address";
    leaf address-family {
      type Ip-addr;
      description
        "AddressFamily";
    }
    leaf ipv4-address {
      when "../address-family = 'ipv4'" {
        description
          "../AddressFamily = 'IPv4'";
      }
      type inet:ipv4-address;
      description
        "IPv4 address";
    }
    leaf ipv6-address {
      when "../address-family = 'ipv6'" {
        description
          "../AddressFamily = 'IPv6'";
      }
      type Ipv6-addr;
      description
        "IPv6 address";
    }
  }

  grouping IP-ADDR-ST {
    description
      "IP address information";
    container address {
      description
        "Address";
      uses IP-ADDR-UN;
    }
  }

  grouping IP-DAPS-SHOW-POOL-BRIEF {
    description
      "IP DAPS pool parameters";
    container start-address-xr {
      description
        "Range start";
      uses IP-ADDR-ST;
    }
    container end-address {
      description
        "Range end";
      uses IP-ADDR-ST;
    }
    container default-router {
      description
        "Default router";
      uses IP-ADDR-ST;
    }
    leaf pool-name {
      type string {
        length "0..64";
      }
      description
        "Pool name";
    }
    leaf vrf-name {
      type string {
        length "0..64";
      }
      description
        "VRF name";
    }
    leaf pool-scope {
      type string {
        length "0..64";
      }
      description
        "Pool scope";
    }
    leaf allocated-addresses {
      type uint32;
      description
        "Number of addresses allocated";
    }
    leaf free-addresses {
      type uint32;
      description
        "Number of addresses free";
    }
    leaf excluded-addresses {
      type uint32;
      description
        "Number of addresses excluded";
    }
    leaf network-blocked-status {
      type uint32;
      description
        "Is network blocked";
    }
    leaf network-blocked-status-trp {
      type uint32;
      description
        "Is network blocked trap send";
    }
  }
}
