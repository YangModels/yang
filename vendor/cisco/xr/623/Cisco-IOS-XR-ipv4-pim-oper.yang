module Cisco-IOS-XR-ipv4-pim-oper {
  namespace "http://cisco.com/ns/yang/Cisco-IOS-XR-ipv4-pim-oper";
  prefix ipv4-pim-oper;

  import ietf-inet-types {
    prefix inet;
  }
  import Cisco-IOS-XR-types {
    prefix xr;
  }
  include Cisco-IOS-XR-ipv4-pim-oper-sub2 {
    revision-date 2015-11-09;
  }
  include Cisco-IOS-XR-ipv4-pim-oper-sub1 {
    revision-date 2015-11-09;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ipv4-pim package operational data.
     
     This module contains definitions
     for the following management objects:
       pim-ma: PIM MA operational data
       pim: pim
       ipv6-pim: ipv6 pim
       pim6-ma: pim6 ma
     
     Copyright (c) 2013-2016 by Cisco Systems, Inc.
     All rights reserved.";

  revision 2015-11-09 {
    description
      "IOS XR 6.0 revision.";
  }

  typedef Pim-topology-interface-flag {
    type enumeration {
      enum "lh" {
        value 0;
        description
          "LH";
      }
      enum "ld" {
        value 1;
        description
          "LD";
      }
      enum "li" {
        value 2;
        description
          "LI";
      }
      enum "ii" {
        value 3;
        description
          "II";
      }
      enum "id" {
        value 4;
        description
          "ID";
      }
      enum "as" {
        value 5;
        description
          "AS";
      }
      enum "ab" {
        value 6;
        description
          "AB";
      }
      enum "ex" {
        value 7;
        description
          "EX";
      }
    }
    description
      "Pim topology interface flag";
  }

  typedef Pim-safi {
    type enumeration {
      enum "unicast" {
        value 1;
        description
          "SAFI unicast";
      }
      enum "multicast" {
        value 2;
        description
          "SAFI Multicast";
      }
      enum "all" {
        value 3;
        description
          "SAFI all";
      }
      enum "default" {
        value 4;
        description
          "SAFI default";
      }
    }
    description
      "Pim safi";
  }

  typedef Pim-client {
    type enumeration {
      enum "none" {
        value 0;
        description
          "No Client";
      }
      enum "configured-embedded-rp" {
        value 1;
        description
          "Embedded RP from configuration";
      }
      enum "embedded" {
        value 2;
        description
          "Embedded RP learnt from the Group addr";
      }
      enum "permanent" {
        value 3;
        description
          "Permanent";
      }
      enum "auto-rp" {
        value 4;
        description
          "AutoRP";
      }
      enum "bsr" {
        value 5;
        description
          "BSR";
      }
      enum "configured" {
        value 6;
        description
          "Configured";
      }
      enum "static" {
        value 7;
        description
          "Static";
      }
    }
    description
      "Pim client";
  }

  typedef Pim-topology-entry-flag {
    type enumeration {
      enum "kat" {
        value 0;
        description
          "KAT";
      }
      enum "aa" {
        value 1;
        description
          "AA";
      }
      enum "pa" {
        value 2;
        description
          "PA";
      }
      enum "ra" {
        value 3;
        description
          "RA";
      }
      enum "ia" {
        value 4;
        description
          "IA";
      }
      enum "rr" {
        value 5;
        description
          "RR";
      }
      enum "lh" {
        value 6;
        description
          "LH";
      }
      enum "dss" {
        value 7;
        description
          "DSS";
      }
      enum "dcc" {
        value 8;
        description
          "DCC";
      }
      enum "sr" {
        value 9;
        description
          "SR";
      }
      enum "e" {
        value 10;
        description
          "E";
      }
      enum "ex" {
        value 11;
        description
          "EX";
      }
      enum "ma" {
        value 12;
        description
          "MA";
      }
      enum "mt" {
        value 13;
        description
          "MT";
      }
      enum "mfa" {
        value 14;
        description
          "MFA";
      }
      enum "mfp" {
        value 15;
        description
          "MFP";
      }
      enum "mfb" {
        value 16;
        description
          "MFB";
      }
    }
    description
      "Pim topology entry flag";
  }

  typedef Pim-protocol {
    type enumeration {
      enum "non-routable" {
        value 0;
        description
          "Non Routable";
      }
      enum "sparse-mode" {
        value 1;
        description
          "Sparse Mode";
      }
      enum "dense-mode" {
        value 2;
        description
          "Dense Mode";
      }
      enum "bidir" {
        value 3;
        description
          "Bidirectional Mode";
      }
      enum "ssm" {
        value 4;
        description
          "Source Specific Multicast Mode";
      }
      enum "maximum" {
        value 5;
        description
          "Maximum";
      }
      enum "any" {
        value 6;
        description
          "Any";
      }
    }
    description
      "Pim protocol";
  }

  grouping AUTO-RP {
    description
      "Common node of vrf, default-context";
    container auto-rp {
      description
        "PIM Auto-RP information";
    }
  }

  grouping ROUTE-POLICY {
    description
      "Common node of vrf, default-context";
    container route-policy {
      description
        "PIM route policy";
      container route-policy-statistics {
        description
          "PIM route policy statistics";
        uses PIM-RPF-POLICY-STATS-BAG;
      }
      container route-policy-tests {
        description
          "PIM route policy test run table";
        list route-policy-test {
          description
            "PIM route policy test run";
          leaf source-address {
            type inet:ip-address-no-zone;
            description
              "Source IP address";
          }
          leaf group-address {
            type inet:ip-address-no-zone;
            description
              "Group IP address";
          }
          leaf ext-comm {
            type xr:Cisco-ios-xr-string {
              length "1..8";
            }
            description
              "Extended Community";
          }
          uses PIM-RPF-POLICY-TEST-BAG;
        }
      }
    }
  }

  grouping GROUP-MAP-SOURCE-TABLE {
    description
      "Common node of vrf, default-context";
    container group-map-sources {
      description
        "PIM group-mapping with source information";
      list group-map-source {
        description
          "PIM Group Mapping Entry with source information";
        leaf prefix {
          type inet:ip-address-no-zone;
          description
            "Prefix";
        }
        leaf prefix-length {
          type int32;
          description
            "Prefix length";
        }
        leaf client {
          type Pim-client;
          description
            "Client";
        }
        leaf protocol {
          type Pim-protocol;
          description
            "Protocol";
        }
        leaf rp-address {
          type inet:ip-address-no-zone;
          description
            "RP address";
        }
        leaf priority {
          type int32;
          description
            "RP Priority";
        }
        uses PIM-GRP-MAP-INFOSRC-BAG;
      }
    }
  }

  grouping BIDIR-DF-STATE-TABLE {
    description
      "Common node of vrf, default-context";
    container bidir-df-states {
      description
        "Bidirectional PIM DF election state table";
      list bidir-df-state {
        description
          "Bidirectional PIM DF Election Table Entry";
        leaf rp-address {
          type inet:ip-address-no-zone;
          description
            "RP address";
        }
        leaf interface-name {
          type xr:Interface-name;
          description
            "Interface name";
        }
        uses PIM-BIDIR-DF-STATE-BAG;
      }
    }
  }

  grouping MIB-DATABASE-TABLE {
    description
      "Common node of vrf, default-context";
    container mib-databases {
      description
        "PIM group database for mroute mibs table";
      list mib-database {
        description
          "PIM multicast static route information";
        leaf source-address {
          type inet:ip-address-no-zone;
          description
            "Multicast static route source address";
        }
        leaf group-address {
          type inet:ip-address-no-zone;
          description
            "Multicast satic route group address";
        }
        leaf source-netmask {
          type int32;
          description
            "Source mask";
        }
        uses PIM-MROUTE-BAG;
      }
    }
  }

  grouping BGP-AF-TABLE {
    description
      "Common node of vrf, default-context";
    container bgp-afs {
      description
        "PIM BGP SAFI table";
      list bgp-af {
        description
          "PIM BGP SAFI information";
        leaf source-address {
          type inet:ip-address-no-zone;
          description
            "Source IP address";
        }
        leaf group-address {
          type inet:ip-address-no-zone;
          description
            "Group IP address";
        }
        uses PIM-BGP-SAFI-BAG;
      }
    }
  }

  grouping TOPOLOGY-ENTRY-FLAG-ROUTE-COUNT-TABLE {
    description
      "Common node of vrf, default-context";
    container topology-entry-flag-route-counts {
      description
        "Route count for topology with entry flag set";
      list topology-entry-flag-route-count {
        key "entry-flag";
        description
          "Route count for topology with entry flag set";
        leaf entry-flag {
          type Pim-topology-entry-flag;
          description
            "entry flag";
        }
        uses PIM-TT-SUMM-BAG;
      }
    }
  }

  grouping BIDIR-DF-WINNER-TABLE {
    description
      "Common node of vrf, default-context";
    container bidir-df-winners {
      description
        "Bidirectional PIM DF election winner table";
      list bidir-df-winner {
        description
          "Bidirectional PIM DF election table entry";
        leaf rp-address {
          type inet:ip-address-no-zone;
          description
            "RP address";
        }
        leaf interface-name {
          type xr:Interface-name;
          description
            "Interface name";
        }
        uses PIM-BIDIR-DF-BAG;
      }
    }
  }

  grouping TABLE-CONTEXT-TABLE {
    description
      "Common node of vrf, default-context";
    container table-contexts {
      description
        "PIM table context list";
      list table-context {
        description
          "PIM table context information";
        leaf saf-name {
          type Pim-safi;
          description
            "SAF name";
        }
        leaf topology-name {
          type xr:Cisco-ios-xr-string {
            length "1..32";
          }
          description
            "Topology name";
        }
        uses PIM-TABLE-CTX-BAG;
      }
    }
  }

  grouping VRF-TABLE {
    description
      "Common node of active, standby";
    container vrfs {
      description
        "VRF Table";
      list vrf {
        key "vrf-name";
        description
          "VRF name";
        leaf vrf-name {
          type xr:Cisco-ios-xr-string {
            length "1..32";
          }
          description
            "VRF name ";
        }
        uses IFRS-INTERFACE-TABLE;
        uses SAF-TABLE;
        uses INTERFACE-STATISTICS-TABLE;
        uses TOPOLOGY-ROUTE-COUNT;
        uses JP-STATISTICS-TABLE;
        uses MIB-DATABASE-TABLE;
        uses NEIGHBOR-OLD-FORMAT-TABLE;
        uses IFRS-SUMMARY;
        uses RANGE-LIST-TABLE;
        uses INTERFACE-OLD-FORMAT-TABLE;
        uses BSR;
        uses ROUTE-POLICY;
        uses RPF-SUMMARY;
        uses IPV4-PIM-COMMON-OPER-INTERFACE-TABLE;
        uses NET-IO-TUNNEL-TABLE;
        uses BIDIR-DF-STATE-TABLE;
        uses TOPOLOGY-TABLE;
        uses BGP-AF-TABLE;
        uses AUTO-RP;
        uses TOPOLOGY-INTERFACE-FLAG-ROUTE-COUNT-TABLE;
        uses GROUP-MAP-SOURCE-TABLE;
        uses TRAFFIC-COUNTERS;
        uses GROUP-MAP-RPF-TABLE;
        uses SUMMARY;
        uses GRE;
        uses BIDIR-DF-WINNER-TABLE;
        uses TABLE-CONTEXT-TABLE;
        uses NEIGHBOR-SUMMARY-TABLE;
        uses CONTEXT;
        uses TOPOLOGY-ENTRY-FLAG-ROUTE-COUNT-TABLE;
        uses RPF-REDIRECT;
        uses TUNNEL-TABLE;
        uses MULTICAST-STATIC-ROUTE-TABLE;
        uses NEIGHBOR-TABLE;
      }
    }
  }

  grouping BSR {
    description
      "Common node of vrf, default-context";
    container bsr {
      description
        "PIM BSR information";
      container rp-caches {
        description
          "PIM BSR RP cache table";
        list rp-cache {
          key "group-prefix";
          description
            "PIM BSR RP cache";
          leaf group-prefix {
            type inet:ip-address-no-zone;
            description
              "Group prefix";
          }
          uses PIM-BSR-RP-CACHE-BAG;
        }
      }
      container candidate-rps {
        description
          "PIM candidate-RP";
        list candidate-rp {
          key "rp-address";
          description
            "PIM BSR candidate RP information";
          leaf rp-address {
            type inet:ip-address-no-zone;
            description
              "Candidate-RP address";
          }
          uses PIM-BSR-CANDIDATE-RP-BAG;
        }
      }
      container bsr-elections {
        description
          "PIM BSR election state";
        list bsr-election {
          key "pim-scope";
          description
            "PIM BSR information";
          leaf pim-scope {
            type int32;
            description
              "BSR information";
          }
          uses PIM-BSR-ELECTION-BAG;
        }
      }
    }
  }

  grouping NET-IO-TUNNEL-TABLE {
    description
      "Common node of vrf, default-context";
    container net-io-tunnels {
      description
        "Tunnel information that NETIO has ";
      list net-io-tunnel {
        key "tunnel-name";
        description
          "PIM netio tunnel information";
        leaf tunnel-name {
          type xr:Cisco-ios-xr-string {
            length "1..64";
          }
          description
            "Tunnel name";
        }
        uses PIM-TUNNEL-INFO-BAG;
      }
    }
  }

  grouping RPF-SUMMARY {
    description
      "Common node of vrf, default-context";
    container rpf-summary {
      description
        "PIM RPF registration summary";
      uses PIM-RPF-SUMMARY-BAG;
    }
  }

  grouping IFRS-INTERFACE-TABLE {
    description
      "Common node of vrf, default-context";
    container ifrs-interfaces {
      description
        "PIM interfaces in forward reference store table";
      list ifrs-interface {
        key "interface-name";
        description
          "PIM IFRS interface information";
        leaf interface-name {
          type xr:Interface-name;
          description
            "Interface name";
        }
        uses PIM-IDB-BAG;
      }
    }
  }

  grouping PROCESS {
    description
      "Common node of active, standby";
    container process {
      description
        "Process";
      container nsr {
        description
          "NSR Information";
        uses PIM-NSR-BAG;
      }
      container summary {
        description
          "PIM Global Summary";
        uses PIM-SUMMARY-BAG;
      }
      container nsf {
        description
          "PIM NSF information";
        uses PIM-NSF-BAG;
      }
      container issu {
        description
          "ISSU Information";
        uses PIM-ISSU-BAG;
      }
    }
  }

  grouping JP-STATISTICS-TABLE {
    description
      "Common node of vrf, default-context";
    container jp-statistics {
      description
        "PIM join prune statistics table";
      list jp-statistic {
        key "interface-name";
        description
          "PIM Join Prune Statistics";
        leaf interface-name {
          type xr:Interface-name;
          description
            "Interface name";
        }
        uses PIM-JPSTATS-BAG;
      }
    }
  }

  grouping TOPOLOGY-TABLE {
    description
      "Common node of vrf, default-context";
    container topologies {
      description
        "PIM topology table";
      list topology {
        description
          "PIM topology information";
        leaf source-address {
          type inet:ip-address-no-zone;
          description
            "Source address";
        }
        leaf group-address {
          type inet:ip-address-no-zone;
          description
            "Group address";
        }
        leaf rpt {
          type int32;
          description
            "RPT bit";
        }
        uses PIM-TT-ROUTE-BAG;
      }
    }
  }

  grouping NEIGHBOR-SUMMARY-TABLE {
    description
      "Common node of vrf, default-context";
    container neighbor-summaries {
      description
        "PIM neighbor summary table";
      list neighbor-summary {
        key "interface-name";
        description
          "PIM neighbor summary information";
        leaf interface-name {
          type xr:Interface-name;
          description
            "Interface name";
        }
        uses PIM-NBR-SUMM-BAG;
      }
    }
  }

  grouping TRAFFIC-COUNTERS {
    description
      "Common node of vrf, default-context";
    container traffic-counters {
      description
        "PIM message traffic counters";
      uses PIM-TRAFFIC-BAG;
    }
  }

  grouping TOPOLOGY-ROUTE-COUNT {
    description
      "Common node of vrf, default-context";
    container topology-route-count {
      description
        "Topology route count information from PIM
         topology table";
      uses PIM-TT-SUMM-BAG;
    }
  }

  grouping TUNNEL-TABLE {
    description
      "Common node of vrf, default-context";
    container tunnels {
      description
        "Tunnels information that PIM has";
      list tunnel {
        key "tunnel-name";
        description
          "PIM tunnel information";
        leaf tunnel-name {
          type xr:Cisco-ios-xr-string {
            length "1..64";
          }
          description
            "Tunnel name";
        }
        uses PIM-TUNNEL-INFO-BAG;
      }
    }
  }

  grouping PIM-MA-COMMON-OPER-PIM-MA-SUMMARY-MP {
    description
      "Common node of active, standby";
    container pim-ma-summary {
      description
        "PIM MA summary";
      uses PIM-MA-SUMMARY;
    }
  }

  grouping ACTIVE {
    description
      "Common node of pim-ma, pim6-ma";
    container active {
      description
        "Active Process";
      uses INTERFACE-TABLE;
      uses PIM-MA-COMMON-OPER-PIM-MA-SUMMARY-MP;
    }
  }

  grouping IPV4-PIM-ROLE-LVL-OPER-ACTIVE {
    description
      "Common node of pim-ma, pim6-maCommon node of pim,
       ipv6-pim";
    container active {
      description
        "Active Process";
      uses DEFAULT-CONTEXT;
      uses PROCESS;
      uses VRF-TABLE;
    }
  }

  grouping GROUP-MAP-RPF-TABLE {
    description
      "Common node of vrf, default-context";
    container group-map-rpfs {
      description
        "PIM group mapping information";
      list group-map-rpf {
        description
          "PIM group mapping entry";
        leaf prefix {
          type inet:ip-address-no-zone;
          description
            "Prefix";
        }
        leaf prefix-length {
          type int32;
          description
            "Prefix length";
        }
        leaf client {
          type Pim-client;
          description
            "Client";
        }
        leaf protocol {
          type Pim-protocol;
          description
            "Protocol";
        }
        leaf rp-address {
          type inet:ip-address-no-zone;
          description
            "RP address";
        }
        leaf rp-priority {
          type int32;
          description
            "RP priority";
        }
        uses PIM-GRP-MAP-INFORPF-BAG;
      }
    }
  }

  grouping INTERFACE-OLD-FORMAT-TABLE {
    description
      "Common node of vrf, default-context";
    container interface-old-formats {
      description
        "PIM interfaces in old format";
      list interface-old-format {
        key "interface-name";
        description
          "PIM interface name";
        leaf interface-name {
          type xr:Interface-name;
          description
            "Interface name";
        }
        uses PIM-IDB-BAG;
      }
    }
  }

  grouping RPF-REDIRECT {
    description
      "Common node of vrf, default-context";
    container rpf-redirect {
      description
        "PIM ECMP RPF-redirect bundle";
      container redirect-route-databases {
        description
          "PIM ECMP RPF-redirect route database";
        list redirect-route-database {
          description
            "PIM ECMP RPF-redirect route information";
          leaf source-address {
            type inet:ip-address-no-zone;
            description
              "Source address";
          }
          leaf group-address {
            type inet:ip-address-no-zone;
            description
              "Group address";
          }
          uses PIM-RPF-RDRCT-ROUTE-BAG;
        }
      }
      container bundle-interfaces {
        description
          "PIM ECMP RPF-redirect bundle information";
        list bundle-interface {
          description
            "PIM ECMP RPF-redirect bundle interface
             information";
          leaf bundle-name {
            type xr:Cisco-ios-xr-string {
              length "1..32";
            }
            description
              "Bundle name";
          }
          leaf interface-name {
            type xr:Interface-name;
            description
              "Bundle interface name";
          }
          uses PIM-RPF-RDRCT-BNDL-BAG;
        }
      }
    }
  }

  grouping CONTEXT {
    description
      "Common node of vrf, default-context";
    container context {
      description
        "PIM context information";
      uses PIM-CONTEXT-BAG;
    }
  }

  grouping INTERFACE-TABLE {
    description
      "Common node of active, standby";
    container interface-table {
      description
        "Interface Table";
      container interface-by-handles {
        description
          "Table of PIM MA interfaces indexed by handle";
        list interface-by-handle {
          key "interface-handle";
          description
            "PIM MA interface referenced by handle";
          leaf interface-handle {
            type int32;
            description
              "Interface handle";
          }
          uses PIM-MA-IDB;
        }
      }
      container interface-by-names {
        description
          "Table of PIM MA interfaces indexed by name";
        list interface-by-name {
          key "interface-name";
          description
            "PIM MA interface referenced by name";
          leaf interface-name {
            type xr:Interface-name;
            description
              "Interface name";
          }
          uses PIM-MA-IDB;
        }
      }
    }
  }

  grouping IPV4-PIM-COMMON-OPER-INTERFACE-TABLE {
    description
      "Common node of active, standbyCommon node of vrf,
       default-context";
    container interfaces {
      description
        "PIM interfaces";
      list interface {
        key "interface-name";
        description
          "PIM interface name";
        leaf interface-name {
          type xr:Interface-name;
          description
            "Interface name";
        }
        uses PIM-IDB-BAG;
      }
    }
  }

  grouping SUMMARY {
    description
      "Common node of vrf, default-context";
    container summary {
      description
        "PIM summary";
      uses PIM-SUMMARY-BAG;
    }
  }

  grouping TOPOLOGY-INTERFACE-FLAG-ROUTE-COUNT-TABLE {
    description
      "Common node of vrf, default-context";
    container topology-interface-flag-route-counts {
      description
        "Route count for topology with interface flag set";
      list topology-interface-flag-route-count {
        key "interface-flag";
        description
          "Route count for topology with interface flag
           set";
        leaf interface-flag {
          type Pim-topology-interface-flag;
          description
            "Interface flag";
        }
        uses PIM-TT-SUMM-BAG;
      }
    }
  }

  grouping INTERFACE-STATISTICS-TABLE {
    description
      "Common node of vrf, default-context";
    container interface-statistics {
      description
        "PIM interface statistics";
      list interface-statistic {
        key "interface-name";
        description
          "PIM interface statistics";
        leaf interface-name {
          type xr:Interface-name;
          description
            "Interface name";
        }
        uses PIM-IFSTATS-BAG;
      }
    }
  }

  grouping GRE {
    description
      "Common node of vrf, default-context";
    container gre {
      description
        "GRE information";
      container gre-hashes {
        description
          "GRE hash";
        list gre-hash {
          key "source-address destination-address ifname";
          description
            "PIM GRE Hashed Underlying Interface";
          leaf source-address {
            type inet:ip-address-no-zone;
            description
              "Source address";
          }
          leaf destination-address {
            type inet:ip-address-no-zone;
            description
              "Destination address";
          }
          leaf ifname {
            type xr:Interface-name;
            description
              "GRE Tunnel Interface";
          }
          uses PIM-GRE-HASH-BAG;
        }
      }
      container gre-next-hops {
        description
          "GRE destination neighbor table";
        list gre-next-hop {
          key "destination-address";
          description
            "PIM GRE address next-hop information";
          leaf destination-address {
            type inet:ip-address-no-zone;
            description
              "GRE destination address";
          }
          uses PIM-GRE-INFO-BAG;
        }
      }
    }
  }

  grouping NEIGHBOR-OLD-FORMAT-TABLE {
    description
      "Common node of vrf, default-context";
    container neighbor-old-formats {
      description
        "PIM neighbor table old format";
      list neighbor-old-format {
        description
          "PIM neighbor information";
        leaf interface-name {
          type xr:Interface-name;
          description
            "Interface name";
        }
        leaf neighbor-address {
          type inet:ip-address-no-zone;
          description
            "Neighbor address";
        }
        uses PIM-NBR-BAG;
      }
    }
  }

  grouping IFRS-SUMMARY {
    description
      "Common node of vrf, default-context";
    container ifrs-summary {
      description
        "PIM interfaces in forward reference store
         summary";
      uses PIM-IDB-SUMM-BAG;
    }
  }

  grouping DEFAULT-CONTEXT {
    description
      "Common node of active, standby";
    container default-context {
      description
        "Default Context";
      container global-interfaces {
        description
          "PIM global interface table";
        list global-interface {
          key "interface-name";
          description
            "PIM interface name";
          leaf interface-name {
            type xr:Interface-name;
            description
              "Interface name";
          }
          uses PIM-IDB-BAG;
        }
      }
      uses IFRS-INTERFACE-TABLE;
      uses SAF-TABLE;
      uses INTERFACE-STATISTICS-TABLE;
      uses TOPOLOGY-ROUTE-COUNT;
      uses JP-STATISTICS-TABLE;
      uses MIB-DATABASE-TABLE;
      uses NEIGHBOR-OLD-FORMAT-TABLE;
      uses IFRS-SUMMARY;
      uses RANGE-LIST-TABLE;
      uses INTERFACE-OLD-FORMAT-TABLE;
      uses BSR;
      uses ROUTE-POLICY;
      uses RPF-SUMMARY;
      uses IPV4-PIM-COMMON-OPER-INTERFACE-TABLE;
      uses NET-IO-TUNNEL-TABLE;
      uses BIDIR-DF-STATE-TABLE;
      uses TOPOLOGY-TABLE;
      uses BGP-AF-TABLE;
      uses AUTO-RP;
      uses TOPOLOGY-INTERFACE-FLAG-ROUTE-COUNT-TABLE;
      uses GROUP-MAP-SOURCE-TABLE;
      uses TRAFFIC-COUNTERS;
      uses GROUP-MAP-RPF-TABLE;
      uses SUMMARY;
      uses GRE;
      uses BIDIR-DF-WINNER-TABLE;
      uses TABLE-CONTEXT-TABLE;
      uses NEIGHBOR-SUMMARY-TABLE;
      uses CONTEXT;
      uses TOPOLOGY-ENTRY-FLAG-ROUTE-COUNT-TABLE;
      uses RPF-REDIRECT;
      uses TUNNEL-TABLE;
      uses MULTICAST-STATIC-ROUTE-TABLE;
      uses NEIGHBOR-TABLE;
    }
  }

  grouping NEIGHBOR-TABLE {
    description
      "Common node of vrf, default-context";
    container neighbors {
      description
        "PIM neighbor table";
      list neighbor {
        description
          "PIM neighbor information";
        leaf interface-name {
          type xr:Interface-name;
          description
            "Interface name";
        }
        leaf neighbor-address {
          type inet:ip-address-no-zone;
          description
            "Neighbor address";
        }
        uses PIM-NBR-BAG;
      }
    }
  }

  grouping SAF-TABLE {
    description
      "Common node of vrf, default-context";
    container safs {
      description
        "SAFI table and type";
      list saf {
        description
          "SAF name ";
        container rpf-hash-source-groups {
          description
            "PIM RPF multipath hash outcome";
          list rpf-hash-source-group {
            description
              "PIM RPF hash outcome for S,G";
            leaf source-address {
              type inet:ip-address-no-zone;
              description
                "Source address";
            }
            leaf group-address {
              type inet:ip-address-no-zone;
              description
                "Group address";
            }
            leaf mask-length {
              type int32;
              description
                "Hash mask length";
            }
            leaf mofrr {
              type int32;
              description
                "MOFRR";
            }
            uses PIM-RPF-HASH-BAG;
          }
        }
        container rpf-hash-sources {
          description
            "PIM RPF multipath hash outcome";
          list rpf-hash-source {
            description
              "PIM RPF hash outcome for S,G";
            leaf source-address {
              type inet:ip-address-no-zone;
              description
                "Source address";
            }
            leaf mofrr {
              type int32;
              description
                "MOFRR";
            }
            uses PIM-RPF-HASH-BAG;
          }
        }
        container rpfs {
          description
            "PIM RPF information table";
          list rpf {
            key "registered-address";
            description
              "PIM RPF information";
            leaf registered-address {
              type inet:ip-address-no-zone;
              description
                "Address for which RPF lookup";
            }
            uses PIM-RPF-INFO-BAG;
          }
        }
        leaf saf-name {
          type Pim-safi;
          description
            "SAF name ";
        }
        leaf topology-name {
          type xr:Cisco-ios-xr-string {
            length "1..32";
          }
          description
            "Topology name ";
        }
      }
    }
  }

  grouping MULTICAST-STATIC-ROUTE-TABLE {
    description
      "Common node of vrf, default-contextCommon node of
       vrf, default-context";
    container multicast-static-routes {
      description
        "PIM multicast static route table";
      list multicast-static-route {
        description
          "PIM multicast static route information";
        leaf address {
          type inet:ip-address-no-zone;
          description
            "Network address";
        }
        leaf prefix-length {
          type int32;
          description
            "Prefix length";
        }
        uses PIM-MSTATIC-BAG;
      }
    }
  }

  grouping RANGE-LIST-TABLE {
    description
      "Common node of vrf, default-context";
    container ranges {
      description
        "PIM range list information";
      list range {
        description
          "PIM range list information";
        leaf rp-address {
          type inet:ip-address-no-zone;
          description
            "RP address";
        }
        leaf client {
          type Pim-client;
          description
            "Client";
        }
        uses PIM-RL-BAG;
      }
    }
  }

  grouping STANDBY {
    description
      "Common node of pim-ma, pim6-ma";
    container standby {
      description
        "Standby Process";
      uses INTERFACE-TABLE;
      uses PIM-MA-COMMON-OPER-PIM-MA-SUMMARY-MP;
    }
  }

  grouping IPV4-PIM-ROLE-LVL-OPER-STANDBY {
    description
      "Common node of pim-ma, pim6-maCommon node of pim,
       ipv6-pim";
    container standby {
      description
        "Standby Process";
      uses DEFAULT-CONTEXT;
      uses PROCESS;
      uses VRF-TABLE;
    }
  }

  container pim-ma {
    config false;
    description
      "PIM MA operational data";
    uses ACTIVE;
    uses STANDBY;
  }
  container pim {
    config false;
    description
      "pim";
    uses IPV4-PIM-ROLE-LVL-OPER-STANDBY;
    uses IPV4-PIM-ROLE-LVL-OPER-ACTIVE;
  }
  container ipv6-pim {
    config false;
    description
      "ipv6 pim";
    uses IPV4-PIM-ROLE-LVL-OPER-STANDBY;
    uses IPV4-PIM-ROLE-LVL-OPER-ACTIVE;
  }
  container pim6-ma {
    config false;
    description
      "pim6 ma";
    uses ACTIVE;
    uses STANDBY;
  }
}
