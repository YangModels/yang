module Cisco-IOS-XR-tunnel-l2tun-oper {
  namespace "http://cisco.com/ns/yang/Cisco-IOS-XR-tunnel-l2tun-oper";
  prefix tunnel-l2tun-oper;

  import Cisco-IOS-XR-types {
    prefix xr;
  }
  include Cisco-IOS-XR-tunnel-l2tun-oper-sub1 {
    revision-date 2015-11-09;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR tunnel-l2tun package operational data.
     
     This module contains definitions
     for the following management objects:
       l2tp: L2TP operational data
       l2tpv2: l2tpv2
     
     Copyright (c) 2013-2016 by Cisco Systems, Inc.
     All rights reserved.";

  revision 2015-11-09 {
    description
      "IOS XR 6.0 revision.";
  }

  grouping CONTROL {
    description
      "Common node of counters, counters";
    container control {
      description
        "L2TP control messages counters";
      container tunnel-xr {
        description
          "L2TP control tunnel messages counters";
        container authentication {
          description
            "Tunnel authentication counters";
          uses L2TP-AUTHEN-STATS-DATA;
        }
        container global {
          description
            "Tunnel counters";
          uses L2TP-CTRL-MSG-STATS-GLOBAL-DATA;
        }
      }
      container tunnels {
        description
          "Table of tunnel IDs of control message counters";
        list tunnel {
          key "tunnel-id";
          description
            "L2TP tunnel control message counters";
          leaf tunnel-id {
            type int32;
            description
              "L2TP tunnel ID";
          }
          uses L2TP-CTRL-MSG-STATS-DATA;
        }
      }
    }
  }

  grouping SESSION-TABLE {
    description
      "Common node of l2tp, l2tpv2";
    container sessions {
      description
        "List of session IDs";
      list session {
        key "local-tunnel-id local-session-id";
        description
          "L2TP information for a particular session";
        leaf local-tunnel-id {
          type int32;
          description
            "Local tunnel ID";
        }
        leaf local-session-id {
          type int32;
          description
            "Local session ID";
        }
        uses L2TP-SESSION-INFO;
      }
    }
  }

  grouping SESSION {
    description
      "Common node of l2tp, l2tpv2";
    container session {
      description
        "L2TP control messages counters";
      container unavailable {
        description
          "L2TP session unavailable  information";
        uses L2TP-SESSION-ID-HOLD-DB-DATA;
      }
    }
  }

  grouping TUNNEL-CONFIGURATION-TABLE {
    description
      "Common node of l2tp, l2tpv2";
    container tunnel-configurations {
      description
        "List of tunnel IDs";
      list tunnel-configuration {
        key "local-tunnel-id";
        description
          "L2TP tunnel information";
        leaf local-tunnel-id {
          type int32;
          description
            "Local tunnel ID";
        }
        uses L2TP-CC-CFG-DATA;
      }
    }
  }

  grouping TUNNEL-TABLE {
    description
      "Common node of l2tp, l2tpv2";
    container tunnels {
      description
        "List of tunnel IDs";
      list tunnel {
        key "local-tunnel-id";
        description
          "L2TP tunnel  information";
        leaf local-tunnel-id {
          type int32;
          description
            "Local tunnel ID";
        }
        uses L2TP-CC-INFO;
      }
    }
  }

  grouping COUNTER-HIST-FAIL {
    description
      "Common node of l2tp, l2tpv2";
    container counter-hist-fail {
      description
        "Failure events leading to disconnection";
      uses L2TP-HIST-FAIL-STATS-BAG-DATA;
    }
  }

  grouping CLASS-TABLE {
    description
      "Common node of l2tp, l2tpv2";
    container classes {
      description
        "List of L2TP class names";
      list class {
        key "class-name";
        description
          "L2TP class name";
        leaf class-name {
          type xr:Cisco-ios-xr-string {
            length "1..31";
          }
          description
            "L2TP class name";
        }
        uses L2TP-CC-CLASS-DATA;
      }
    }
  }

  container l2tp {
    config false;
    description
      "L2TP operational data";
    container counters {
      description
        "L2TP control messages counters";
      uses CONTROL;
    }
    uses TUNNEL-CONFIGURATION-TABLE;
    uses COUNTER-HIST-FAIL;
    uses CLASS-TABLE;
    uses TUNNEL-TABLE;
    uses SESSION-TABLE;
    uses SESSION;
  }
  container l2tpv2 {
    config false;
    description
      "l2tpv2";
    container counters {
      description
        "L2TP control messages counters";
      container forwarding {
        description
          "L2TP forwarding messages counters";
        container sessions {
          description
            "List of class and session IDs";
          list session {
            key "tunnel-id session-id";
            description
              "L2TP information for a particular session";
            leaf tunnel-id {
              type int32;
              description
                "Local tunnel ID";
            }
            leaf session-id {
              type int32;
              description
                "Local session ID";
            }
            uses L2TP-SESS-FWD-STATS;
          }
        }
      }
      uses CONTROL;
    }
    container statistics {
      description
        "L2TP v2 statistics information";
      uses L2TPV2-STATS-DATA;
    }
    container tunnel {
      description
        "L2TPv2 tunnel ";
      container accounting {
        description
          "Tunnel accounting counters";
        container statistics {
          description
            "Tunnel accounting statistics";
          uses L2TPV2-CC-ACCT-STATS-DATA;
        }
      }
    }
    uses TUNNEL-CONFIGURATION-TABLE;
    uses COUNTER-HIST-FAIL;
    uses CLASS-TABLE;
    uses TUNNEL-TABLE;
    uses SESSION-TABLE;
    uses SESSION;
  }
}
