module Cisco-IOS-XR-atm-vcm-cfg {
  namespace "http://cisco.com/ns/yang/Cisco-IOS-XR-atm-vcm-cfg";
  prefix atm-vcm-cfg;

  import Cisco-IOS-XR-types {
    prefix xr;
  }
  import Cisco-IOS-XR-atm-common-datatypes {
    prefix dt1;
  }
  import Cisco-IOS-XR-ifmgr-cfg {
    prefix a1;
  }
  import Cisco-IOS-XR-l2vpn-cfg {
    prefix a2;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR atm-vcm package configuration.
     
     This YANG module augments the
       Cisco-IOS-XR-ifmgr-cfg,
       Cisco-IOS-XR-l2vpn-cfg
     modules with configuration data.
     
     Copyright (c) 2013-2016 by Cisco Systems, Inc.
     All rights reserved.";

  revision 2015-11-09 {
    description
      "IOS XR 6.0 revision.";
  }

  typedef Atm-vpi-bits-mode {
    type enumeration {
      enum "twelve" {
        value 12;
        description
          "12-bits VPI cell format";
      }
    }
    description
      "Atm vpi bits mode";
  }

  typedef Vpi-range {
    type uint32 {
      range "0..4095";
    }
    description
      "Vpi range";
  }

  typedef Atm-pvc-test-mode {
    type enumeration {
      enum "loop" {
        value 1;
        description
          "Loop mode applicable to L2/L3 PVC";
      }
      enum "reserved" {
        value 2;
        description
          "Reserved mode applicable to L2 PVC";
      }
    }
    description
      "Atm pvc test mode";
  }

  typedef Atm-pvp-test-mode {
    type enumeration {
      enum "loop" {
        value 1;
        description
          "Loop mode";
      }
    }
    description
      "Atm pvp test mode";
  }

  augment "/a1:interface-configurations/a1:interface-configuration" {
    description
      "This augment extends the configuration data of
       'Cisco-IOS-XR-ifmgr-cfg'";
    container atm {
      description
        "ATM Configuration";
      container pvps {
        description
          "PVP Configuration";
        list pvp {
          key "vpi";
          description
            "Configuration of particular PVP";
          container shape {
            description
              "Configure traffic shaping parameters";
            leaf type {
              type dt1:Atm-pvc-shaping;
              description
                "Traffic shaping type";
            }
            leaf peak-cell-rate {
              type uint32 {
                range "8..622080";
              }
              description
                "Peak cell rate (kbps)";
            }
            leaf sustained-cell-rate {
              when "../type != 'cbr' and ../type != 'ubr'" {
                description
                  "../Type != CBR and ../Type != UBR";
              }
              type uint32 {
                range "8..622080";
              }
              description
                "Sustained cell rate (kbps)";
            }
            leaf burst-size {
              when "../type != 'cbr' and ../type != 'ubr'" {
                description
                  "../Type != CBR and ../Type != UBR";
              }
              type uint32 {
                range "1..8192";
              }
              description
                "Burst size in cells";
            }
          }
          container cell-packing {
            presence "Indicates a cell-packing node is configured.";
            description
              "Configure cell-packing parameters.  All
               parameters are mandatory.";
            leaf maximum-cells-packed {
              type uint32 {
                range "2..255";
              }
              mandatory true;
              description
                "Maximum number of cells to be packed in a
                 packet";
            }
            leaf cell-packing-timer-id {
              type uint32 {
                range "1..3";
              }
              mandatory true;
              description
                "Which cell packing timer to use";
            }
          }
          leaf enable {
            type empty;
            description
              "Create the PVP";
          }
          leaf test-mode {
            type Atm-pvp-test-mode;
            description
              "Configure the PVP test mode";
          }
          leaf oam-segment-endpoint {
            type empty;
            description
              "Enable L2VPN PVP OAM segment endpoint";
          }
          leaf vpi {
            type Vpi-range;
            description
              "VPI value";
          }
        }
      }
      container pvcs {
        description
          "PVC Configuration";
        list pvc {
          key "vpi vci pv-ctype";
          description
            "Configuration particular PVC";
          container shape {
            description
              "Configure traffic shaping parameters";
            leaf type {
              type dt1:Atm-pvc-shaping;
              description
                "Traffic shaping type";
            }
            leaf peak-cell-rate {
              type uint32 {
                range "8..622080";
              }
              description
                "Peak cell rate (kbps)";
            }
            leaf sustained-cell-rate {
              when "../type != 'cbr' and ../type != 'ubr'" {
                description
                  "../Type != CBR and ../Type != UBR";
              }
              type uint32 {
                range "8..622080";
              }
              description
                "Sustained cell rate (kbps)";
            }
            leaf burst-size {
              when "../type != 'cbr' and ../type != 'ubr'" {
                description
                  "../Type != CBR and ../Type != UBR";
              }
              type uint32 {
                range "1..8192";
              }
              description
                "Burst size in cells";
            }
          }
          container oam-emulation {
            description
              "L2VPN OAM emulation";
            leaf enable {
              type empty;
              description
                "Enable OAM emulation";
            }
            leaf ais-transmit-rate {
              type uint32 {
                range "0..60";
              }
              description
                "AIS cell transmit rate (1 per x seconds)";
            }
          }
          container cell-packing {
            presence "Indicates a cell-packing node is configured.";
            description
              "Configure cell-packing parameters.  All
               parameters are mandatory.";
            leaf maximum-cells-packed {
              type uint32 {
                range "2..255";
              }
              mandatory true;
              description
                "Maximum number of cells to be packed in a
                 packet";
            }
            leaf cell-packing-timer-id {
              type uint32 {
                range "1..3";
              }
              mandatory true;
              description
                "Which cell packing timer to use";
            }
          }
          leaf vc-class {
            type dt1:Atm-vc-class-name;
            description
              "Name of the VC class";
          }
          leaf encapsulation {
            type dt1:Atm-pvc-encapsulation;
            description
              "Configure encapsulation";
          }
          leaf enable {
            type empty;
            description
              "Create the PVC";
          }
          leaf test-mode {
            type Atm-pvc-test-mode;
            description
              "Configure the PVC test mode";
          }
          leaf oam-segment-endpoint {
            type empty;
            description
              "Enable L2VPN PVC OAM segment endpoint";
          }
          leaf vpi {
            type Vpi-range;
            description
              "VPI value";
          }
          leaf vci {
            type uint32 {
              range "1..65535";
            }
            description
              "VCI value";
          }
          leaf pv-ctype {
            type dt1:Atm-pvc-data;
            description
              "PVC type";
          }
        }
      }
      container maximum-cell-packing-timers {
        presence "Indicates a maximum-cell-packing-timers node is configured.";
        description
          "Configure maximum cell-packing timers.  All
           parameters are mandatory.";
        leaf cell-packing-timer1 {
          type uint32 {
            range "50..4095";
          }
          mandatory true;
          description
            "Cell-packing timer1 (micro seconds)";
        }
        leaf cell-packing-timer2 {
          type uint32 {
            range "50..4095";
          }
          mandatory true;
          description
            "Cell-packing timer2 (micro seconds)";
        }
        leaf cell-packing-timer3 {
          type uint32 {
            range "50..4095";
          }
          mandatory true;
          description
            "Cell-packing timer3 (micro seconds)";
        }
      }
      container vp-tunnels {
        description
          "VP tunnel configuration";
        list vp-tunnel {
          key "vpi";
          description
            "Configure a VP tunnel on this interface";
          container shape {
            description
              "Configure Traffic shaping parameters";
            leaf type {
              type dt1:Atm-vp-shaping;
              description
                "Traffic shaping type";
            }
            leaf peak-cell-rate {
              type uint32 {
                range "8..622080";
              }
              description
                "Peak cell rate (kbps)";
            }
            leaf sustained-cell-rate {
              when "../type != 'cbr' and ../type != 'ubr'" {
                description
                  "../Type != CBR and ../Type != UBR";
              }
              type uint32 {
                range "8..622080";
              }
              description
                "Sustained cell rate (kbps)";
            }
            leaf burst-size {
              when "../type != 'cbr' and ../type != 'ubr'" {
                description
                  "../Type != CBR and ../Type != UBR";
              }
              type uint32 {
                range "1..8192";
              }
              description
                "Burst size in cells";
            }
          }
          leaf enable-hierarchical-shaping {
            type empty;
            description
              "Enable Hierarchical Shaping configuration";
          }
          leaf enable {
            type empty;
            description
              "Create the VP Tunnel";
          }
          leaf disable-f4oam {
            type empty;
            description
              "Disable F4 OAM configuration";
          }
          leaf vpi {
            type Vpi-range;
            description
              "VPI value";
          }
        }
      }
      leaf max-vpi-bits {
        type Atm-vpi-bits-mode;
        description
          "Support 12-bits VPI cell format";
      }
      leaf vc-class {
        type dt1:Atm-vc-class-name;
        description
          "Name of the VC class";
      }
    }
  }
  augment "/a1:interface-configurations/a1:interface-configuration/a2:l2-transport" {
    description
      "This augment extends the configuration data of
       'Cisco-IOS-XR-l2vpn-cfg'";
    container atm-port-mode-parameters {
      description
        "ATM L2transport Port Mode Parameters
         Configuration";
      container cell-packing {
        presence "Indicates a cell-packing node is configured.";
        description
          "Configure cell-packing parameters.  All
           parameters are mandatory.";
        leaf maximum-cells-packed {
          type uint32 {
            range "2..255";
          }
          mandatory true;
          description
            "Maximum number of cells to be packed in a
             packet";
        }
        leaf cell-packing-timer-id {
          type uint32 {
            range "1..3";
          }
          mandatory true;
          description
            "Which cell packing timer to use";
        }
      }
    }
  }
}
