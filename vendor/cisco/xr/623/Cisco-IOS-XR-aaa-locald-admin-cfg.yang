module Cisco-IOS-XR-aaa-locald-admin-cfg {
  namespace "http://cisco.com/ns/yang/Cisco-IOS-XR-aaa-locald-admin-cfg";
  prefix aaa-locald-admin-cfg;

  import Cisco-IOS-XR-types {
    prefix xr;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR aaa-locald package admin-plane configuration.
     
     This module contains definitions
     for the following management objects:
       aaa: Admin plane AAA configuration
     
     Copyright (c) 2013-2016 by Cisco Systems, Inc.
     All rights reserved.";

  revision 2015-11-09 {
    description
      "IOS XR 6.0 revision.";
  }

  container aaa {
    description
      "Admin plane AAA configuration";
    container usernames {
      description
        "Configure local username";
      list username {
        key "name";
        description
          "Admin Username";
        container usergroup-under-usernames {
          description
            "Specify the usergroup to which this admin user
             belongs";
          list usergroup-under-username {
            key "name";
            description
              "Name of the usergroup";
            leaf name {
              type xr:Cisco-ios-xr-string;
              description
                "Name of the usergroup";
            }
          }
        }
        leaf secret {
          type xr:Md5-password;
          description
            "Specify the secret for the admin user";
        }
        leaf name {
          type string;
          description
            "Username";
        }
      }
    }
  }
}
