module Cisco-IOS-XR-fabhfr-mib-cfg {
  namespace "http://cisco.com/ns/yang/Cisco-IOS-XR-fabhfr-mib-cfg";
  prefix fabhfr-mib-cfg;

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR fabhfr-mib package configuration.
     
     Copyright (c) 2013-2016 by Cisco Systems, Inc.
     All rights reserved.";

  revision 2017-05-31 {
    description
      "Yang Schema added.";
  }
  revision 2015-11-09 {
    description
      "IOS XR 6.0 revision.";
  }
}
