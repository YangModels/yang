submodule Cisco-IOS-XR-tty-management-cmd-oper-sub1 {
  belongs-to Cisco-IOS-XR-tty-management-cmd-oper {
    prefix Cisco-IOS-XR-tty-management-cmd-oper;
  }

  import Cisco-IOS-XR-types {
    prefix xr;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR tty-management-cmd package operational data.
     
     Copyright (c) 2013-2016 by Cisco Systems, Inc.
     All rights reserved.";

  revision 2015-11-09 {
    description
      "IOS XR 6.0 revision.";
  }

  grouping SHOWUSERS-ENTRY {
    description
      " Per Line Information";
    leaf line {
      type string;
      description
        "Line Number";
    }
    leaf user {
      type string;
      description
        "User Name";
    }
    leaf service {
      type string;
      description
        "Service Name";
    }
    leaf conns {
      type string;
      description
        "No. of Connections";
    }
    leaf idle-string {
      type string;
      description
        "Idle Time";
    }
    leaf location {
      type string;
      description
        "location";
    }
  }
}
