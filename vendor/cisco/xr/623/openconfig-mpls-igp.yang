submodule openconfig-mpls-igp {
  yang-version 1;
  belongs-to openconfig-mpls {
    prefix mpls;
  }

  import openconfig-mpls-ldp {
    prefix ldp;
  }
  import openconfig-mpls-sr {
    prefix sr;
  }
  import openconfig-extensions {
    prefix oc-ext;
  }

  organization
    "OpenConfig working group";
  contact
    "OpenConfig working group
     netopenconfig@googlegroups.com";
  description
    "Configuration generic configuration parameters for IGP-congruent
     LSPs";

  revision 2015-11-05 {
    description
      "Initial public release of MPLS models";
    reference "0.2.1";
  }
  revision 2015-10-14 {
    description
      "Work in progress";
    reference "0.2.0";
  }

  grouping igp-lsp-common {
    description
      "common definitions for IGP-congruent LSPs";
  }

  grouping igp-lsp-setup {
    description
      "signaling protocol definitions for IGP-based LSPs";
    container path-setup-protocol {
      description
        "select and configure the signaling method for
          the LSP";
      uses ldp:igp-lsp-ldp-setup;
      uses sr:igp-lsp-sr-setup;
    }
  }
  oc-ext:openconfig-version "0.2.1";
}
