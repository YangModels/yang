module Cisco-IOS-XR-ipv4-bgp-oc-oper {
  namespace "http://cisco.com/ns/yang/Cisco-IOS-XR-ipv4-bgp-oc-oper";
  prefix ipv4-bgp-oc-oper;

  import ietf-inet-types {
    prefix inet;
  }
  import Cisco-IOS-XR-types {
    prefix xr;
  }
  import Cisco-IOS-XR-ipv4-bgp-datatypes {
    prefix dt1;
  }
  include Cisco-IOS-XR-ipv4-bgp-oc-oper-sub1 {
    revision-date 2015-11-09;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ipv4-bgp-oc package operational data.
     
     This module contains definitions
     for the following management objects:
       oc-bgp: OC-BGP operational data
     
     Copyright (c) 2013-2016 by Cisco Systems, Inc.
     All rights reserved.";

  revision 2015-11-09 {
    description
      "IOS XR 6.0 revision.";
  }

  grouping ROUTE-TABLE {
    description
      "Common node of loc-rib, adj-rib-in-pre,
       adj-rib-in-post, adj-rib-out-pre,
       adj-rib-out-post";
    container routes {
      description
        "routes table";
      list route {
        description
          "route entry";
        leaf route {
          type inet:ip-prefix;
          description
            "Network in prefix/length format";
        }
        leaf neighbor-address {
          type inet:ip-address-no-zone;
          description
            "Neighbor address";
        }
        leaf path-id {
          type int32;
          description
            "Path ID";
        }
        uses BGP-OC-ROUTE-BAG;
      }
    }
  }

  grouping LOC-RIB {
    description
      "Common node of ipv4-unicast, ipv6-unicast";
    container loc-rib {
      description
        "Local rib route table";
      uses ROUTE-TABLE;
      uses NUM-ROUTES;
    }
  }

  grouping NUM-ROUTES {
    description
      "Common node of loc-rib, adj-rib-in-pre,
       adj-rib-in-post, adj-rib-out-pre,
       adj-rib-out-post";
    container num-routes {
      description
        "Number of routes in adjacency rib out-bound
         post-policy table";
      uses BGP-OC-RIB-COMMON-BAG;
    }
  }

  grouping OPEN-CONFIG-NEIGHBOR-TABLE {
    description
      "Common node of ipv4-unicast, ipv6-unicast";
    container open-config-neighbors {
      description
        "Neighbor list";
      list open-config-neighbor {
        key "neighbor-address";
        description
          "Neighbor name";
        container adj-rib-in-post {
          description
            "Adjacency rib in-bound post-policy table";
          uses ROUTE-TABLE;
          uses NUM-ROUTES;
        }
        container adj-rib-out-post {
          description
            "Adjacency rib out-bound post-policy table";
          uses ROUTE-TABLE;
          uses NUM-ROUTES;
        }
        container adj-rib-out-pre {
          description
            "Adjacency rib out-bound pre-policy table";
          uses ROUTE-TABLE;
          uses NUM-ROUTES;
        }
        container adj-rib-in-pre {
          description
            "Adjacency rib in-bound pre-policy table";
          uses ROUTE-TABLE;
          uses NUM-ROUTES;
        }
        leaf neighbor-address {
          type inet:ip-address-no-zone;
          description
            "Neighbor Address";
        }
      }
    }
  }

  container oc-bgp {
    config false;
    description
      "OC-BGP operational data";
    container bgp-rib {
      description
        "BGP-RIB operational data";
      container afi-safi-table {
        description
          "AFI-SAFIs information";
        container ipv4-unicast {
          description
            "IPv4 Unicast";
          uses LOC-RIB;
          uses OPEN-CONFIG-NEIGHBOR-TABLE;
        }
        container ipv6-unicast {
          description
            "IPv6 Unicast";
          uses LOC-RIB;
          uses OPEN-CONFIG-NEIGHBOR-TABLE;
        }
      }
    }
  }
}
