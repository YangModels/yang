module Cisco-IOS-XR-clns-isis-datatypes {
  namespace "http://cisco.com/ns/yang/Cisco-IOS-XR-clns-isis-datatypes";
  prefix clns-isis-datatypes;

  import Cisco-IOS-XR-types {
    prefix xr;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of generally useful
     derived YANG data types.
     
     Copyright (c) 2013-2016 by Cisco Systems, Inc.
     All rights reserved.";

  revision 2015-11-09 {
    description
      "IOS XR 6.0 revision.";
  }

  typedef Isis-address-family {
    type enumeration {
      enum "ipv4" {
        value 0;
        description
          "IPv4";
      }
      enum "ipv6" {
        value 1;
        description
          "IPv6";
      }
    }
    description
      "Isis address family";
  }

  typedef Isis-ipv6-prefix-length {
    type uint32 {
      range "0..128";
    }
    description
      "Isis ipv6 prefix length";
  }

  typedef Isis-ipv4-prefix-length {
    type uint32 {
      range "0..32";
    }
    description
      "Isis ipv4 prefix length";
  }

  typedef Isis-instance-name {
    type xr:Cisco-ios-xr-string {
      length "1..40";
    }
    description
      "Isis instance name";
  }

  typedef Isis-internal-level {
    type enumeration {
      enum "not-set" {
        value 0;
        description
          "Level not set";
      }
      enum "level1" {
        value 1;
        description
          "Level1";
      }
      enum "level2" {
        value 2;
        description
          "Level2";
      }
    }
    description
      "Isis internal level";
  }

  typedef Isis-link-group-name {
    type xr:Cisco-ios-xr-string {
      length "1..40";
    }
    description
      "Isis link group name";
  }

  typedef Isis-sub-address-family {
    type enumeration {
      enum "unicast" {
        value 0;
        description
          "Unicast";
      }
      enum "multicast" {
        value 1;
        description
          "Multicast";
      }
    }
    description
      "Isis sub address family";
  }

  typedef Isis-topology-name {
    type xr:Cisco-ios-xr-string {
      length "1..32";
    }
    description
      "Isis topology name";
  }
}
