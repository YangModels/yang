module Cisco-IOS-XR-ipv4-autorp-datatypes {
  namespace "http://cisco.com/ns/yang/Cisco-IOS-XR-ipv4-autorp-datatypes";
  prefix ipv4-autorp-datatypes;

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of generally useful
     derived YANG data types.
     
     Copyright (c) 2013-2016 by Cisco Systems, Inc.
     All rights reserved.";

  revision 2015-11-09 {
    description
      "IOS XR 6.0 revision.";
  }

  typedef Auto-rp-protocol-mode {
    type enumeration {
      enum "sparse" {
        value 0;
        description
          "Sparse Mode";
      }
      enum "bidirectional" {
        value 1;
        description
          "Bidirectional Mode";
      }
    }
    description
      "Auto rp protocol mode";
  }
}
