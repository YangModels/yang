submodule Cisco-IOS-XR-cmproxy-oper-sub1 {
  belongs-to Cisco-IOS-XR-cmproxy-oper {
    prefix Cisco-IOS-XR-cmproxy-oper;
  }

  import Cisco-IOS-XR-types {
    prefix xr;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR cmproxy package operational data.
     
     Copyright (c) 2013-2016 by Cisco Systems, Inc.
     All rights reserved.";

  revision 2015-11-09 {
    description
      "IOS XR 6.0 revision.";
  }

  grouping CMP-INV-ST {
    description
      "cmp inv info";
    leaf valid {
      type uint32;
      description
        "valid flag";
    }
    leaf card-type {
      type uint32;
      description
        "card type";
    }
    leaf card-type-string {
      type string {
        length "0..32";
      }
      description
        "card type string";
    }
    leaf nodeid {
      type int32;
      description
        "node ID";
    }
    leaf node-name {
      type string {
        length "0..32";
      }
      description
        "node name string";
    }
    leaf partner-id {
      type int32;
      description
        "partner node id";
    }
    leaf partner-name {
      type string {
        length "0..32";
      }
      description
        "partner name string";
    }
    leaf red-state {
      type uint32;
      description
        "redundancy state";
    }
    leaf red-state-string {
      type string {
        length "0..32";
      }
      description
        "redundancy state string";
    }
    leaf node-sw-state {
      type uint32;
      description
        "current software state";
    }
    leaf node-sw-state-string {
      type string {
        length "0..32";
      }
      description
        "current software state string";
    }
    leaf prev-sw-state {
      type uint32;
      description
        "previous software state";
    }
    leaf prev-sw-state-string {
      type string {
        length "0..32";
      }
      description
        "previous software state string";
    }
    leaf node-ip {
      type uint32;
      description
        "node IP address";
    }
    leaf node-ipv4-string {
      type string {
        length "0..16";
      }
      description
        "node IPv4 address string";
    }
  }
}
