submodule Cisco-IOS-XR-infra-policymgr-oper-sub1 {
  belongs-to Cisco-IOS-XR-infra-policymgr-oper {
    prefix Cisco-IOS-XR-infra-policymgr-oper;
  }

  import Cisco-IOS-XR-types {
    prefix xr;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR infra-policymgr package operational data.
     
     Copyright (c) 2013-2016 by Cisco Systems, Inc.
     All rights reserved.";

  revision 2015-11-09 {
    description
      "IOS XR 6.0 revision.";
  }

  typedef Plmgr-appln {
    type enumeration {
      enum "qos" {
        value 1;
        description
          "Application type QOS";
      }
      enum "pbr" {
        value 2;
        description
          "Application type PBR";
      }
      enum "subscriber-control" {
        value 3;
        description
          "Application type subscriber control";
      }
      enum "accounting" {
        value 4;
        description
          "Application type accounting";
      }
      enum "traffic" {
        value 5;
        description
          "Application type traffic";
      }
      enum "performance-traffic" {
        value 6;
        description
          "Application type performance traffic";
      }
    }
    description
      "Different Application types";
  }

  typedef Shared-bucket {
    type enumeration {
      enum "shared-bucket-type-not-specified" {
        description
          "shared bucket type not specified";
      }
      enum "shared-bucket-referred" {
        description
          "shared bucket referred";
      }
      enum "shared-bucket-defined" {
        description
          "shared bucket defined";
      }
    }
    description
      "Shared bucket";
  }

  typedef Vsvc-service {
    type enumeration {
      enum "vsvc-service-invalid" {
        value 0;
        description
          "vsvc service invalid";
      }
      enum "vsvc-service-v-path" {
        value 1;
        description
          "vsvc service v path";
      }
      enum "vsvc-service-ipsec" {
        value 2;
        description
          "vsvc service ipsec";
      }
      enum "vsvc-service-cgn" {
        value 3;
        description
          "vsvc service cgn";
      }
      enum "vsvc-service-o-flow" {
        value 4;
        description
          "vsvc service o flow";
      }
      enum "vsvc-service-output" {
        value 5;
        description
          "vsvc service output";
      }
      enum "vsvc-service-cfg-v-path" {
        value 6;
        description
          "vsvc service cfg v path";
      }
      enum "vsvc-service-sfp" {
        value 7;
        description
          "vsvc service sfp";
      }
      enum "vsvc-service-sfl" {
        value 8;
        description
          "vsvc service sfl";
      }
      enum "vsvc-service-sffl" {
        value 9;
        description
          "vsvc service sffl";
      }
      enum "vsvc-service-max" {
        value 10;
        description
          "vsvc service max";
      }
    }
    description
      "Vsvc service";
  }

  typedef Policy-param-unit {
    type enumeration {
      enum "policy-param-unit-invalid" {
        description
          "policy param unit invalid";
      }
      enum "policy-param-unit-bytes" {
        description
          "policy param unit bytes";
      }
      enum "policy-param-unit-kbytes" {
        description
          "policy param unit kbytes";
      }
      enum "policy-param-unit-mbytes" {
        description
          "policy param unit mbytes";
      }
      enum "policy-param-unit-gbytes" {
        description
          "policy param unit gbytes";
      }
      enum "policy-param-unit-bitsps" {
        description
          "policy param unit bitsps";
      }
      enum "policy-param-unit-kbitsps" {
        description
          "policy param unit kbitsps";
      }
      enum "policy-param-unit-mbitsps" {
        description
          "policy param unit mbitsps";
      }
      enum "policy-param-unit-gbitsps" {
        description
          "policy param unit gbitsps";
      }
      enum "policy-param-unit-cells-ps" {
        description
          "policy param unit cells ps";
      }
      enum "policy-param-unit-packets-ps" {
        description
          "policy param unit packets ps";
      }
      enum "policy-param-unit-us" {
        description
          "policy param unit us";
      }
      enum "policy-param-unit-ms" {
        description
          "policy param unit ms";
      }
      enum "policy-param-unit-seconds" {
        description
          "policy param unit seconds";
      }
      enum "policy-param-unit-packets" {
        description
          "policy param unit packets";
      }
      enum "policy-param-unit-cells" {
        description
          "policy param unit cells";
      }
      enum "policy-param-unit-percent" {
        description
          "policy param unit percent";
      }
      enum "policy-param-unit-per-thousand" {
        description
          "policy param unit per thousand";
      }
      enum "policy-param-unit-per-million" {
        description
          "policy param unit per million";
      }
      enum "policy-param-unit-hz" {
        description
          "policy param unit hz";
      }
      enum "policy-param-unit-khz" {
        description
          "policy param unit khz";
      }
      enum "policy-param-unit-mhz" {
        description
          "policy param unit mhz";
      }
      enum "policy-param-unit-ratio" {
        description
          "policy param unit ratio";
      }
      enum "policy-param-unit-max" {
        description
          "policy param unit max";
      }
    }
    description
      "Policy param unit";
  }

  typedef Wred {
    type enumeration {
      enum "wred-cos-cmd" {
        description
          "wred cos cmd";
      }
      enum "wred-dscp-cmd" {
        description
          "wred dscp cmd";
      }
      enum "wred-precedence-cmd" {
        description
          "wred precedence cmd";
      }
      enum "wred-discard-class-cmd" {
        description
          "wred discard class cmd";
      }
      enum "wred-mpls-exp-cmd" {
        description
          "wred mpls exp cmd";
      }
      enum "red-with-user-min-max" {
        description
          "red with user min max";
      }
      enum "red-with-default-min-max" {
        description
          "red with default min max";
      }
      enum "wred-dei-cmd" {
        description
          "wred dei cmd";
      }
      enum "wred-ecn-cmd" {
        description
          "wred ecn cmd";
      }
      enum "wred-invalid-cmd" {
        description
          "wred invalid cmd";
      }
    }
    description
      "Wred";
  }

  typedef Match-nas-port-sub-id {
    type enumeration {
      enum "match-nas-port-sub-id-unspecified" {
        value 0;
        description
          "match nas port sub id unspecified";
      }
      enum "match-nas-port-sub-id-adapter" {
        value 1;
        description
          "match nas port sub id adapter";
      }
      enum "match-nas-port-sub-id-channel" {
        value 2;
        description
          "match nas port sub id channel";
      }
      enum "match-nas-port-sub-id-ip-addr" {
        value 3;
        description
          "match nas port sub id ip addr";
      }
      enum "match-nas-port-sub-id-port" {
        value 4;
        description
          "match nas port sub id port";
      }
      enum "match-nas-port-sub-id-shelf" {
        value 5;
        description
          "match nas port sub id shelf";
      }
      enum "match-nas-port-sub-id-slot" {
        value 6;
        description
          "match nas port sub id slot";
      }
      enum "match-nas-port-sub-id-sub-interface" {
        value 7;
        description
          "match nas port sub id sub interface";
      }
      enum "match-nas-port-sub-id-type" {
        value 8;
        description
          "match nas port sub id type";
      }
      enum "match-nas-port-sub-id-vci" {
        value 9;
        description
          "match nas port sub id vci";
      }
      enum "match-nas-port-sub-id-vlan" {
        value 10;
        description
          "match nas port sub id vlan";
      }
      enum "match-nas-port-sub-id-vpi" {
        value 11;
        description
          "match nas port sub id vpi";
      }
      enum "match-nas-port-sub-id-max" {
        value 12;
        description
          "match nas port sub id max";
      }
    }
    description
      "Match nas port sub id";
  }

  typedef Match-mlp-negotiated {
    type enumeration {
      enum "match-mlp-negotiated-unspecified" {
        value 0;
        description
          "match mlp negotiated unspecified";
      }
      enum "match-mlp-negotiated" {
        value 1;
        description
          "match mlp negotiated";
      }
      enum "match-mlp-not-negotiated" {
        value 2;
        description
          "match mlp not negotiated";
      }
      enum "match-mlp-max" {
        value 3;
        description
          "match mlp max";
      }
    }
    description
      "Match mlp negotiated";
  }

  typedef Match-authen-status {
    type enumeration {
      enum "match-authen-status-unspecified" {
        value 0;
        description
          "match authen status unspecified";
      }
      enum "match-authen-status-authenticated" {
        value 1;
        description
          "match authen status authenticated";
      }
      enum "match-authen-status-unauthenticated" {
        value 2;
        description
          "match authen status unauthenticated";
      }
      enum "match-authen-status-max" {
        value 3;
        description
          "match authen status max";
      }
    }
    description
      "Match authen status";
  }

  typedef Class-map {
    type enumeration {
      enum "class-map-type-none" {
        description
          "class map type none";
      }
      enum "class-map-type-qos" {
        description
          "class map type qos";
      }
      enum "class-map-type-pbr" {
        description
          "class map type pbr";
      }
      enum "class-map-type-traffic" {
        description
          "class map type traffic";
      }
      enum "class-map-type-subs-control" {
        description
          "class map type subs control";
      }
      enum "class-map-type-max" {
        description
          "class map type max";
      }
    }
    description
      "Class map";
  }

  typedef Policy-map {
    type enumeration {
      enum "policy-map-type-none" {
        description
          "policy map type none";
      }
      enum "policy-map-type-qos" {
        description
          "policy map type qos";
      }
      enum "policy-map-type-pbr" {
        description
          "policy map type pbr";
      }
      enum "policy-map-type-traffic" {
        description
          "policy map type traffic";
      }
      enum "policy-map-type-subs-control" {
        description
          "policy map type subs control";
      }
      enum "policy-map-type-accounting" {
        description
          "policy map type accounting";
      }
      enum "policy-map-type-redirect" {
        description
          "policy map type redirect";
      }
      enum "policy-map-type-afmon" {
        description
          "policy map type afmon";
      }
      enum "policy-map-type-merge" {
        description
          "policy map type merge";
      }
      enum "policy-map-type-max" {
        description
          "policy map type max";
      }
    }
    description
      "Policy map";
  }

  typedef String-arr {
    type string;
    description
      "String arr";
  }

  grouping PLMGR-SUMMARY-BG {
    description
      "The policymgr database";
    leaf total-class-maps {
      type uint32;
      description
        "Total number of Classmaps configured";
    }
    leaf total-class-map-types {
      type uint32;
      description
        "Total number of Classmap types configured";
    }
    leaf total-policy-maps {
      type uint32;
      description
        "Total number of Policymaps configured";
    }
    leaf total-policy-map-types {
      type uint32;
      description
        "Total number of Policymap types configured";
    }
    list class-map {
      description
        "Summary of Classmap database";
      uses PLMGR-APP-DB-BG;
    }
    list policy-map {
      description
        "Summary of Policymap database";
      uses PLMGR-APP-DB-BG;
    }
  }

  grouping PLMGR-PMAP-LIST {
    description
      "policy-map list";
    leaf object-type {
      type Plmgr-appln;
      description
        "Application type configured";
    }
    leaf policy-map-name {
      type string {
        length "0..64";
      }
      description
        "Name of Policymap referencing a Classmap";
    }
  }

  grouping PLMGR-OBJ-CMAP-DETAIL-BG {
    description
      "Object detail.";
    leaf total-reference-objects {
      type uint32;
      description
        "Total number of Policymaps referencing a
         Classmap";
    }
    list policy-map-reference {
      description
        "List of Policymaps referencing a Classmap";
      uses PLMGR-PMAP-LIST;
    }
  }

  grouping PLMGR-OBJ-REF-SUMMARY-BG {
    description
      "Object detail.";
    leaf object-name {
      type string {
        length "0..64";
      }
      description
        "Name of object (Policymap/Classmap)";
    }
  }

  grouping PLMGR-OBJ-REF-PMAP-BG {
    description
      "Object detail.";
    leaf total-internal-reference-objects {
      type uint32;
      description
        "Total number of internal reference objects";
    }
    leaf total-class-maps {
      type uint32;
      description
        "Total number of Classmaps in a Policymap";
    }
    leaf total-flows {
      type uint32;
      description
        "Total flows in a Policymap";
    }
  }

  grouping PLMGR-APP-DB-BG {
    description
      "Per application Classmap/Policymap database";
    leaf object-type {
      type Plmgr-appln;
      description
        "Application type configured";
    }
    leaf total-objects {
      type uint32;
      description
        "Total number of objects configured for a
         specific object type";
    }
    leaf transient {
      type boolean;
      description
        "Transient object";
    }
    list reference {
      description
        "Each Policymap details";
      uses PLMGR-OBJ-REF-PMAP-BG;
    }
    list object {
      description
        "Each object details";
      uses PLMGR-OBJ-REF-SUMMARY-BG;
    }
    list class-map-reference {
      description
        "Each Classmapdetails";
      uses PLMGR-OBJ-CMAP-DETAIL-BG;
    }
  }

  grouping POLICY-PARAM-UINT32-ST {
    description
      "POLICY PARAM UINT32 ST";
    leaf value {
      type uint32;
      description
        "value";
    }
    leaf unit {
      type Policy-param-unit;
      description
        "unit";
    }
  }

  grouping PLMGR-PMAP-TARGETS-SUMMARY-BG {
    description
      "Policymap targets summary info. returned to show
       client(from policymgr)";
    leaf total-policy-maps-input-direction {
      type uint32;
      description
        "Total policymapsin the input direction";
    }
    leaf total-policy-maps-output-direction {
      type uint32;
      description
        "Total policymapsin the output direction";
    }
    leaf total-child-policy-maps-input-direction {
      type uint32;
      description
        "Totalpolicymaps applied as child policy in the
         input direction";
    }
    leaf total-child-policy-maps-output-direction {
      type uint32;
      description
        "Totalpolicymaps applied as child policy in the
         output direction";
    }
    leaf total-interfaces-input-direction {
      type uint32;
      description
        "Totalinterfaces with service-policy in the input
         direction";
    }
    leaf total-interfaces-output-direction {
      type uint32;
      description
        "Totalinterfaces with service-policy in the
         output direction";
    }
  }

  grouping PLMGR-PMAP-STR-TARGETS-BG {
    description
      "Policymap and target info returned to the show
       client";
    leaf-list target {
      type String-arr;
      description
        "target";
    }
    leaf-list parent-target {
      type String-arr;
      description
        "parent target";
    }
  }
}
