submodule Cisco-IOS-XR-wdsysmon-fd-oper-sub1 {
  belongs-to Cisco-IOS-XR-wdsysmon-fd-oper {
    prefix Cisco-IOS-XR-wdsysmon-fd-oper;
  }

  import Cisco-IOS-XR-types {
    prefix xr;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR wdsysmon-fd package operational data.
     
     Copyright (c) 2013-2016 by Cisco Systems, Inc.
     All rights reserved.";

  revision 2015-11-09 {
    description
      "IOS XR 6.0 revision.";
  }
  revision 2015-08-15 {
    description
      "IOS XR 5.3.2 revision.";
  }

  grouping PROCESS-CPU-UTIL {
    description
      "Process CPU utilization information";
    leaf process-name {
      type string;
      description
        "Process name";
    }
    leaf process-id {
      type uint32;
      description
        "Process ID";
    }
    leaf process-cpu-one-minute {
      type uint32;
      units "percentage";
      description
        "Process CPU utilization in percent for past 1
         minute";
    }
    leaf process-cpu-five-minute {
      type uint32;
      units "percentage";
      description
        "Process CPU utilization in percent for past 5
         minute";
    }
    leaf process-cpu-fifteen-minute {
      type uint32;
      units "percentage";
      description
        "Process CPU utilization in percent for past 15
         minute";
    }
  }

  grouping NODE-CPU-UTIL {
    description
      "Node CPU utilization information";
    leaf total-cpu-one-minute {
      type uint32;
      description
        "Total CPU utilization in past 1 minute";
    }
    leaf total-cpu-five-minute {
      type uint32;
      description
        "Total CPU utilization in past 5 minute";
    }
    leaf total-cpu-fifteen-minute {
      type uint32;
      description
        "Total CPU utilization in past 15 minute";
    }
    list process-cpu {
      description
        "Per process CPU utilization";
      uses PROCESS-CPU-UTIL;
    }
  }
}
