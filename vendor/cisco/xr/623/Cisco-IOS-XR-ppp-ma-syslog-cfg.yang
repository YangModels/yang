module Cisco-IOS-XR-ppp-ma-syslog-cfg {
  namespace "http://cisco.com/ns/yang/Cisco-IOS-XR-ppp-ma-syslog-cfg";
  prefix ppp-ma-syslog-cfg;

  import Cisco-IOS-XR-types {
    prefix xr;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ppp-ma-syslog package configuration.
     
     This module contains definitions
     for the following management objects:
       ppp: PPP configuration
     
     Copyright (c) 2013-2016 by Cisco Systems, Inc.
     All rights reserved.";

  revision 2015-11-09 {
    description
      "IOS XR 6.0 revision.";
  }

  container ppp {
    description
      "PPP configuration";
    container syslog {
      description
        "syslog option for session status";
      leaf enable-session-status {
        type empty;
        description
          "Enable syslog for ppp session status";
      }
    }
  }
}
