module Cisco-IOS-XR-infra-sla-datatypes {
  namespace "http://cisco.com/ns/yang/Cisco-IOS-XR-infra-sla-datatypes";
  prefix infra-sla-datatypes;

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of generally useful
     derived YANG data types.
     
     Copyright (c) 2013-2016 by Cisco Systems, Inc.
     All rights reserved.";

  revision 2015-11-09 {
    description
      "IOS XR 6.0 revision.";
  }

  typedef Sla-burst-interval-units-enum {
    type enumeration {
      enum "once" {
        value 1;
        description
          "Send one burst per probe";
      }
      enum "milliseconds" {
        value 2;
        description
          "Send bursts within a probe with an interval
           unit of milliseconds";
      }
      enum "seconds" {
        value 3;
        description
          "Send bursts within a probe with an interval
           unit of seconds";
      }
      enum "minutes" {
        value 4;
        description
          "Send bursts within a probe with an interval
           unit of minutes";
      }
      enum "hours" {
        value 5;
        description
          "Send bursts within a probe with an interval
           unit of hours";
      }
    }
    description
      "Sla burst interval units enum";
  }

  typedef Sla-send {
    type enumeration {
      enum "packet" {
        value 0;
        description
          "Send individual packets";
      }
      enum "burst" {
        value 1;
        description
          "Send bursts of packets";
      }
    }
    description
      "Sla send";
  }

  typedef Sla-probe-interval-day-enum {
    type enumeration {
      enum "monday" {
        value 1;
        description
          "Schedule every Monday";
      }
      enum "tuesday" {
        value 2;
        description
          "Schedule every Tuesday";
      }
      enum "wednesday" {
        value 3;
        description
          "Schedule every Wednesday";
      }
      enum "thursday" {
        value 4;
        description
          "Schedule every Thursday";
      }
      enum "friday" {
        value 5;
        description
          "Schedule every Friday";
      }
      enum "saturday" {
        value 6;
        description
          "Schedule every Saturday";
      }
      enum "sunday" {
        value 7;
        description
          "Schedule every Sunday";
      }
    }
    description
      "Sla probe interval day enum";
  }

  typedef Sla-packet-interval-units-enum {
    type enumeration {
      enum "once" {
        value 1;
        description
          "Send one packet per burst";
      }
      enum "milliseconds" {
        value 2;
        description
          "Send packets with an interval unit of
           milliseconds";
      }
      enum "seconds" {
        value 3;
        description
          "Send packets with an interval unit of seconds";
      }
      enum "minutes" {
        value 4;
        description
          "Send packets with an interval unit of minutes";
      }
      enum "hours" {
        value 5;
        description
          "Send packets with an interval unit of hours";
      }
    }
    description
      "Sla packet interval units enum";
  }

  typedef Sla-on-demand-repeat-interval-units-enum {
    type enumeration {
      enum "seconds" {
        value 3;
        description
          "Schedule probes to repeat with an interval unit
           of seconds";
      }
      enum "minutes" {
        value 4;
        description
          "Schedule probes to repeat with an interval unit
           of minutes";
      }
      enum "hours" {
        value 5;
        description
          "Schedule probes to repeat with an interval unit
           of hours";
      }
    }
    description
      "Sla on demand repeat interval units enum";
  }

  typedef Sla-probe-duration-units-enum {
    type enumeration {
      enum "seconds" {
        value 3;
        description
          "Schedule probes to run with a duration unit of
           seconds";
      }
      enum "minutes" {
        value 4;
        description
          "Schedule probes to run with a duration unit of
           minutes";
      }
      enum "hours" {
        value 5;
        description
          "Schedule probes to run with a duration unit of
           hours";
      }
      enum "day" {
        value 6;
        description
          "Schedule probes to run for a duration of 1 day";
      }
      enum "week" {
        value 7;
        description
          "Schedule probes to run for a duration of 1 week";
      }
    }
    description
      "Sla probe duration units enum";
  }

  typedef Sla-statistic-type-enum {
    type enumeration {
      enum "round-trip-delay" {
        value 1;
        description
          "Collect round trip delay metric data";
      }
      enum "one-way-delay-sd" {
        value 2;
        description
          "Collect one way delay source->dest metric data";
      }
      enum "one-way-delay-ds" {
        value 3;
        description
          "Collect one way delay dest->source metric data";
      }
      enum "round-trip-jitter" {
        value 4;
        description
          "Collect round trip delay metric data";
      }
      enum "one-way-jitter-sd" {
        value 5;
        description
          "Collect one way jitter source->dest metric data";
      }
      enum "one-way-jitter-ds" {
        value 6;
        description
          "Collect one way jitter dest->source metric data";
      }
      enum "one-way-loss-sd" {
        value 7;
        description
          "Collect one way loss source->dest metric data";
      }
      enum "one-way-loss-ds" {
        value 8;
        description
          "Collect one way loss dest->source metric data";
      }
    }
    description
      "Sla statistic type enum";
  }

  typedef Sla-buckets-size-units-enum {
    type enumeration {
      enum "buckets-per-probe" {
        value 0;
        description
          "Store results as a number of buckets per probe
           - note that this option has been DEPRECATED";
      }
      enum "probes-per-bucket" {
        value 1;
        description
          "Store results as a number of probes per bucket";
      }
    }
    description
      "Sla buckets size units enum";
  }

  typedef Sla-probe-interval-units-enum {
    type enumeration {
      enum "minutes" {
        value 4;
        description
          "Schedule probes to run with an interval unit of
           minutes";
      }
      enum "hours" {
        value 5;
        description
          "Schedule probes to run with an interval unit of
           hours";
      }
      enum "day" {
        value 6;
        description
          "Schedule probes to run every day";
      }
      enum "week" {
        value 7;
        description
          "Schedule probes to run every week";
      }
    }
    description
      "Sla probe interval units enum";
  }

  typedef Sla-on-demand-start-month-enum {
    type enumeration {
      enum "january" {
        value 0;
        description
          "January";
      }
      enum "february" {
        value 1;
        description
          "February";
      }
      enum "march" {
        value 2;
        description
          "March";
      }
      enum "april" {
        value 3;
        description
          "April";
      }
      enum "may" {
        value 4;
        description
          "May";
      }
      enum "june" {
        value 5;
        description
          "June";
      }
      enum "july" {
        value 6;
        description
          "July";
      }
      enum "august" {
        value 7;
        description
          "August";
      }
      enum "september" {
        value 8;
        description
          "September";
      }
      enum "october" {
        value 9;
        description
          "October";
      }
      enum "november" {
        value 10;
        description
          "November";
      }
      enum "december" {
        value 11;
        description
          "December";
      }
    }
    description
      "Sla on demand start month enum";
  }

  typedef Sla-padding-pattern {
    type enumeration {
      enum "hex" {
        value 0;
        description
          "Use an optionally specified hex pattern for
           packet padding";
      }
      enum "pseudo-random" {
        value 1;
        description
          "Use a pseudo-random bit sequence for packet
           padding";
      }
    }
    description
      "Sla padding pattern";
  }

  typedef Sla-on-demand-start-time-types-enum {
    type enumeration {
      enum "now" {
        value 0;
        description
          "Start immediately";
      }
      enum "absolute" {
        value 1;
        description
          "Start at a specified time";
      }
      enum "relative" {
        value 2;
        description
          "Start after a specified period";
      }
    }
    description
      "Sla on demand start time types enum";
  }

  typedef Sla-on-demand-probe-duration-units-enum {
    type enumeration {
      enum "seconds" {
        value 3;
        description
          "Schedule probes to run with a duration unit of
           seconds";
      }
      enum "minutes" {
        value 4;
        description
          "Schedule probes to run with a duration unit of
           minutes";
      }
      enum "hours" {
        value 5;
        description
          "Schedule probes to run with a duration unit of
           hours";
      }
    }
    description
      "Sla on demand probe duration units enum";
  }

  typedef Sla-on-demand-start-time-relative-units-enum {
    type enumeration {
      enum "seconds" {
        value 3;
        description
          "Schedule probe to start after a unit of seconds";
      }
      enum "minutes" {
        value 4;
        description
          "Schedule probe to start after a unit of minutes";
      }
      enum "hours" {
        value 5;
        description
          "Schedule probe to start after a unit of hours";
      }
    }
    description
      "Sla on demand start time relative units enum";
  }
}
