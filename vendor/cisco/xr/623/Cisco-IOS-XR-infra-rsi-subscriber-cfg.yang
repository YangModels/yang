module Cisco-IOS-XR-infra-rsi-subscriber-cfg {
  namespace "http://cisco.com/ns/yang/Cisco-IOS-XR-infra-rsi-subscriber-cfg";
  prefix infra-rsi-subscriber-cfg;

  import Cisco-IOS-XR-types {
    prefix xr;
  }
  import Cisco-IOS-XR-subscriber-infra-tmplmgr-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR infra-rsi-subscriber package configuration.
     
     This YANG module augments the
       Cisco-IOS-XR-subscriber-infra-tmplmgr-cfg
     module with configuration data.
     
     Copyright (c) 2013-2016 by Cisco Systems, Inc.
     All rights reserved.";

  revision 2015-07-30 {
    description
      "Descriptions updated.";
  }
  revision 2015-01-07 {
    description
      "IOS XR 5.3.1 revision.";
  }

  grouping VRF {
    description
      "Common node of ip-subscriber, ppp,
       subscriber-service";
    leaf vrf {
      type xr:Cisco-ios-xr-string {
        length "1..32";
      }
      description
        "Assign the interface to a VRF ";
    }
  }

  augment "/a1:dynamic-template/a1:subscriber-services/a1:subscriber-service" {
    description
      "This augment extends the configuration data of
       'Cisco-IOS-XR-subscriber-infra-tmplmgr-cfg'";
    uses VRF;
  }
  augment "/a1:dynamic-template/a1:ppps/a1:ppp" {
    description
      "This augment extends the configuration data of
       'Cisco-IOS-XR-subscriber-infra-tmplmgr-cfg'";
    uses VRF;
  }
  augment "/a1:dynamic-template/a1:ip-subscribers/a1:ip-subscriber" {
    description
      "This augment extends the configuration data of
       'Cisco-IOS-XR-subscriber-infra-tmplmgr-cfg'";
    uses VRF;
  }
}
