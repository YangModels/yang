module Cisco-IOS-XR-tty-management-datatypes {
  namespace "http://cisco.com/ns/yang/Cisco-IOS-XR-tty-management-datatypes";
  prefix tty-management-datatypes;

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of generally useful
     derived YANG data types.
     
     Copyright (c) 2013-2016 by Cisco Systems, Inc.
     All rights reserved.";

  revision 2015-01-07 {
    description
      "IOS XR 5.3.1 revision.";
  }

  typedef Tty-pager {
    type enumeration {
      enum "more" {
        value 1;
        description
          "More paging Utility";
      }
      enum "less" {
        value 2;
        description
          "Less paging Utility";
      }
      enum "none" {
        value 3;
        description
          "No Paging Utility";
      }
    }
    description
      "Tty pager";
  }

  typedef Tty-escape-char {
    type union {
      type enumeration {
        enum "break" {
          value 257;
          description
            "Cause escape on BREAK";
        }
        enum "default" {
          value 30;
          description
            "Use default escape character";
        }
        enum "none" {
          value 256;
          description
            "Disable escape entirely";
        }
      }
      type uint32 {
        range "0..257";
      }
    }
    description
      "Tty escape char";
  }

  typedef Tty-transport-protocol-select {
    type enumeration {
      enum "none" {
        value 0;
        description
          "No protocols";
      }
      enum "all" {
        value 1;
        description
          "All protocols";
      }
      enum "some" {
        value 2;
        description
          "Some Protocol";
      }
    }
    description
      "Tty transport protocol select";
  }

  typedef Tty-session-timeout-direction {
    type enumeration {
      enum "in" {
        value 1;
        description
          "Input traffic";
      }
      enum "in-out" {
        value 3;
        description
          "In & Output traffic";
      }
    }
    description
      "Tty session timeout direction";
  }

  typedef Tty-transport-protocol {
    type enumeration {
      enum "none" {
        value 0;
        description
          "No protocols";
      }
      enum "telnet" {
        value 1;
        description
          "TCP/IP Telnet protocol";
      }
      enum "ssh" {
        value 3;
        description
          "Unix ssh protocol";
      }
    }
    description
      "Tty transport protocol";
  }
}
