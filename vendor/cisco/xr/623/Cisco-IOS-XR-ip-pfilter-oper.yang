module Cisco-IOS-XR-ip-pfilter-oper {
  namespace "http://cisco.com/ns/yang/Cisco-IOS-XR-ip-pfilter-oper";
  prefix ip-pfilter-oper;

  import Cisco-IOS-XR-types {
    prefix xr;
  }
  include Cisco-IOS-XR-ip-pfilter-oper-sub1 {
    revision-date 2015-11-09;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ip-pfilter package operational data.
     
     This module contains definitions
     for the following management objects:
       pfilter-ma: Root class of PfilterMa Oper schema
     
     Copyright (c) 2013-2016 by Cisco Systems, Inc.
     All rights reserved.";

  revision 2015-11-09 {
    description
      "IOS XR 6.0 revision.";
  }

  grouping ACL-INFO-TABLE {
    description
      "Common node of ipv4, ipv6";
    container acl-info-table {
      description
        "Operational data for pfilter";
      container interface-infos {
        description
          "Operational data for pfilter";
        list interface-info {
          key "interface-name";
          description
            "Operational data for pfilter in bag";
          leaf interface-name {
            type xr:Interface-name;
            description
              "Name of the interface";
          }
          uses PFILTER-INTF-ACL-INFO;
        }
      }
    }
  }

  container pfilter-ma {
    config false;
    description
      "Root class of PfilterMa Oper schema";
    container nodes {
      description
        "Node-specific operational data";
      list node {
        key "node-name";
        description
          "PfilterMa operational data for a particular
           node";
        container process {
          description
            "Operational data for pfilter";
          container ipv6 {
            description
              "Operational data for pfilter";
            uses ACL-INFO-TABLE;
          }
          container ipv4 {
            description
              "Operational data for pfilter";
            uses ACL-INFO-TABLE;
          }
        }
        leaf node-name {
          type xr:Node-id;
          description
            "The node";
        }
      }
    }
  }
}
