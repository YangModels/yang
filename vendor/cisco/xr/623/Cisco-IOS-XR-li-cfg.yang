module Cisco-IOS-XR-li-cfg {
  namespace "http://cisco.com/ns/yang/Cisco-IOS-XR-li-cfg";
  prefix li-cfg;

  import Cisco-IOS-XR-types {
    prefix xr;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR li package configuration.
     
     This module contains definitions
     for the following management objects:
       lawful-intercept: Lawful intercept configuration
     
     Copyright (c) 2013-2016 by Cisco Systems, Inc.
     All rights reserved.";

  revision 2015-11-09 {
    description
      "IOS XR 6.0 revision.";
  }

  container lawful-intercept {
    description
      "Lawful intercept configuration";
    leaf disable {
      type empty;
      description
        "Disable lawful intercept feature";
    }
  }
}
