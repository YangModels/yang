module Cisco-IOS-XR-asr9k-sc-envmon-admin-oper {
  namespace "http://cisco.com/ns/yang/Cisco-IOS-XR-asr9k-sc-envmon-admin-oper";
  prefix asr9k-sc-envmon-admin-oper;

  import Cisco-IOS-XR-types {
    prefix xr;
  }
  include Cisco-IOS-XR-asr9k-sc-envmon-admin-oper-sub1 {
    revision-date 2017-01-19;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR asr9k-sc-envmon package
     admin-plane operational data.
     
     This module contains definitions
     for the following management objects:
       environmental-monitoring: Admin Environmental Monitoring
         Operational data space
     
     Copyright (c) 2013-2016 by Cisco Systems, Inc.
     All rights reserved.";

  revision 2017-01-19 {
    description
      "IOS-XR 6.2.1 revision.";
  }
  revision 2015-11-09 {
    description
      "IOS XR 6.0 revision.";
  }

  container environmental-monitoring {
    config false;
    description
      "Admin Environmental Monitoring Operational data
       space";
    container racks {
      description
        "Table of racks";
      list rack {
        key "rack";
        description
          "Number";
        container slots {
          description
            "Table of slots";
          list slot {
            key "slot";
            description
              "Name";
            container modules {
              description
                "Table of modules";
              list module {
                key "module";
                description
                  "Name";
                container sensor-types {
                  description
                    "Table of sensor types";
                  list sensor-type {
                    key "type";
                    description
                      "Type of sensor";
                    container sensor-names {
                      description
                        "Table of sensors";
                      list sensor-name {
                        key "name";
                        description
                          "Name of sensor";
                        container thresholds {
                          description
                            "The threshold information";
                          list threshold {
                            key "type";
                            description
                              "Types of thresholds";
                            container value-detailed {
                              description
                                "Detailed sensor threshold
                                 information";
                              uses ENVMON-THRESHOLD-INFO;
                            }
                            leaf trap {
                              type boolean;
                              description
                                "Threshold trap enable flag
                                 true-ENABLE, false-DISABLE";
                            }
                            leaf value-brief {
                              type xr:Hex-integer;
                              description
                                "Threshold value for the sensor";
                            }
                            leaf type {
                              type xr:Cisco-ios-xr-string;
                              description
                                "Threshold type";
                            }
                          }
                        }
                        container value-detailed {
                          description
                            "Detailed sensor information including
                             the sensor value";
                          uses ENVMON-SENSOR-INFO;
                        }
                        leaf value-brief {
                          type xr:Hex-integer;
                          description
                            "The sensor value";
                        }
                        leaf name {
                          type xr:Cisco-ios-xr-string;
                          description
                            "Sensor name";
                        }
                      }
                    }
                    leaf type {
                      type xr:Cisco-ios-xr-string;
                      description
                        "Sensor type";
                    }
                  }
                }
                container power {
                  description
                    "Module Power Draw";
                  container power-bag {
                    description
                      "Detailed power bag information";
                    uses ENVMON-POWER-INFO;
                  }
                }
                leaf module {
                  type xr:Cisco-ios-xr-string;
                  description
                    "Module name";
                }
              }
            }
            leaf slot {
              type xr:Cisco-ios-xr-string;
              description
                "Slot name";
            }
          }
        }
        leaf rack {
          type int32;
          description
            "Rack number";
        }
      }
    }
  }
}
