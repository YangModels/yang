module Cisco-IOS-XR-mpls-io-cfg {
  namespace "http://cisco.com/ns/yang/Cisco-IOS-XR-mpls-io-cfg";
  prefix mpls-io-cfg;

  import Cisco-IOS-XR-types {
    prefix xr;
  }
  import Cisco-IOS-XR-ifmgr-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR mpls-io package configuration.
     
     This YANG module augments the
       Cisco-IOS-XR-ifmgr-cfg
     module with configuration data.
     
     Copyright (c) 2013-2016 by Cisco Systems, Inc.
     All rights reserved.";

  revision 2017-05-18 {
    description
      "IOS XR 6.2.2 revision.";
  }
  revision 2015-11-09 {
    description
      "IOS XR 6.0 revision.";
  }

  augment "/a1:interface-configurations/a1:interface-configuration" {
    description
      "This augment extends the configuration data of
       'Cisco-IOS-XR-ifmgr-cfg'";
    container mpls {
      description
        "MPLS configuration under an interface";
      container label-security {
        description
          "MPLS label security";
        leaf multi-label-drop {
          type empty;
          description
            "Enable drop of multi-labelled incoming packets
             on a Interface";
        }
        leaf rpf {
          type empty;
          description
            "Enable MPLS RPF for incoming packets on a
             Interface";
        }
      }
      leaf mtu {
        type uint32 {
          range "68..65535";
        }
        description
          "Set the MPLS MTU for the interface";
      }
    }
  }
}
