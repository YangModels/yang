module Cisco-IOS-XR-mpls-lsd-cfg {
  namespace "http://cisco.com/ns/yang/Cisco-IOS-XR-mpls-lsd-cfg";
  prefix mpls-lsd-cfg;

  import Cisco-IOS-XR-types {
    prefix xr;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR mpls-lsd package configuration.
     
     This module contains definitions
     for the following management objects:
       mpls-lsd: MPLS LSD configuration data
     
     Copyright (c) 2013-2016 by Cisco Systems, Inc.
     All rights reserved.";

  revision 2015-11-09 {
    description
      "IOS XR 6.0 revision.";
  }

  typedef Mpls-ip-ttl-propagate-disable {
    type enumeration {
      enum "all" {
        value 0;
        description
          "Disable IP TTL propagation for all MPLS packets";
      }
      enum "forward" {
        value 1;
        description
          "Disable IP TTL propagation for only forwarded
           MPLS packets";
      }
      enum "local" {
        value 2;
        description
          "Disable IP TTL propagation for only locally
           generated MPLS packets";
      }
    }
    description
      "Mpls ip ttl propagate disable";
  }

  grouping TTL-EXPIRATION-POP {
    description
      "Common node of ipv4, ipv6";
    leaf ttl-expiration-pop {
      type uint32 {
        range "1..10";
      }
      description
        "Number of labels to pop upon MPLS IP TTL expiry";
    }
  }

  container mpls-lsd {
    description
      "MPLS LSD configuration data";
    container ipv6 {
      description
        "Configure IPv6 parameters";
      uses TTL-EXPIRATION-POP;
    }
    container ipv4 {
      description
        "Configure IPv4 parameters";
      uses TTL-EXPIRATION-POP;
    }
    container label-databases {
      description
        "Table of label databases";
      list label-database {
        key "label-database-id";
        description
          "A label database";
        container label-range {
          description
            "Label range";
          leaf minvalue {
            type uint32 {
              range "16000..1048575";
            }
            description
              "Minimum label value";
          }
          leaf max-value {
            type uint32 {
              range "16000..1048575";
            }
            description
              "Maximum label value";
          }
          leaf min-static-value {
            type uint32 {
              range "0..1048575";
            }
            description
              "Minimum static label value";
          }
          leaf max-static-value {
            type uint32 {
              range "0..1048575";
            }
            description
              "Maximum static label value";
          }
        }
        leaf label-database-id {
          type uint32;
          description
            "Label database identifier";
        }
      }
    }
    leaf app-reg-delay-disable {
      type empty;
      description
        "Disable LSD application reg delay";
    }
    leaf mpls-entropy-label {
      type empty;
      description
        "Enable MPLS Entropy Label";
    }
    leaf mpls-ip-ttl-propagate-disable {
      type Mpls-ip-ttl-propagate-disable;
      description
        "Disable Propagation of IP TTL onto the label
         stack";
    }
  }
}
