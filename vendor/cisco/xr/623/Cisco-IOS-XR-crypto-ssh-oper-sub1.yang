submodule Cisco-IOS-XR-crypto-ssh-oper-sub1 {
  belongs-to Cisco-IOS-XR-crypto-ssh-oper {
    prefix Cisco-IOS-XR-crypto-ssh-oper;
  }

  import Cisco-IOS-XR-types {
    prefix xr;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR crypto-ssh package operational data.
     
     Copyright (c) 2013-2016 by Cisco Systems, Inc.
     All rights reserved.";

  revision 2015-06-02 {
    description
      "IOS XR 5.3.2 revision.";
  }
  revision 2015-01-07 {
    description
      "IOS XR 5.3.1 revision.";
  }

  typedef Connection {
    type enumeration {
      enum "undefined" {
        value 0;
        description
          "connection type not yet known";
      }
      enum "shell" {
        value 1;
        description
          "Interactive Shell";
      }
      enum "exec" {
        value 2;
        description
          "Remote Command Execution";
      }
      enum "scp" {
        value 3;
        description
          "Secure Copy";
      }
      enum "sftp-subsystem" {
        value 4;
        description
          "Secure File Transfer";
      }
      enum "netconf-subsystem" {
        value 5;
        description
          "Netconf Subsystem";
      }
      enum "tl1-subsystem" {
        value 6;
        description
          "TL1 Subsystem";
      }
      enum "netconf-xml-subsystem" {
        value 7;
        description
          "Netconf XML Subsystem";
      }
    }
    description
      "SSH channel connection types";
  }

  typedef Authen {
    type enumeration {
      enum "password" {
        value 0;
        description
          "Password";
      }
      enum "rsa-public-key" {
        value 1;
        description
          "RSA public key encryption type";
      }
      enum "keyboard-interactive" {
        value 2;
        description
          "Keyboard interactive";
      }
    }
    description
      "SSH session authentication types";
  }

  typedef Version {
    type enumeration {
      enum "v2" {
        value 0;
        description
          "Version V2";
      }
      enum "v1" {
        value 1;
        description
          "Version V1";
      }
    }
    description
      "SSH state versions";
  }

  typedef States {
    type enumeration {
      enum "open" {
        value 1;
        description
          "SSH Open";
      }
      enum "version-ok" {
        value 2;
        description
          "SSH version OK";
      }
      enum "key-exchange-initialize" {
        value 3;
        description
          "Key exchange(KEX) init message exchanged";
      }
      enum "key-exchange-dh" {
        value 4;
        description
          "Diffie-Hellman(DH) secret is generated";
      }
      enum "new-keys" {
        value 5;
        description
          "New keys are received";
      }
      enum "authenticate-information" {
        value 6;
        description
          "Need more information to authenticate";
      }
      enum "authenticated" {
        value 7;
        description
          "The client successfully authenticated";
      }
      enum "channel-open" {
        value 8;
        description
          "Channel has been successfully opened";
      }
      enum "pty-open" {
        value 9;
        description
          "Allocated PTY";
      }
      enum "session-open" {
        value 10;
        description
          "Opened an exec shell";
      }
      enum "rekey" {
        value 11;
        description
          "Received rekey request";
      }
      enum "suspended" {
        value 12;
        description
          "Session is suspended";
      }
      enum "session-closed" {
        value 13;
        description
          "Session has been closed";
      }
    }
    description
      "SSH session states";
  }

  typedef Mac {
    type enumeration {
      enum "hmac-md5" {
        value 0;
        description
          "Hash-based Message Authentication Code(HMAC)
           MD5 algorithm";
      }
      enum "hmac-sha1" {
        value 1;
        description
          "Hash-based Message Authentication Code(HMAC)
           SHA1 algorithm";
      }
      enum "hmac-sha2-256" {
        value 2;
        description
          "Hash-based Message Authentication Code(HMAC)
           SHA2-256 algorithm";
      }
      enum "hmac-sha2-512" {
        value 3;
        description
          "Hash-based Message Authentication Code(HMAC)
           SHA2-512 algorithm";
      }
    }
    description
      "Different Message Authentication Code(MAC)
       functions";
  }

  typedef Cipher {
    type enumeration {
      enum "aes128-cbc" {
        value 0;
        description
          "Advanced Encryption Standard(AES) 128 bits
           cipher block chaining(CBC)";
      }
      enum "aes192-cbc" {
        value 1;
        description
          "Advanced Encryption Standard(AES) 192 bits
           cipher block chaining(CBC)";
      }
      enum "aes256-cbc" {
        value 2;
        description
          "Advanced Encryption Standard(AES) 256 bits
           cipher block chaining(CBC)";
      }
      enum "triple-des-cbc" {
        value 3;
        description
          "Triple Data Encryption Standard(DES) cipher
           block chaining(CBC)";
      }
      enum "aes128-ctr" {
        value 4;
        description
          "Advanced Encryption Standard(AES) 128 bits
           counter mode (CTR)";
      }
      enum "aes192-ctr" {
        value 5;
        description
          "Advanced Encryption Standard(AES) 192 bits
           counter mode (CTR)";
      }
      enum "aes256-ctr" {
        value 6;
        description
          "Advanced Encryption Standard(AES) 256 bits
           counter mode (CTR)";
      }
    }
    description
      "SSH session in and out cipher standards";
  }

  typedef Hostkey {
    type enumeration {
      enum "ssh-dss" {
        value 0;
        description
          "Algorithm type DSS";
      }
      enum "ssh-rsa" {
        value 1;
        description
          "Algorithm type RSA";
      }
    }
    description
      "SSH session authentication types";
  }

  typedef Kex-name {
    type enumeration {
      enum "diffie-hellman-group1" {
        value 0;
        description
          "Diffie-Hellman group 1 key exchange algorithm";
      }
      enum "diffie-hellman-group14" {
        value 1;
        description
          "Diffie-Hellman group 14 key exchange algorithm";
      }
      enum "diffie-hellman-group15" {
        value 2;
        description
          "Diffie-Hellman group 14 key exchange algorithm";
      }
      enum "diffie-hellman-group16" {
        value 3;
        description
          "Diffie-Hellman group 16 key exchange algorithm";
      }
      enum "diffie-hellman-group17" {
        value 4;
        description
          "Diffie-Hellman group 17 key exchange algorithm";
      }
      enum "diffie-hellman-group18" {
        value 5;
        description
          "Diffie-Hellman key group 18 exchange algorithm";
      }
      enum "ecdh-nistp256" {
        value 6;
        description
          "Elliptical curve Diffie-Hellman prime 256 key
           exchange algorithm";
      }
      enum "ecdh-nistp384" {
        value 7;
        description
          "Elliptical curve Diffie-Hellman prime 384 key
           exchange algorithm";
      }
      enum "ecdh-nistp521" {
        value 8;
        description
          "Elliptical curve Diffie-Hellman prime 521
           exchange algorithm";
      }
      enum "password-authenticated" {
        value 9;
        description
          "Password authenticated key agreement algorithm";
      }
    }
    description
      "Different key-exchange(kex) algorithms";
  }

  grouping SESSION-BRIEF-INFO {
    description
      "Information for a particular session/channel";
    list session-brief-info {
      description
        "session brief info";
      leaf session-id {
        type uint32;
        description
          "Session ID";
      }
      leaf channel-id {
        type uint32;
        description
          "Channel ID";
      }
      leaf vty-assigned {
        type boolean;
        description
          "Boolean indicating whether line VTY line number
           is valid";
      }
      leaf vty-line-number {
        type uint32;
        description
          "VTY line number";
      }
      leaf node-name {
        type xr:Node-id;
        description
          "Node name";
      }
      leaf session-state {
        type States;
        description
          "SSH session state";
      }
      leaf user-id {
        type string;
        description
          "User ID";
      }
      leaf host-address {
        type string;
        description
          "Host address";
      }
      leaf version {
        type Version;
        description
          "SSH state version";
      }
      leaf authentication-type {
        type Authen;
        description
          "Authentication method";
      }
      leaf connection-type {
        type Connection;
        description
          "Channel Connection Type";
      }
    }
  }

  grouping SSH-SESSION-BRIEF {
    description
      "Incoming and outgoing session information";
    container incoming-sessions {
      description
        "List of incoming sessions";
      uses SESSION-BRIEF-INFO;
    }
    container outgoing-sessions {
      description
        "List of outgoing sessions";
      uses SESSION-BRIEF-INFO;
    }
  }

  grouping SESSION-REKEY-INFO {
    description
      "Session rekey info";
    list session-rekey-info {
      description
        "session rekey info";
      leaf session-id {
        type uint32;
        description
          "Session ID";
      }
      leaf session-rekey-count {
        type uint32;
        description
          "Session Rekey Count";
      }
      leaf time-to-rekey {
        type string;
        description
          "Time To Rekey";
      }
      leaf volume-to-rekey {
        type string;
        description
          "Volume To Rekey";
      }
    }
  }

  grouping SSH-SESSION-REKEY {
    description
      "Incoming and outgoing session rekey details";
    container incoming-sessions {
      description
        "List of incoming sessions";
      uses SESSION-REKEY-INFO;
    }
    container outgoing-connections {
      description
        "List of outgoing connections";
      uses SESSION-REKEY-INFO;
    }
  }

  grouping SESSION-DETAIL-INFO {
    description
      "Particular session details";
    list session-detail-info {
      description
        "session detail info";
      leaf session-id {
        type uint32;
        description
          "Session ID";
      }
      leaf key-exchange {
        type Kex-name;
        description
          "Key exchange name";
      }
      leaf public-key {
        type Hostkey;
        description
          "Host key algorithm";
      }
      leaf in-cipher {
        type Cipher;
        description
          "In cipher algorithm";
      }
      leaf out-cipher {
        type Cipher;
        description
          "Out cipher algorithm";
      }
      leaf in-mac {
        type Mac;
        description
          "In MAC";
      }
      leaf out-mac {
        type Mac;
        description
          "Out MAC";
      }
    }
  }

  grouping SSH-SESSION-DETAIL {
    description
      "Incoming and outgoing session details";
    container incoming-sessions {
      description
        "List of incoming sessions";
      uses SESSION-DETAIL-INFO;
    }
    container outgoing-connections {
      description
        "List of outgoing connections";
      uses SESSION-DETAIL-INFO;
    }
  }
}
