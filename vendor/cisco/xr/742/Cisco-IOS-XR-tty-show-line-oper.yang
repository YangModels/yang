module Cisco-IOS-XR-tty-show-line-oper {
  namespace "http://cisco.com/ns/yang/Cisco-IOS-XR-tty-show-line-oper";
  prefix tty-show-line-oper;

  import cisco-semver {
    prefix semver;
  }
  include Cisco-IOS-XR-tty-show-line-oper-sub1 {
    revision-date 2021-08-27;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR tty-show-line package operational data.
     
     This module contains definitions
     for the following management objects:
       show-line: Show line statistics
     
     Copyright (c) 2013-2021 by Cisco Systems, Inc.
     All rights reserved.";

  revision 2021-08-27 {
    description
      "yang support for show line";
    semver:module-version "1.0.0";
  }
  revision 2019-04-05 {
    description
      "Establish semantic version baseline.";
  }
  revision 2015-11-09 {
    description
      "IOS XR 6.0 revision.";
  }

  container show-line {
    config false;
    description
      "Show line statistics";
    container lines {
      description
        "Show line statistics";
      list line {
        key "line-id";
        description
          "Show line statistics";
        leaf line-id {
          type uint32 {
            range "0..100";
          }
          description
            "Line ID";
        }
        uses SHOWLINE-ENTRY;
      }
    }
  }
}
