module Cisco-IOS-XR-um-snmp-server-cfg {
  namespace "http://cisco.com/ns/yang/Cisco-IOS-XR-um-snmp-server-cfg";
  prefix um-snmp-server-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR snmp-server package configuration.
     
     This YANG module augments the
     modules with configuration data.
     
     Copyright (c) 2019, 2021 by Cisco Systems, Inc.
     All rights reserved.";

  revision 2019-06-10 {
    description
      "Establish semantic version baseline.";
    semver:module-version "1.0.1";
  }
  revision 2019-04-12 {
    description
      "Initial version";
  }

  container snmp-server-mibs {
    description
      "MIB for configurations";
  }
  container snmp-server {
    description
      "SNMP configuration subcommands";
    container traps {
      description
        "Enable SNMP traps";
    }
  }
}
