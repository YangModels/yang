module Cisco-IOS-XR-plim-ether-stats-oper {
  namespace "http://cisco.com/ns/yang/Cisco-IOS-XR-plim-ether-stats-oper";
  prefix plim-ether-stats-oper;

  import Cisco-IOS-XR-types {
    prefix xr;
  }
  import cisco-semver {
    prefix semver;
  }
  include Cisco-IOS-XR-plim-ether-stats-oper-sub1 {
    revision-date 2019-04-05;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR plim-ether-stats package operational data.
     
     This module contains definitions
     for the following management objects:
       plimasic: Plim Asic Stats
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  container plimasic {
    config false;
    description
      "Plim Asic Stats";
    container nodes {
      description
        "List of nodes";
      list node {
        key "node-name";
        description
          "Per node NPU data";
        container statistics {
          description
            "Plim Asic stats directory";
          container interfaces {
            description
              "Plim Interface Entry";
            list interface {
              key "interface-name";
              description
                "Plim Asic Statistics Interface Based";
              leaf interface-name {
                type xr:Cisco-ios-xr-string;
                description
                  "Interface Name";
              }
              uses PLIM-ETHER-EDM-STRING;
            }
          }
          container summary {
            description
              "Plim Asic Statistics Summary";
            uses PLIM-ETHER-EDM-STRING;
          }
        }
        leaf node-name {
          type xr:Node-id;
          description
            "Node name";
        }
      }
    }
  }
}
