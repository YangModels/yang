submodule Cisco-IOS-XR-interface-cem-oper-sub1 {
  belongs-to Cisco-IOS-XR-interface-cem-oper {
    prefix Cisco-IOS-XR-interface-cem-oper;
  }

  import ietf-yang-types {
    prefix yang;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR interface-cem package operational data.
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  typedef Cem-rtp {
    type enumeration {
      enum "disabled" {
        value 0;
        description
          "Disabled";
      }
      enum "enabled" {
        value 1;
        description
          "Enabled";
      }
    }
    description
      "CEM RTP";
  }

  typedef Cem-signalling {
    type enumeration {
      enum "no-cas" {
        value 0;
        description
          "NoCAS";
      }
      enum "cas" {
        value 1;
        description
          "CAS";
      }
    }
    description
      "CEM signalling";
  }

  typedef Cem-dummy-mode {
    type enumeration {
      enum "last-frame" {
        value 0;
        description
          "LastFrame";
      }
      enum "user-defined" {
        value 1;
        description
          "UserDefined";
      }
    }
    description
      "CEM interface dummy mode";
  }

  typedef Cem-interface-state {
    type enumeration {
      enum "down" {
        value 0;
        description
          "Down";
      }
      enum "up" {
        value 1;
        description
          "Up";
      }
    }
    description
      "CEM interface states";
  }

  grouping CEM-INFO {
    description
      "CEM controller information";
    leaf admin-state {
      type Cem-interface-state;
      description
        "Administrative state";
    }
    leaf oper-state {
      type Cem-interface-state;
      description
        "Operational state";
    }
    leaf bandwidth {
      type uint32;
      units "kbit/s";
      description
        "Bandwidth in kbps";
    }
    leaf dejitter-buffer-length {
      type uint32;
      units "microsecond";
      description
        "Dejitter buffer length in microseconds";
    }
    leaf payload-size {
      type uint16;
      units "byte";
      description
        "Payload size in bytes";
    }
    leaf dummy-mode {
      type Cem-dummy-mode;
      description
        "Dummy mode";
    }
    leaf dummy-pattern {
      type yang:hex-string;
      description
        "Dummy pattern";
    }
    leaf idle-pattern {
      type yang:hex-string;
      description
        "Idle pattern";
    }
    leaf signalling {
      type Cem-signalling;
      description
        "Signalling";
    }
    leaf rtp-enabled {
      type Cem-rtp;
      description
        "RTP enabled or not";
    }
    leaf ingress-packets {
      type uint64;
      description
        "Ingress packets";
    }
    leaf ingress-drop-packets {
      type uint64;
      description
        "Ingress dropped packets";
    }
    leaf egress-packets {
      type uint64;
      description
        "Egress packets";
    }
    leaf egress-drop-packets {
      type uint64;
      description
        "Egress dropped packets";
    }
    leaf missing-packets {
      type uint64;
      description
        "Missing packets";
    }
    leaf reordered-packets {
      type uint64;
      description
        "Reordered packets";
    }
    leaf malformed-packets {
      type uint64;
      description
        "Malformed packets";
    }
    leaf misordered-drops {
      type uint64;
      description
        "Misorder drops";
    }
    leaf jitter-buffer-under-runs {
      type uint64;
      description
        "Jitter buffer underruns";
    }
    leaf errored-seconds {
      type uint64;
      units "second";
      description
        "Number of errored seconds";
    }
    leaf severely-errored-seconds {
      type uint64;
      units "second";
      description
        "Number of severely errored secs";
    }
    leaf unavailable-seconds {
      type uint64;
      units "second";
      description
        "Number of Unavailable seconds";
    }
    leaf failures {
      type uint64;
      description
        "Failure counts";
    }
  }
}
