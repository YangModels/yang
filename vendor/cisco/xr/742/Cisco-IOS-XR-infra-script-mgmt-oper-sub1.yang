submodule Cisco-IOS-XR-infra-script-mgmt-oper-sub1 {
  belongs-to Cisco-IOS-XR-infra-script-mgmt-oper {
    prefix Cisco-IOS-XR-infra-script-mgmt-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR infra-script-mgmt package operational data.
     
     Copyright (c) 2013-2021 by Cisco Systems, Inc.
     All rights reserved.";

  revision 2021-04-08 {
    description
      "Removed Detail, Output, Error, Reverse, Last, classes under ShowDel.";
    semver:module-version "2.0.0";
  }
  revision 2019-04-05 {
    description
      "Establish semantic version baseline.";
  }
  revision 2015-11-09 {
    description
      "IOS XR 6.0 revision.";
  }

  grouping SCRIPT-EXECUTION-DETAIL {
    description
      "Execution detail bag";
    list execution-detail {
      description
        "Execution Details";
      uses EXEC-DETAILS;
    }
  }

  grouping SCRIPT-EXECUTION-SUMMARY {
    description
      "Execution summary bag";
    list execution-summary {
      description
        "Summary of requests";
      uses EXEC-SUM-TYPE;
    }
  }

  grouping EXEC-LOG-TYPE {
    description
      "Show Script Execution - Log Fields";
    leaf output-file {
      type string;
      description
        "Output File Path";
    }
    leaf output-file-content {
      type string;
      description
        "Output File Content";
    }
    leaf error-file {
      type string;
      description
        "Error File Path";
    }
    leaf error-file-content {
      type string;
      description
        "Error File Content";
    }
  }

  grouping EXEC-EVENT-TYPE {
    description
      "Show Script Execution - Event Fields";
    leaf description {
      type string;
      description
        "Description";
    }
    leaf duration {
      type string;
      description
        "Time Elapsed";
    }
    leaf event {
      type string;
      description
        "Event";
    }
    leaf time {
      type string;
      description
        "Time";
    }
  }

  grouping EXEC-DETAIL-TYPE {
    description
      "Show Script Execution - Detail Fields";
    leaf log-path {
      type string;
      description
        "Log location";
    }
    leaf arguments {
      type string;
      description
        "Arguments for script execution";
    }
    leaf run-options {
      type string;
      description
        "Run options";
    }
  }

  grouping EXEC-SUM-TYPE {
    description
      "Script execution summary struct";
    leaf request-id {
      type uint32;
      description
        "Request Id of script execution";
    }
    leaf return-val {
      type string;
      description
        "Return value of execution";
    }
    leaf script-type {
      type string;
      description
        "Repository of script being executed";
    }
    leaf script-name {
      type string;
      description
        "Script name that script being execution";
    }
    leaf duration {
      type string;
      description
        "Duration of script execution";
    }
    leaf event-time {
      type string;
      description
        "Start time of script execution";
    }
    leaf status {
      type string;
      description
        "Status of script exectuion";
    }
  }

  grouping EXEC-DETAILS {
    description
      "Execution detail struct";
    container execution-summary {
      description
        "Summary information for execution request(s)";
      uses EXEC-SUM-TYPE;
    }
    container execution-detail {
      description
        "Detail information for execution request(s)";
      uses EXEC-DETAIL-TYPE;
    }
    list execution-event {
      description
        "Event information for execution request(s)";
      uses EXEC-EVENT-TYPE;
    }
  }

  grouping EXEC-LOGS {
    description
      "Execution log struct";
    container execution-details {
      description
        "Execution Details";
      uses EXEC-DETAILS;
    }
    container execution-log {
      description
        "Log information for execution request(s)";
      uses EXEC-LOG-TYPE;
    }
  }

  grouping SCRIPT-EXECUTION-LOG {
    description
      "Execution log bag";
    list execution-log-detail {
      description
        "Execution Log (Output/Error) Details";
      uses EXEC-LOGS;
    }
  }

  grouping SCRIPT-STATUS-SUMMARY {
    description
      "Status summary bag";
    list status-summary {
      description
        "Summary information for script status";
      uses STATUS-SUMMARY-TYPE;
    }
  }

  grouping STATUS-HISTORY-TYPE {
    description
      "Show Script Status - History Fields";
    leaf action {
      type string;
      description
        "Script action";
    }
    leaf checksum {
      type string;
      description
        "Checksum of script";
    }
    leaf description {
      type string;
      description
        "Description of user action";
    }
    leaf time-stamp {
      type string;
      description
        "Time of script action";
    }
  }

  grouping STATUS-SUMMARY-TYPE {
    description
      "Show Script Status - Summary Fields";
    leaf last-action {
      type string;
      description
        "Last action of the script";
    }
    leaf last-action-time {
      type string;
      description
        "Time of last action";
    }
    leaf script-name {
      type string;
      description
        "Name of Script";
    }
    leaf script-type {
      type string;
      description
        "Type of script";
    }
    leaf status {
      type string;
      description
        "Status of script";
    }
  }

  grouping STATUS-DETAILS {
    description
      "Status detail struct";
    container status-summary {
      description
        "Summary information for script status";
      uses STATUS-SUMMARY-TYPE;
    }
    leaf checksum {
      type string;
      description
        "Checksum of script";
    }
    list status-history {
      description
        "History information for script";
      uses STATUS-HISTORY-TYPE;
    }
  }

  grouping SCRIPT-STATUS-DETAIL {
    description
      "Status Detail bag";
    list status-detail {
      description
        "Script status details";
      uses STATUS-DETAILS;
    }
  }
}
