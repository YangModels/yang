module Cisco-IOS-XR-pfi-im-cmd-oper {
  namespace "http://cisco.com/ns/yang/Cisco-IOS-XR-pfi-im-cmd-oper";
  prefix pfi-im-cmd-oper;

  import Cisco-IOS-XR-types {
    prefix xr;
  }
  import cisco-semver {
    prefix semver;
  }
  include Cisco-IOS-XR-pfi-im-cmd-oper-sub2 {
    revision-date 2021-11-15;
  }
  include Cisco-IOS-XR-pfi-im-cmd-oper-sub1 {
    revision-date 2021-11-15;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR pfi-im-cmd package operational data.
     
     This module contains definitions
     for the following management objects:
       interfaces: Interface operational data
     
     Copyright (c) 2013-2021 by Cisco Systems, Inc.
     All rights reserved.";

  revision 2021-11-15 {
    description
      "Support added for sparse interface container.";
    semver:module-version "4.1.0";
  }
  revision 2021-05-23 {
    description
      "Removed container for non-dynamic interfaces.
       2020-12-02
       added new mediatype for 25GBASE_LR.
       2020-10-08
       Unit of last-data-time in milliseconds reverted to seconds for generic stats
       2020-10-01
       64-bit Bandwidth support
       2020-09-03
       Removed event-telemetry annotation from leaf interface-name of grouping BM-MEMBER-DATA
       2020-04-14
       Unit of last-data-time changed from seconds to milliseconds for generic stats
       2020-04-14
       Support added for non-dynamic interfaces.
       2020-04-14
       Data type of last-data-time changed from uint32 to uint64 for generic and proto stats";
    semver:module-version "4.0.0";
  }
  revision 2019-12-03 {
    description
      "Updated description.";
    semver:module-version "3.0.0";
  }
  revision 2019-08-14 {
    description
      "Added last state transition time.
       2019-07-23
       Changes in IosApi version.
       2019-05-30
       64 bit bandwidth changes.";
    semver:module-version "2.0.0";
  }
  revision 2019-04-05 {
    description
      "Establish semantic version baseline.";
    semver:module-version "1.0.0";
  }
  revision 2017-06-26 {
    description
      "Change identifiers to be more readable.";
  }
  revision 2017-05-01 {
    description
      "Fixing backward compatibility error in module.";
  }
  revision 2016-12-18 {
    description
      "Description updated.";
  }
  revision 2015-11-09 {
    description
      "IOS XR 6.0 revision.";
  }

  typedef Interface-type-set {
    type enumeration {
      enum "hardware-interfaces" {
        value 0;
        description
          "Restrict the output to hardware interfaces only";
      }
      enum "non-dynamic-interfaces" {
        value 1;
        description
          "Restrict the output to non-dynamic interfaces
           only";
      }
    }
    description
      "Interface type set";
  }

  grouping INTERFACE-SUMMARY {
    description
      "Common node of node-type-set, interfaces";
    container interface-summary {
      description
        "Interface summary information";
      uses IM-IF-SUMMARY-INFO;
    }
  }

  container interfaces {
    config false;
    description
      "Interface operational data";
    container interface-sparses {
      description
        "Sparse operational data for interfaces";
      list interface-sparse {
        key "interface-name";
        description
          "Sparse operational data for a particular
           interface";
        leaf interface-name {
          type xr:Interface-name;
          description
            "The name of the interface";
        }
        uses IM-SPARSE-INTF-INFO;
      }
    }
    container interface-xr {
      description
        "Detailed operational data for interfaces and
         configured features";
      list interface {
        key "interface-name";
        description
          "Detailed operational data for a particular
           interface";
        leaf interface-name {
          type xr:Interface-name;
          description
            "The name of the interface";
        }
        uses IM-CMD-INFO;
      }
    }
    container node-type-sets {
      description
        "Node and/or interface type specific view of
         interface summary data";
      list node-type-set {
        description
          "Summary data for all interfaces on a particular
           node";
        leaf node-name {
          type xr:Node-id;
          description
            "The location to filter on";
        }
        leaf type-set-name {
          type Interface-type-set;
          description
            "The interface type to filter on";
        }
        uses INTERFACE-SUMMARY;
      }
    }
    container interface-briefs {
      description
        "Brief operational data for interfaces";
      list interface-brief {
        key "interface-name";
        description
          "Brief operational attributes for a particular
           interface";
        leaf interface-name {
          type xr:Interface-name;
          description
            "The name of the interface";
        }
        uses IMDS-IFATTR-BASE-INFO;
      }
    }
    container inventory-summary {
      description
        "Inventory summary information";
      uses IM-IF-SUMMARY-INFO;
    }
    container interfaces {
      description
        "Descriptions for interfaces";
      list interface {
        key "interface-name";
        description
          "Description for a particular interface";
        leaf interface-name {
          type xr:Interface-name;
          description
            "The name of the interface";
        }
        uses IM-DESC-INFO;
      }
    }
    uses INTERFACE-SUMMARY;
  }
}
