module Cisco-IOS-XR-hwmod-bcc-disable-cfg {
  namespace "http://cisco.com/ns/yang/Cisco-IOS-XR-hwmod-bcc-disable-cfg";
  prefix hwmod-bcc-disable-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR hwmod-bcc-disable package configuration.
     
     This module contains definitions
     for the following management objects:
       hardware-module-bcc-disable: HW module BCC Disable config
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  container hardware-module-bcc-disable {
    description
      "HW module BCC Disable config";
    container bcc {
      description
        "bundle configuration";
      container node {
        description
          "Node";
        container all {
          description
            "all node configuration";
          leaf disable {
            type empty;
            description
              "bcc disable config";
          }
        }
      }
    }
  }
}
