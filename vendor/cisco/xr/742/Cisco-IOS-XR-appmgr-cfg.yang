module Cisco-IOS-XR-appmgr-cfg {
  namespace "http://cisco.com/ns/yang/Cisco-IOS-XR-appmgr-cfg";
  prefix appmgr-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR appmgr package configuration.
     
     This module contains definitions
     for the following management objects:
       appmgr: Appmgr configuration data
     
     Copyright (c) 2013-2021 by Cisco Systems, Inc.
     All rights reserved.";

  revision 2021-04-04 {
    description
      "Support for secure vault tuple.";
    semver:module-version "1.0.0";
  }
  revision 2021-02-15 {
    description
      "Support for process scripts.";
  }
  revision 2019-04-05 {
    description
      "Establish semantic version baseline.";
  }
  revision 2015-11-09 {
    description
      "IOS XR 6.0 revision.";
  }

  typedef App {
    type enumeration {
      enum "docker" {
        value 1;
        description
          "Docker application";
      }
    }
    description
      "App";
  }

  container appmgr {
    description
      "Appmgr configuration data";
    container applications {
      description
        "Table of applications";
      list application {
        key "name";
        description
          "Application configuration";
        container activate {
          description
            "Application activation";
          leaf type {
            type App;
            default "docker";
            description
              "Appliction type - type of application to be
               deployed";
          }
          leaf source {
            type string {
              length "1..255";
            }
            default "none";
            description
              "Appliction source - name of source";
          }
          leaf command {
            type string {
              length "1..1024";
            }
            default "none";
            description
              "Command to be run inside the container -
               Docker Only ";
          }
          leaf run-options {
            type string {
              length "1..1024";
            }
            default "none";
            description
              "Docker run options as a string - Docker Only";
          }
          leaf svault-options {
            type string {
              length "1..255";
            }
            default "none";
            description
              "Secure Vault Profile as a string - Docker
               Only";
          }
        }
        leaf name {
          type string {
            length "1..255";
          }
          description
            "Application identifier";
        }
      }
    }
  }
}
