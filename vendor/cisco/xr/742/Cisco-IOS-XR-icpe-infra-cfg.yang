module Cisco-IOS-XR-icpe-infra-cfg {
  namespace "http://cisco.com/ns/yang/Cisco-IOS-XR-icpe-infra-cfg";
  prefix icpe-infra-cfg;

  import ietf-inet-types {
    prefix inet;
  }
  import ietf-yang-types {
    prefix yang;
  }
  import Cisco-IOS-XR-types {
    prefix xr;
  }
  import cisco-semver {
    prefix semver;
  }
  import Cisco-IOS-XR-ifmgr-cfg {
    prefix a1;
  }
  import Cisco-IOS-XR-rgmgr-cfg {
    prefix a2;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR icpe-infra package configuration.
     
     This module contains definitions
     for the following management objects:
       nv-satellite-global: nV Satellite Global configuration
       nv-satellites: Satellite Configuration table
     
     This YANG module augments the
       Cisco-IOS-XR-ifmgr-cfg,
       Cisco-IOS-XR-rgmgr-cfg,
     modules with configuration data.
     
     Copyright (c) 2013-2019 by Cisco Systems, Inc.
     All rights reserved.";

  revision 2019-04-05 {
    description
      "Establish semantic version baseline.";
    semver:module-version "1.0.1";
  }
  revision 2017-09-30 {
    description
      "Ensure propagation of MDA mandatory state to YANG model.";
  }
  revision 2015-11-09 {
    description
      "IOS XR 6.0 revision.";
  }

  typedef Icpe-sat-id {
    type uint32 {
      range "100..65534";
    }
    description
      "Icpe sat id";
  }

  typedef Icpe-slot {
    type uint32 {
      range "0..8";
    }
    description
      "Icpe slot";
  }

  typedef Icpe-min-links {
    type uint32 {
      range "1..64";
    }
    description
      "Icpe min links";
  }

  typedef Icpe-subslot {
    type uint32 {
      range "0..8";
    }
    description
      "Icpe subslot";
  }

  grouping ENABLE {
    description
      "Common node of nv-satellite-fabric-network,
       satellites";
    leaf enable {
      type empty;
      mandatory true;
      description
        "Enable";
    }
  }

  grouping REMOTE-PORTS-TABLE {
    description
      "Common node of nv-satellite-fabric-link,
       satellites";
    container remote-ports {
      description
        "Remote Ports table";
      list remote-port {
        key "port-type slot sub-slot";
        description
          "Remote Ports";
        leaf port-type {
          type xr:Cisco-ios-xr-string;
          description
            "Port type";
        }
        leaf slot {
          type Icpe-slot;
          description
            "Slot";
        }
        leaf sub-slot {
          type Icpe-subslot;
          description
            "Sub slot";
        }
        leaf port-range {
          type string;
          mandatory true;
          description
            "Port range";
        }
      }
    }
  }

  grouping REDUNDANCY {
    description
      "Common node of nv-satellite-fabric-link,
       nv-satellite-fabric-network";
    container redundancy {
      description
        "Redundancy submode";
      leaf iccp-group {
        type uint32 {
          range "0..4294967295";
        }
        description
          "Links the satellite fabric to the given ICCP
           group";
      }
      leaf minimum-preferred-links {
        type Icpe-min-links;
        description
          "Mininum number of active links preferred";
      }
    }
  }

  augment "/a1:interface-configurations/a1:interface-configuration" {
    description
      "This augment extends the configuration data of
       'Cisco-IOS-XR-ifmgr-cfg'";
    container nv-satellite-access {
      description
        "nV Satellite Access Link Configuration";
    }
  }
  augment "/a1:interface-configurations/a1:interface-configuration" {
    description
      "This augment extends the configuration data of
       'Cisco-IOS-XR-ifmgr-cfg'";
    container nv-satellite-fabric-link {
      presence "Indicates a nv-satellite-fabric-link node is configured.";
      description
        "nV Satellite Fabric Link Configuration";
      leaf satellite {
        type Icpe-sat-id;
        mandatory true;
        description
          "Hub & Spoke connection to a single Satellite";
      }
      leaf minimum-required-links {
        type Icpe-min-links;
        description
          "Mininum number of active links required";
      }
      uses REDUNDANCY;
      uses REMOTE-PORTS-TABLE;
    }
  }
  augment "/a1:interface-configurations/a1:interface-configuration" {
    description
      "This augment extends the configuration data of
       'Cisco-IOS-XR-ifmgr-cfg'";
    container nv-satellite-fabric-network {
      presence "Indicates a nv-satellite-fabric-network node is configured.";
      description
        "Complex Network connection to one or more
         Satellites";
      container satellites {
        description
          "Connected Satellite table";
        list satellite {
          key "satellite-id";
          description
            "Connected Satellite";
          leaf satellite-id {
            type Icpe-sat-id;
            description
              "Satellite ID";
          }
          uses REMOTE-PORTS-TABLE;
          uses ENABLE;
        }
      }
      uses REDUNDANCY;
      uses ENABLE;
    }
  }
  augment "/a2:redundancy-group-manager/a2:iccp/a2:iccp-groups/a2:iccp-group" {
    description
      "This augment extends the configuration data of
       'Cisco-IOS-XR-rgmgr-cfg'";
    container nv-satellite {
      description
        "nV Satellite configuration";
      leaf system-mac {
        type yang:mac-address;
        description
          "Optional identifier for this system";
      }
    }
  }
  container nv-satellite-global {
    description
      "nV Satellite Global configuration";
    container chassis-mac {
      description
        "Chassis MAC address";
      leaf mac1 {
        type uint32 {
          range "0..2147483647";
        }
        units "byte";
        description
          "First two bytes of MAC address";
      }
      leaf mac2 {
        type uint32 {
          range "0..2147483647";
        }
        units "byte";
        description
          "Second two bytes of MAC address";
      }
      leaf mac3 {
        type uint32 {
          range "0..2147483647";
        }
        units "byte";
        description
          "Third two bytes of MAC address";
      }
    }
  }
  container nv-satellites {
    description
      "Satellite Configuration table";
    list nv-satellite {
      key "satellite-id";
      description
        "Satellite Configuration";
      container upgrade-on-connect {
        description
          "Satellite auto-upgrade capability";
        leaf connect-type {
          type enumeration {
            enum "on-connection" {
              value 1;
              description
                "Satellite Upgrade on Connection";
            }
            enum "on-first-connection" {
              value 2;
              description
                "Satellite Upgrade on First Connection after
                 configuration or host boot";
            }
          }
          description
            "When to upgrade the satellite";
        }
        leaf reference {
          type string;
          description
            "Reference name";
        }
        leaf image-reference {
          type string;
          description
            "Image Reference name";
        }
      }
      container candidate-fabric-ports {
        description
          "Enable interfaces on the satellite to be used
           as fabric ports table";
        list candidate-fabric-port {
          key "port-type slot sub-slot";
          description
            "Enable interfaces on the satellite to be used
             as fabric ports";
          leaf port-type {
            type xr:Cisco-ios-xr-string;
            description
              "Port type";
          }
          leaf slot {
            type Icpe-slot;
            description
              "Slot";
          }
          leaf sub-slot {
            type Icpe-subslot;
            description
              "Sub slot";
          }
          leaf port-range {
            type string;
            mandatory true;
            description
              "Port range";
          }
        }
      }
      container connection-info {
        description
          "Satellite User";
        leaf username {
          type string;
          description
            "Satellite Username";
        }
        leaf password {
          type xr:Md5-password;
          description
            "Encrypted password for the user";
        }
      }
      container redundancy {
        description
          "Redundancy submode";
        leaf host-priority {
          type uint32 {
            range "0..255";
          }
          description
            "Priority for this host for the given satellite";
        }
      }
      leaf vrf {
        type string;
        description
          "VRF for Satellite IP Address";
      }
      leaf timeout-warning {
        type uint32 {
          range "0..4294967295";
        }
        description
          "Discovery timeout warning for the satellite";
      }
      leaf device-name {
        type string;
        description
          "Satellite Name";
      }
      leaf description {
        type string;
        description
          "Satellite Description";
      }
      leaf type {
        type string;
        mandatory true;
        description
          "Satellite Type";
      }
      leaf enable {
        type empty;
        mandatory true;
        description
          "Enable";
      }
      leaf disc-timeout {
        type uint32 {
          range "0..4294967295";
        }
        description
          "Discovery timeout for the satellite";
      }
      leaf delayed-switchback {
        type uint32 {
          range "0..4294967295";
        }
        units "second";
        description
          "Timer (in seconds) for delaying switchback in a
           dual home setup";
      }
      leaf serial-number {
        type string;
        description
          "Satellite Serial Number";
      }
      leaf secret {
        type xr:Md5-password;
        description
          "Encrypted password for the Satellite";
      }
      leaf ip-address {
        type inet:ip-address-no-zone;
        description
          "Satellite IP Address";
      }
      leaf satellite-id {
        type Icpe-sat-id;
        description
          "Satellite ID";
      }
    }
  }
}
