submodule Cisco-IOS-XR-fib-common-oper-sub5 {
  belongs-to Cisco-IOS-XR-fib-common-oper {
    prefix Cisco-IOS-XR-fib-common-oper;
  }

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR fib-common package operational data.
     
     Copyright (c) 2013-2020 by Cisco Systems, Inc.
     All rights reserved.";

  revision 2020-12-02 {
    description
      "Adding per-object accounting.";
    semver:module-version "3.1.0";
  }
  revision 2020-01-16 {
    description
      "NBC documentation of CSCvs27272,CSCvs22018,CSCvs45512
       2019-10-29
       Updated srv6 global bag";
    semver:module-version "2.0.0";
  }
  revision 2019-09-27 {
    description
      "IOS XR 7.0.x revision.";
    semver:module-version "1.1.0";
  }
  revision 2019-04-05 {
    description
      "Establish semantic version baseline.";
    semver:module-version "1.0.0";
  }
  revision 2019-04-02 {
    description
      "Fixed schema descriptions.";
  }
  revision 2017-09-07 {
    description
      "Fixed type translation error.";
  }
  revision 2017-05-01 {
    description
      "Fixing backward compatibility error in module.";
  }
  revision 2017-01-20 {
    description
      "IOS XR 6.2.1 revision";
  }
  revision 2015-11-09 {
    description
      "IOS XR 6.0 revision.";
  }

  typedef Fib-global-aggregation-bag {
    type enumeration {
      enum "aggregation-type-state" {
        description
          "Aggregation OOR and ERROR State";
      }
      enum "aggregation-type-adj" {
        description
          "Aggregation Adj Replication";
      }
    }
    description
      "FIB Aggregation bag type";
  }

  typedef Fib-bag-ao-attribute {
    type enumeration {
      enum "none" {
        description
          "Invalid attribute type";
      }
      enum "error" {
        description
          "Error type attribute";
      }
      enum "out-of-resource" {
        description
          "Out-of-Resource type attribute";
      }
      enum "adjacency" {
        description
          "Adjacency type attribute";
      }
      enum "attribute-count" {
        description
          "Number of attributes";
      }
    }
    description
      "Attribute types for the Aggregation Object (AO)";
  }

  typedef Fib-bag-object {
    type enumeration {
      enum "none" {
        value 0;
        description
          "None";
      }
      enum "adjacency" {
        value 8;
        description
          "NHINFO";
      }
      enum "all" {
        value 23;
        description
          "ALL";
      }
      enum "object-count" {
        value 86;
        description
          "Number of Objects";
      }
    }
    description
      "Object type definitions for FIB Bags";
  }

  typedef Fib-glbl-bag-protocol {
    type enumeration {
      enum "ipv4" {
        description
          "IPv4 Protocol";
      }
      enum "ipv6" {
        description
          "IPv6 Protocol";
      }
      enum "mpls" {
        description
          "MPLS Protocol";
      }
    }
    description
      "Global Protocol definitions for FIB Bags";
  }

  grouping FIB-GLOBAL-CLIENT {
    description
      "FIB GLOBAL CLIENT";
    leaf client-id-xr {
      type uint32;
      description
        "Client ID";
    }
    leaf node-id {
      type uint32;
      description
        "Location of the client";
    }
    leaf client-name {
      type string;
      description
        "Client name";
    }
    leaf create-time {
      type uint64;
      description
        "Time of creation";
    }
  }

  grouping FIB-GLOBAL-AGGREGATION-SUMMARY {
    description
      "FIB Aggregation Summary";
    leaf total {
      type uint32;
      description
        "Total number of Aggregations";
    }
    leaf total-ipv4 {
      type uint32;
      description
        "Total number of Aggregations of V4";
    }
    leaf total-ipv6 {
      type uint32;
      description
        "Total number of Aggregations of V6";
    }
    leaf total-adj-ipv4 {
      type uint32;
      description
        "Total number of V4 Adjacency Replications";
    }
    leaf total-adj-ipv6 {
      type uint32;
      description
        "Total number of V6 Adjacency Replications";
    }
  }

  grouping FIB-GLOBAL-AGGREGATION-ADJ-REPL-ATTR-EXT {
    description
      "FIB Aggregation Data of Adjacency Replication";
    leaf mac-length {
      type uint32;
      description
        "Adjacency MAC length";
    }
    leaf mac-string {
      type string;
      description
        "Adjacency MAC string";
    }
  }

  grouping FIB-GLOBAL-AGGREGATION-ATTR-EXT {
    description
      "FIB GLOBAL AGGREGATION ATTR EXT";
    container adjacency-attribute-extension {
      when "../type = 'aggregation-type-adj'" {
        description
          "../type = 'AggregationTypeAdj'";
      }
      description
        "adjacency attribute extension";
      uses FIB-GLOBAL-AGGREGATION-ADJ-REPL-ATTR-EXT;
    }
    leaf type {
      type Fib-global-aggregation-bag;
      description
        "type";
    }
  }

  grouping FIB-GLOBAL-AGGREGATION-ATTR {
    description
      "FIB Aggregation Attribute";
    leaf node-id {
      type uint32;
      description
        "NodeID of Aggregation Info from";
    }
  }

  grouping FIB-GLOBAL-AGGREGATION-ADJ-REPL-KEY-EXT {
    description
      "FIB Aggregation Key-Ext of Adjacency Replication";
    leaf interface-name {
      type xr:Interface-name;
      description
        "Adjacency Replication Interface";
    }
    leaf is-mpls {
      type boolean;
      description
        "Adjacency Replication Is MPLS";
    }
  }

  grouping FIB-GLOBAL-AGGREGATION-KEY-EXT {
    description
      "FIB GLOBAL AGGREGATION KEY EXT";
    container adjacency-key-extension {
      when "../type = 'aggregation-type-adj'" {
        description
          "../type = 'AggregationTypeAdj'";
      }
      description
        "adjacency key extension";
      uses FIB-GLOBAL-AGGREGATION-ADJ-REPL-KEY-EXT;
    }
    leaf type {
      type Fib-global-aggregation-bag;
      description
        "type";
    }
  }

  grouping FIB-GLOBAL-AGGREGATION-KEY {
    description
      "FIB Aggregation Key";
    leaf protocol {
      type Fib-glbl-bag-protocol;
      description
        "Aggregation AFI Protocol";
    }
    leaf object-type {
      type Fib-bag-object;
      description
        "Aggregation Object Type";
    }
    leaf attribute-type {
      type Fib-bag-ao-attribute;
      description
        "Aggregation Attribute Type";
    }
  }

  grouping FIB-GLOBAL-AGGREGATION-ENTRY {
    description
      "FIB Aggregation Entry Info";
    container key {
      description
        "Aggregation Key";
      uses FIB-GLOBAL-AGGREGATION-KEY;
    }
    container key-extension {
      description
        "Aggregation Key Extension";
      uses FIB-GLOBAL-AGGREGATION-KEY-EXT;
    }
    list attribute {
      description
        "Aggregation Attributes";
      uses FIB-GLOBAL-AGGREGATION-ATTR;
    }
    list attribute-extension {
      description
        "Aggregation Attributes Ext";
      uses FIB-GLOBAL-AGGREGATION-ATTR-EXT;
    }
  }

  grouping FIB-GLOBAL-SUMMARY-OBJ-HISTORY {
    description
      "FIB Global summary object history";
    leaf count {
      type uint32;
      description
        "Placeholder for obj history counts";
    }
  }

  grouping FIB-GLOBAL-SUMMARY-OBJ-HISTORY-PROTO {
    description
      "FIB GLOBAL SUMMARY OBJ HISTORY PROTO";
    container base-object {
      description
        "Base object";
      uses FIB-GLOBAL-BASE-ST;
    }
    container object-history {
      description
        "Obj History";
      uses FIB-GLOBAL-SUMMARY-OBJ-HISTORY;
    }
  }

  grouping FIB-GLOBAL-SUMMARY-HEALTH {
    description
      "FIB Global summary health";
    leaf is-retry-db-empty {
      type boolean;
      description
        "Boolean to indicate if the retry database is
         empty or not";
    }
  }

  grouping FIB-GLOBAL-BASE-ST {
    description
      "FIB Global Base st";
    leaf protocol {
      type uint32;
      description
        "Fib Global base protocol";
    }
  }

  grouping FIB-GLOBAL-SUMMARY {
    description
      "FIB Global summary";
    container base-object {
      description
        "Base object";
      uses FIB-GLOBAL-BASE-ST;
    }
    container summary-counts {
      description
        "Global Summary counts";
      uses FIB-GLOBAL-SUMMARY-COUNTS;
    }
    container health {
      description
        "Global summary health";
      uses FIB-GLOBAL-SUMMARY-HEALTH;
    }
  }

  grouping FIB-GLOBAL-SUMMARY-PROTO {
    description
      "FIB GLOBAL SUMMARY PROTO";
    container common-info {
      description
        "Common Info";
      uses FIB-GLOBAL-SUMMARY-COMMON-INFO;
    }
    container summary {
      description
        "Global summary";
      uses FIB-GLOBAL-SUMMARY;
    }
  }

  grouping FIB-BAG-SUM-OBJ {
    description
      "Object summary";
    container object-attributes {
      description
        "Object's attributes";
      uses FIB-BAG-SUM-OBJ-ATTR;
    }
    leaf object-type {
      type uint32;
      description
        "Object type";
    }
    leaf object-name {
      type string;
      description
        "Object name";
    }
  }

  grouping FIB-BAG-SUM-OBJ-ATTR {
    description
      "Object summary attributes";
    leaf-list fsum-attr-cnt {
      type uint32;
      max-elements "4";
      description
        "fsum attr cnt";
    }
  }

  grouping FIB-BAG-GLBL-SUM {
    description
      "FIB BAG GLBL SUM";
    container obj-attr {
      description
        "Aggregate Summary across protocols";
      uses FIB-BAG-SUM-OBJ-ATTR;
    }
  }

  grouping FIB-GLOBAL-NUM-OBJECTS-ST {
    description
      "FIB Global summary num retries";
    leaf object-type {
      type string {
        length "0..30";
      }
      description
        "object";
    }
    leaf num-objects {
      type uint32;
      description
        "number of elements for this obj type";
    }
  }

  grouping FIB-GLOBAL-NUM-RETRIES-ST {
    description
      "FIB Global summary num retries";
    leaf retry-object-type {
      type string {
        length "0..30";
      }
      description
        "retry object";
    }
    leaf num-retries {
      type uint64;
      description
        "number of elements for this obj type in retry db";
    }
  }

  grouping FIB-GLOBAL-SUMMARY-COUNTS {
    description
      "FIB Global summary counts";
    leaf num-retry-timeouts {
      type uint64;
      description
        "number of retry timeouts";
    }
    leaf num-retry-ojbects {
      type uint32;
      description
        "number of elements in retry db";
    }
    list array-number-of-retry {
      description
        "number of objects in retry db";
      uses FIB-GLOBAL-NUM-RETRIES-ST;
    }
    list array-number-of-object {
      description
        "total number of objects";
      uses FIB-GLOBAL-NUM-OBJECTS-ST;
    }
  }

  grouping FIB-GLOBAL-SUMMARY-COMMON-INFO {
    description
      "FIB Global summary common";
    leaf count {
      type uint32;
      description
        "Placeholder for common info counts";
    }
  }

  grouping FIB-GLOBAL-SUMMARY-TOTAL {
    description
      "FIB GLOBAL SUMMARY TOTAL";
    container common-info {
      description
        "FIB global Summary Common info";
      uses FIB-GLOBAL-SUMMARY-COMMON-INFO;
    }
    container total-counters {
      description
        "Aggregate counters of all protocols";
      uses FIB-GLOBAL-SUMMARY-COUNTS;
    }
    container global-summary {
      description
        "Global Summary";
      uses FIB-BAG-GLBL-SUM;
    }
  }
}
