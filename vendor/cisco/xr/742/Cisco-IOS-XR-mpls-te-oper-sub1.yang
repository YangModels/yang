submodule Cisco-IOS-XR-mpls-te-oper-sub1 {
  belongs-to Cisco-IOS-XR-mpls-te-oper {
    prefix Cisco-IOS-XR-mpls-te-oper;
  }

  import ietf-inet-types {
    prefix inet;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR mpls-te package operational data.
     
     Copyright (c) 2013-2021 by Cisco Systems, Inc.
     All rights reserved.";

  revision 2021-01-19 {
    description
      "Added bandwidth-protection for auto-backups. Added signalled-bandwidth and soft-preemption for attribute set of autobackups.";
    semver:module-version "1.1.0";
  }
  revision 2020-03-28 {
    description
      "Added dark bandwidth accounting related oper info. Added stateful PCE static delegation related oper info. Added P2MP TE realted oper info. Added new operational leaves sim-rate-set sim-rate pce-address rewrite-lsd-queue tunnel-id-xr controller-handle backup-tunnel-sig-name protected-interface attribute-set-crc32 error delegation-status error context rewrite-lsd-queue simrate-enabled-in-last-application tunnel-id-xr p2mp-id-xr lsp-id-xr source-address-xr simrate-enabled-in-last-application is-expand-timer-running expand-timer-duration expand-timer-remain egress-interface-handle ingress-interface-handle srdb-check-enabled destination-create-time link-if-index create-time is-config-pending attribute-set-crc32 destination-list-crc32 maximum-destination-count maximum-tunnel-count srlg-number-xr tunnel-interface-name lsp-id-xr tunnel-rewrite-ctype tunnel-load-share tunnel-policy-class tunnel-forward-class lmp-is-allocated topology-node-igp-id topology-node-igp-area topology-node-is-router link-id classification-flags current-lsp-bandwidth-requested current-lsp-bandwidth-requested-type standby-lsp-bandwidth-requested standby-lsp-bandwidth-requested-type reopt-lsp-bandwidth-requested reopt-lsp-bandwidth-requested-type standby-reopt-lsp-bandwidth-requested standby-reopt-lsp-bandwidth-requested-type destination-address error tunnel-name-xr interface-name-xr interface-name";
    semver:module-version "1.0.0";
  }
  revision 2019-04-05 {
    description
      "Establish semantic version baseline.";
    semver:module-version "1.0.0";
  }
  revision 2018-08-01 {
    description
      "Removed empty groupings.";
  }
  revision 2017-09-07 {
    description
      "Fixed type translation error.";
  }
  revision 2017-05-01 {
    description
      "Fixing backward compatibility error in module.";
  }
  revision 2015-11-09 {
    description
      "IOS XR 6.0 revision.";
  }

  typedef Mpls-tp-tunnel-switchover-trig {
    type enumeration {
      enum "none" {
        description
          "Deprecated";
      }
      enum "bfd" {
        description
          "Deprecated";
      }
      enum "local-lockout" {
        description
          "Deprecated";
      }
      enum "remote-lockout" {
        description
          "Deprecated";
      }
      enum "ais" {
        description
          "Deprecated";
      }
      enum "ldi" {
        description
          "Deprecated";
      }
      enum "lkr" {
        description
          "Deprecated";
      }
      enum "link-down" {
        description
          "Deprecated";
      }
    }
    description
      "Deprecated";
  }

  typedef Mpls-tp-tunnel-active-lsp {
    type enumeration {
      enum "working" {
        description
          "Deprecated";
      }
      enum "protect" {
        description
          "Deprecated";
      }
      enum "none" {
        description
          "Deprecated";
      }
    }
    description
      "Deprecated";
  }

  typedef Mpls-tp-lsp-bfd-state {
    type enumeration {
      enum "down" {
        description
          "Deprecated";
      }
      enum "up" {
        description
          "Deprecated";
      }
    }
    description
      "Deprecated";
  }

  typedef Mpls-tp-lsp-oam-state {
    type enumeration {
      enum "none" {
        description
          "Deprecated";
      }
      enum "ldi" {
        description
          "Deprecated";
      }
      enum "lkr" {
        description
          "Deprecated";
      }
      enum "ais" {
        description
          "Deprecated";
      }
    }
    description
      "Deprecated";
  }

  typedef Mpls-tp-lsp-state {
    type enumeration {
      enum "down" {
        description
          "Deprecated";
      }
      enum "up" {
        description
          "Deprecated";
      }
      enum "active" {
        description
          "Deprecated";
      }
      enum "unknown" {
        description
          "Deprecated";
      }
    }
    description
      "Deprecated";
  }

  typedef Mpls-tp-tunnel-state {
    type enumeration {
      enum "admin-down" {
        description
          "Deprecated";
      }
      enum "admin-up" {
        description
          "Deprecated";
      }
      enum "oper-up" {
        description
          "Deprecated";
      }
      enum "oper-down" {
        description
          "Deprecated";
      }
    }
    description
      "Deprecated";
  }

  grouping MPLS-TE-TP-GLOBAL-INFO {
    description
      "Deprecated";
    container oam-protection-triggers {
      description
        "Deprecated";
      uses MPLS-TE-TP-OAM-PROT-TRIGGER;
    }
    leaf node-id {
      type inet:ipv4-address;
      description
        "Deprecated";
    }
    leaf global-id {
      type uint32;
      description
        "Deprecated";
    }
    leaf oam-refresh {
      type uint32;
      description
        "Deprecated";
    }
    leaf bfd-interval {
      type uint32;
      description
        "Deprecated";
    }
    leaf bfd-interval-in-micro-sec {
      type boolean;
      description
        "Deprecated";
    }
    leaf bfd-interval-standby {
      type uint32;
      description
        "Deprecated";
    }
    leaf bfd-interval-standby-in-micro-sec {
      type boolean;
      description
        "Deprecated";
    }
    leaf bfd-multiplier {
      type uint32;
      description
        "Deprecated";
    }
    leaf bfd-multiplier-standby {
      type uint32;
      description
        "Deprecated";
    }
    leaf wait-to-restore-interval {
      type uint32;
      description
        "Deprecated";
    }
    leaf alarm-suppression {
      type boolean;
      description
        "Deprecated";
    }
    leaf soak-time {
      type uint32;
      description
        "Deprecated";
    }
  }

  grouping MPLS-TE-TP-OAM-PROT-TRIGGER {
    description
      "Deprecated";
    leaf ais {
      type boolean;
      description
        "Deprecated";
    }
    leaf ldi {
      type boolean;
      description
        "Deprecated";
    }
    leaf lkr {
      type boolean;
      description
        "Deprecated";
    }
  }

  grouping MPLS-TE-TP-DETAIL-TUNNEL-LSP-INFO {
    description
      "Deprecated";
    container brief-information {
      description
        "Deprecated";
      uses MPLS-TE-TP-TUNNEL-LSP-INFO;
    }
    leaf oam-refresh-interval {
      type uint32;
      description
        "Deprecated";
    }
    leaf tp-out-label {
      type uint32;
      description
        "Deprecated";
    }
    leaf link-id {
      type uint32;
      description
        "Deprecated";
    }
    leaf out-interface-name {
      type string;
      description
        "Deprecated";
    }
    leaf out-next-hop {
      type inet:ipv4-address;
      description
        "Deprecated";
    }
    leaf in-label {
      type uint32;
      description
        "Deprecated";
    }
    leaf reserved-bandwidth {
      type uint32;
      description
        "Deprecated";
    }
  }

  grouping MPLS-TE-TP-TUNNEL-LSP-INFO {
    description
      "Deprecated";
    leaf lsp-id {
      type uint32;
      description
        "Deprecated";
    }
    leaf state {
      type Mpls-tp-lsp-state;
      description
        "Deprecated";
    }
    leaf lock-out {
      type boolean;
      description
        "Deprecated";
    }
    leaf rx-oam-state {
      type Mpls-tp-lsp-oam-state;
      description
        "Deprecated";
    }
    leaf tx-oam-state {
      type Mpls-tp-lsp-oam-state;
      description
        "Deprecated";
    }
    leaf bfd-state {
      type Mpls-tp-lsp-bfd-state;
      description
        "Deprecated";
    }
  }

  grouping MPLS-TE-TP-TUNNEL-INFO {
    description
      "Deprecated";
    container working-lsp {
      description
        "Deprecated";
      uses MPLS-TE-TP-TUNNEL-LSP-INFO;
    }
    container protect-lsp {
      description
        "Deprecated";
      uses MPLS-TE-TP-TUNNEL-LSP-INFO;
    }
    leaf tunnel-name {
      type string;
      description
        "Deprecated";
    }
    leaf source-tunnel-id {
      type uint32;
      description
        "Deprecated";
    }
    leaf source-node-id {
      type inet:ipv4-address;
      description
        "Deprecated";
    }
    leaf source-global-id {
      type uint32;
      description
        "Deprecated";
    }
    leaf destination-node-id {
      type inet:ipv4-address;
      description
        "Deprecated";
    }
    leaf destination-global-id {
      type uint32;
      description
        "Deprecated";
    }
    leaf remote-tunnel-id {
      type uint32;
      description
        "Deprecated";
    }
    leaf admin-status {
      type Mpls-tp-tunnel-state;
      description
        "Deprecated";
    }
    leaf operation-status {
      type Mpls-tp-tunnel-state;
      description
        "Deprecated";
    }
    leaf active-lsp {
      type Mpls-tp-tunnel-active-lsp;
      description
        "Deprecated";
    }
  }

  grouping MPLS-TE-TP-DETAIL-TUNNEL-INFO {
    description
      "Deprecated";
    container tunnel {
      description
        "Deprecated";
      uses MPLS-TE-TP-TUNNEL-INFO;
    }
    container working-lsp {
      description
        "Deprecated";
      uses MPLS-TE-TP-DETAIL-TUNNEL-LSP-INFO;
    }
    container protect-lsp {
      description
        "Deprecated";
      uses MPLS-TE-TP-DETAIL-TUNNEL-LSP-INFO;
    }
    container oam-protection-triggers {
      description
        "Deprecated";
      uses MPLS-TE-TP-OAM-PROT-TRIGGER;
    }
    leaf req-bandwidth {
      type uint32;
      description
        "Deprecated";
    }
    leaf oam-interval {
      type uint32;
      description
        "Deprecated";
    }
    leaf bfd-interval-active {
      type uint32;
      description
        "Deprecated";
    }
    leaf bfd-interval-active-in-micro-sec {
      type boolean;
      description
        "Deprecated";
    }
    leaf bfd-multiplier-active {
      type uint32;
      description
        "Deprecated";
    }
    leaf bfd-interval-standby {
      type uint32;
      description
        "Deprecated";
    }
    leaf bfd-interval-standby-in-micro-sec {
      type boolean;
      description
        "Deprecated";
    }
    leaf bfd-multiplier-standby {
      type uint32;
      description
        "Deprecated";
    }
    leaf tunnel-up-time {
      type uint32;
      description
        "Deprecated";
    }
    leaf switchover-trig {
      type Mpls-tp-tunnel-switchover-trig;
      description
        "Deprecated";
    }
    leaf switch-over-time {
      type uint32;
      description
        "Deprecated";
    }
  }

  grouping MPLS-TE-TP-TUNNEL-SUMMARY {
    description
      "Deprecated";
    leaf up-working-ls-ps {
      type uint32;
      description
        "Deprecated";
    }
    leaf active-working-ls-ps {
      type uint32;
      description
        "Deprecated";
    }
    leaf down-working-ls-ps {
      type uint32;
      description
        "Deprecated";
    }
    leaf locked-working-ls-ps {
      type uint32;
      description
        "Deprecated";
    }
    leaf up-protect-ls-ps {
      type uint32;
      description
        "Deprecated";
    }
    leaf active-protect-ls-ps {
      type uint32;
      description
        "Deprecated";
    }
    leaf down-protect-ls-ps {
      type uint32;
      description
        "Deprecated";
    }
    leaf locked-protect-ls-ps {
      type uint32;
      description
        "Deprecated";
    }
    leaf up-tunnels {
      type uint32;
      description
        "Deprecated";
    }
    leaf down-tunnels {
      type uint32;
      description
        "Deprecated";
    }
    leaf admin-down-tunnels {
      type uint32;
      description
        "Deprecated";
    }
    leaf complete-fec-working-ls-ps {
      type uint32;
      description
        "Deprecated";
    }
    leaf complete-fec-protect-ls-ps {
      type uint32;
      description
        "Deprecated";
    }
    leaf bfd-session-working-ls-ps {
      type uint32;
      description
        "Deprecated";
    }
    leaf bfd-session-protect-ls-ps {
      type uint32;
      description
        "Deprecated";
    }
  }
}
