module Cisco-IOS-XR-appmgr-oper {
  namespace "http://cisco.com/ns/yang/Cisco-IOS-XR-appmgr-oper";
  prefix appmgr-oper;

  import Cisco-IOS-XR-types {
    prefix xr;
  }
  import cisco-semver {
    prefix semver;
  }
  include Cisco-IOS-XR-appmgr-oper-sub1 {
    revision-date 2021-03-01;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR appmgr package operational data.
     
     This module contains definitions
     for the following management objects:
       appmgr: Appmgr Operational data space
     
     Copyright (c) 2013-2021 by Cisco Systems, Inc.
     All rights reserved.";

  revision 2021-03-01 {
    description
      "Adding information about installed packages";
    semver:module-version "1.0.0";
  }
  revision 2021-02-15 {
    description
      "Support for process scripts.";
  }
  revision 2019-04-05 {
    description
      "Establish semantic version baseline.";
  }
  revision 2015-11-09 {
    description
      "IOS XR 6.0 revision.";
  }

  container appmgr {
    config false;
    description
      "Appmgr Operational data space";
    container packages {
      description
        "Packages managed by the App Mgr";
      container installed {
        description
          "Installed packages";
        uses APPMGR-PACKAGES;
      }
    }
    container sources {
      description
        "Sources downloaded by the App Manager";
      list source {
        key "name";
        description
          "Information about a source";
        leaf name {
          type xr:Cisco-ios-xr-string;
          description
            "Name";
        }
        uses APPMGR-SOURCE;
      }
    }
    container applications {
      description
        "Applications managed by the App Mgr";
      list application {
        key "name";
        description
          "Information about individual application";
        container stats {
          description
            "Information about an application";
          uses APPMGR-APP-STATS;
        }
        container info {
          description
            "Information about an application";
          uses APPMGR-APP-INFO;
        }
        leaf name {
          type xr:Cisco-ios-xr-string;
          description
            "Name";
        }
      }
    }
  }
}
