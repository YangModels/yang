submodule Cisco-IOS-XR-icpe-sdacp-oper-sub3 {
  belongs-to Cisco-IOS-XR-icpe-sdacp-oper {
    prefix Cisco-IOS-XR-icpe-sdacp-oper;
  }

  import ietf-inet-types {
    prefix inet;
  }
  import ietf-yang-types {
    prefix yang;
  }
  import Cisco-IOS-XR-types {
    prefix xr;
  }
  import cisco-semver {
    prefix semver;
  }
  include Cisco-IOS-XR-icpe-sdacp-oper-sub2 {
    revision-date 2019-04-05;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR icpe-sdacp package operational data.
     
     Copyright (c) 2013-2019 by Cisco Systems, Inc.
     All rights reserved.";

  revision 2019-04-05 {
    description
      "Establish semantic version baseline.";
    semver:module-version "1.0.1";
  }
  revision 2015-11-09 {
    description
      "IOS XR 6.0 revision.";
  }

  grouping ICPE-SDACP-DISC-SAT-LINK-TYPE {
    description
      "ICPE SDACP DISC SAT LINK TYPE";
    leaf interface-handle {
      type xr:Interface-name;
      description
        "Interface handle";
    }
    leaf satellite-status {
      type Dpm-proto-state;
      description
        "Satellite status";
    }
    leaf conflict-reason {
      type uint32;
      description
        "Conflict reason";
    }
    leaf satellite-chassis-vendor {
      type Xr-yang-string;
      description
        "Satellite chassis vendor";
    }
    leaf satellite-interface-id {
      type uint32;
      description
        "Satellite interface ID";
    }
    leaf satellite-interface-mac {
      type yang:mac-address;
      description
        "Satellite interface MAC";
    }
    leaf satellite-chassis-mac {
      type yang:mac-address;
      description
        "Satellite chassis MAC";
    }
    leaf satellite-serial-id {
      type Xr-yang-string;
      description
        "Satellite serial id";
    }
    leaf satellite-module-vendor {
      type Xr-yang-string;
      description
        "Satellite module vendor";
    }
  }

  grouping ICPE-SDACP-SAT-TYPE {
    description
      "ICPE SDACP SAT TYPE";
    leaf satellite-id {
      type uint16;
      description
        "Satellite ID";
    }
    leaf satellite-status {
      type Dpm-proto-state;
      description
        "Satellite status";
    }
    leaf conflict-reason {
      type uint32;
      description
        "Conflict reason";
    }
    leaf satellite-ip-address {
      type inet:ipv4-address;
      description
        "Satellite IP address";
    }
    leaf host-ip-address {
      type inet:ipv4-address;
      description
        "Host IP address";
    }
    list interface {
      description
        "ICPE Discovered satellite state information
         table";
      uses ICPE-SDACP-DISC-SAT-LINK-TYPE;
    }
  }

  grouping ICPE-SDACP-DISC-SFL-TYPE {
    description
      "ICPE SDACP DISC SFL TYPE";
    leaf interface-name {
      type Xr-yang-string;
      description
        "Interface name";
    }
    leaf interface-status {
      type Dpm-proto-state;
      description
        "Interface status";
    }
  }

  grouping ICPE-SDACP-CFG-SFL {
    description
      "ICPE Configured interface state information";
    leaf interface-name-xr {
      type Xr-yang-string;
      description
        "Interface name";
    }
    list interface {
      description
        "ICPE Discovery interface state information table";
      uses ICPE-SDACP-DISC-SFL-TYPE;
    }
    list satellite {
      description
        "ICPE Satellite state information table";
      uses ICPE-SDACP-SAT-TYPE;
    }
  }
}
