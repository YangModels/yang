submodule Cisco-IOS-XR-subscriber-srg-oper-sub1 {
  belongs-to Cisco-IOS-XR-subscriber-srg-oper {
    prefix Cisco-IOS-XR-subscriber-srg-oper;
  }

  import ietf-inet-types {
    prefix inet;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR subscriber-srg package operational data.
     
     Copyright (c) 2013-2024 by Cisco Systems, Inc.
     All rights reserved.";

  revision 2024-04-22 {
    description
      "Added SRG client message stats in SRG group information
       2024-04-05
         added srg object track registration status.
       2024-03-28
         added subscriber infra state info.
       2022-08-24
         added srg nack request and reply time.
       2022-05-22
         last error component id is added.
       2021-11-21
         stale stats are updated.";
    semver:module-version "1.2.0";
  }
  revision 2021-07-21 {
    description
      "EOMS time is updated in cli.";
    semver:module-version "1.1.0";
  }
  revision 2019-10-03 {
    description
      "added new bags and bag elements in srg-show bag.";
    semver:module-version "1.1.0";
  }
  revision 2019-04-05 {
    description
      "Establish semantic version baseline.";
    semver:module-version "1.0.0";
  }
  revision 2015-11-09 {
    description
      "IOS XR 6.0 revision.";
  }

  typedef Srg-show-so-reason {
    type enumeration {
      enum "internal" {
        value 0;
        description
          "SwitchOver for Internal Reason";
      }
      enum "admin" {
        value 1;
        description
          "SwitchOver for Admin";
      }
      enum "peer-up" {
        value 2;
        description
          "SwitchOver for Peer UP";
      }
      enum "peer-down" {
        value 3;
        description
          "SwitchOver for Peer Down";
      }
      enum "object-tracking-status-change" {
        value 4;
        description
          "SwitchOver for Object Tracking status change";
      }
      enum "srg-show-so-reason-max" {
        value 5;
        description
          "Unknown Switchover Reason";
      }
    }
    description
      "Subscriber Redundancy Switchover Reason";
  }

  typedef Srg-show-session-error {
    type enumeration {
      enum "none" {
        value 0;
        description
          "Invalid Error";
      }
      enum "hard" {
        value 1;
        description
          "Hard Error";
      }
      enum "soft" {
        value 2;
        description
          "Soft Error";
      }
    }
    description
      "SRG Session Error Operation";
  }

  typedef Srg-show-session-operation {
    type enumeration {
      enum "none" {
        value 0;
        description
          "No Operation";
      }
      enum "update" {
        value 1;
        description
          "SRG Session Update Operation";
      }
      enum "delete" {
        value 2;
        description
          "SRG Session Delete Operation";
      }
      enum "in-sync" {
        value 3;
        description
          "SRG Session In Sync";
      }
    }
    description
      "SRG Session Operation";
  }

  typedef Srg-show-comp {
    type enumeration {
      enum "srga" {
        value 0;
        description
          "SRG Agent";
      }
      enum "dhcpv4" {
        value 1;
        description
          "DHCPv4";
      }
      enum "dhcpv6" {
        value 2;
        description
          "DHCPv6";
      }
      enum "pppoe" {
        value 3;
        description
          "PPPoE";
      }
      enum "ppp" {
        value 4;
        description
          "PPP";
      }
      enum "l2tp" {
        value 5;
        description
          "L2TP";
      }
      enum "iedge" {
        value 6;
        description
          "iEdge";
      }
    }
    description
      "SRG Components";
  }

  typedef Srg-peer-status {
    type enumeration {
      enum "not-configured" {
        value 0;
        description
          "Peer not configured";
      }
      enum "initialize" {
        value 1;
        description
          "Peer initialization";
      }
      enum "retry" {
        value 2;
        description
          "Peer retry pending";
      }
      enum "connect" {
        value 3;
        description
          "Connection in Progress";
      }
      enum "listen" {
        value 4;
        description
          "Listening in Progress";
      }
      enum "registration" {
        value 5;
        description
          "Awaiting Registration from Peer";
      }
      enum "cleanup" {
        value 6;
        description
          "Peer cleanup in progress";
      }
      enum "connected" {
        value 7;
        description
          "Peer Connected";
      }
      enum "established" {
        value 8;
        description
          "Peer Established";
      }
    }
    description
      "SRG Peer Status";
  }

  typedef Srg-show-slave-mode {
    type enumeration {
      enum "none" {
        value 0;
        description
          "Not Configured";
      }
      enum "warm" {
        value 1;
        description
          "Warm Modem";
      }
      enum "hot" {
        value 2;
        description
          "Hot Mode";
      }
    }
    description
      "SRG Slave Mode";
  }

  typedef Srg-show-role {
    type enumeration {
      enum "none" {
        value 0;
        description
          "Not Configured";
      }
      enum "master" {
        value 1;
        description
          "Master Role";
      }
      enum "slave" {
        value 2;
        description
          "Slave Role";
      }
    }
    description
      "SRG Role";
  }

  typedef Srg-show-im-role {
    type enumeration {
      enum "none" {
        value 0;
        description
          "Not Determined";
      }
      enum "master" {
        value 1;
        description
          "Master Role";
      }
      enum "slave" {
        value 2;
        description
          "Slave Role";
      }
    }
    description
      "SRG Interface Management Role";
  }

  grouping SRG-GROUP-STATS-COUNTER {
    description
      "Group counter description and value";
    leaf counter-name {
      type string {
        length "0..40";
      }
      description
        "Name of counter";
    }
    leaf counter-val {
      type uint32;
      description
        "Counter value";
    }
  }

  grouping SRG-GROUP-CLIENT-STATS {
    description
      "List of SRG group client statistics";
    list counter {
      description
        "List of SRG group counters";
      uses SRG-GROUP-STATS-COUNTER;
    }
  }

  grouping SRG-SHOW-GROUP-ROUTE-IPV6 {
    description
      "srg static route ipv6";
    leaf ipv6 {
      type inet:ipv6-address;
      description
        "ipv6";
    }
    leaf vrf-name {
      type string {
        length "0..33";
      }
      description
        "vrf name";
    }
    leaf prefix-len {
      type uint8;
      description
        "prefix len";
    }
    leaf type {
      type uint8;
      description
        "type";
    }
    leaf tag {
      type uint32;
      description
        "tag";
    }
  }

  grouping SRG-SHOW-GROUP-ROUTE-IPV4 {
    description
      "srg static route ipv4";
    leaf vrf-name {
      type string {
        length "0..33";
      }
      description
        "vrf name";
    }
    leaf prefix-len {
      type uint8;
      description
        "prefix len";
    }
    leaf ipv4 {
      type inet:ipv4-address;
      description
        "ipv4";
    }
    leaf tag {
      type uint32;
      description
        "tag";
    }
  }

  grouping SRG-SHOW-GRP-SWITCHOVER-HISTORY {
    description
      "srg switchover history";
    leaf group-switchover-time {
      type uint64;
      description
        "Group Switchover Time";
    }
    leaf role {
      type Srg-show-im-role;
      description
        "SRG Role";
    }
    leaf reason {
      type Srg-show-so-reason;
      description
        "Switchover reason";
    }
  }

  grouping SRG-SHOW-GROUP-INTF-INFO {
    description
      "Subscriber Redundancy Group Interface-List
       Information";
    leaf interface-name {
      type string;
      description
        "Interface Name";
    }
    leaf interface-synchronization-id {
      type uint32;
      description
        "Interface Synchronization ID";
    }
    leaf forward-referenced {
      type boolean;
      description
        "Forward Referenced";
    }
    leaf session-count {
      type uint32;
      description
        "Session Count";
    }
  }

  grouping SRG-SHOW-GROUP-ENTRY {
    description
      "Subscriber Redundancy Group Information";
    container event-history {
      description
        "Event history of group";
      uses EVT-HIST-INFO;
    }
    leaf group-id-xr {
      type uint32;
      description
        "Group ID";
    }
    leaf description {
      type string;
      description
        "Group Description";
    }
    leaf disabled {
      type boolean;
      description
        "Disabled by Config";
    }
    leaf init-role {
      type Srg-show-role;
      description
        "Preferred Init Role";
    }
    leaf negotiating-role {
      type Srg-show-role;
      description
        "Negotiating Role";
    }
    leaf current-role {
      type Srg-show-role;
      description
        "Current Role";
    }
    leaf slave-mode {
      type Srg-show-slave-mode;
      description
        "Slave Mode";
    }
    leaf hold-timer {
      type uint32;
      description
        "Switch Over Hold Time";
    }
    leaf virtual-mac-address {
      type string;
      description
        "Virtual MAC Address";
    }
    leaf virtual-mac-address-disable {
      type boolean;
      description
        "Virtual MAC Address Disable";
    }
    leaf l2tp-source-ip {
      type inet:ipv4-address;
      description
        "L2TP Souce IP Address";
    }
    leaf core-tracking-object-name {
      type string;
      description
        "Core Object Tracking Name";
    }
    leaf core-tracking-object-status {
      type boolean;
      description
        "Core Object Tracking Status";
    }
    leaf access-tracking-object-name {
      type string;
      description
        "Access Object Tracking Name";
    }
    leaf access-tracking-object-status {
      type boolean;
      description
        "Access Object Tracking Status";
    }
    leaf object-tracking-status {
      type boolean;
      description
        "Object Tracking Status (Enabled/Disabled)";
    }
    leaf peer-ipv4-address {
      type inet:ipv4-address;
      description
        "Peer IPv4 Address";
    }
    leaf peer-ipv6-address {
      type inet:ipv6-address;
      description
        "Peer IPv6 Address";
    }
    leaf peer-name {
      type string;
      description
        "Peer name";
    }
    leaf peer-status {
      type Srg-peer-status;
      description
        "Peer Status";
    }
    leaf peer-last-negotiation-time-epoch {
      type uint64;
      units "second";
      description
        "Last Negotiation time of Peer in epoch seconds";
    }
    leaf peer-last-up-time-epoch {
      type uint64;
      units "second";
      description
        "Last UP time of Peer in epoch seconds";
    }
    leaf peer-last-down-time-epoch {
      type uint64;
      units "second";
      description
        "Last Down time of Peer in epoch seconds";
    }
    leaf peer-init-role {
      type Srg-show-role;
      description
        "Peer Preferred Init Role";
    }
    leaf peer-negotiating-role {
      type Srg-show-role;
      description
        "Peer Negotiating Role";
    }
    leaf peer-current-role {
      type Srg-show-role;
      description
        "Peer Current Role";
    }
    leaf peer-object-tracking-status {
      type boolean;
      description
        "Peer Object Tracking Status";
    }
    leaf last-switchover-time-epoch {
      type uint64;
      units "second";
      description
        "Last Switchover time in epoch seconds";
    }
    leaf switchover-count {
      type uint32;
      description
        "Switchover Count";
    }
    leaf last-switchover-reason {
      type Srg-show-so-reason;
      description
        "Last Switchover Reason";
    }
    leaf switchover-hold-time {
      type uint32;
      units "second";
      description
        "Switchover Hold Time in seconds";
    }
    leaf session-count {
      type uint32;
      description
        "Session Count";
    }
    leaf slave-update-failure-count {
      type uint32;
      description
        "Slave Session update fail count";
    }
    leaf tunnel-count {
      type uint32;
      description
        "Tunnel Count";
    }
    leaf pending-session-update-count {
      type uint32;
      description
        "Pending Session Update Count";
    }
    leaf pending-session-delete-count {
      type uint32;
      description
        "Pending Session Delete Count";
    }
    leaf interface-count {
      type uint32;
      description
        "No. of Configured Interfaces";
    }
    leaf revertive-timer {
      type uint32;
      description
        "Revertive timer for SWO back";
    }
    leaf switchover-revert-time {
      type uint32;
      units "second";
      description
        "Switchover Revert Time in seconds";
    }
    leaf last-hitory-index {
      type uint8;
      description
        "Index of last switchover timestamp";
    }
    leaf access-track-cb {
      type boolean;
      description
        "Access track callback status";
    }
    leaf core-track-cb {
      type boolean;
      description
        "Core track callback status";
    }
    list interface {
      description
        "Interface List";
      uses SRG-SHOW-GROUP-INTF-INFO;
    }
    list history-array {
      description
        "Array of switchover history ";
      uses SRG-SHOW-GRP-SWITCHOVER-HISTORY;
    }
    list route-ipv4-array {
      description
        "Array of ipv4 static route";
      uses SRG-SHOW-GROUP-ROUTE-IPV4;
    }
    list route-ipv6-array {
      description
        "Array of ipv6 static route";
      uses SRG-SHOW-GROUP-ROUTE-IPV6;
    }
    list received-stat {
      description
        "Statistics of client message received";
      uses SRG-GROUP-CLIENT-STATS;
    }
    list sent-stat {
      description
        "Statistics of client message sent";
      uses SRG-GROUP-CLIENT-STATS;
    }
  }

  grouping SRG-AGT-SHOW-GROUP-LIST-ENTRY {
    description
      "Subscriber Redundancy Agent Group Summary
       Information";
    leaf group-id-xr {
      type uint32;
      description
        "Group ID";
    }
    leaf role {
      type Srg-show-im-role;
      description
        "SRG Role";
    }
    leaf disabled {
      type boolean;
      description
        "Disabled by Config";
    }
    leaf peer-ipv4-address {
      type inet:ipv4-address;
      description
        "Peer IPv4 Address";
    }
    leaf peer-ipv6-address {
      type inet:ipv6-address;
      description
        "Peer IPv6 Address";
    }
    leaf peer-name {
      type string;
      description
        "Peer name";
    }
    leaf peer-status {
      type Srg-peer-status;
      description
        "Peer Status";
    }
    leaf preferred-role {
      type Srg-show-role;
      description
        "Preferred Role";
    }
    leaf slave-mode {
      type Srg-show-slave-mode;
      description
        "Slave Mode";
    }
    leaf object-tracking-status {
      type boolean;
      description
        "Object Tracking Status (Enabled/Disabled)";
    }
    leaf interface-count {
      type uint32;
      description
        "Interface Count";
    }
    leaf session-count {
      type uint32;
      description
        "Session Count";
    }
    leaf pending-add-session-count {
      type uint32;
      description
        "Pending Session Count for Synchornization";
    }
  }

  grouping BAG-TIMESPEC {
    description
      "Timespec specifying the number of seconds since
       the base time of 00:00:00 GMT, 1 January 1970.";
    leaf seconds {
      type uint32;
      units "second";
      description
        "Number of seconds";
    }
  }

  grouping SRG-SHOW-AGT-INTF-ENTRY-HIST {
    description
      "IDB statistics history";
    container time-updated {
      description
        "Time stamp when the stats was updated";
      uses BAG-TIMESPEC;
    }
    leaf interface-enable-error-count-hist {
      type uint32;
      description
        "Interface Enable Error Count History";
    }
    leaf interface-disable-error-count-hist {
      type uint32;
      description
        "Interface Disable Error Count History";
    }
    leaf interface-caps-add-error-count-hist {
      type uint32;
      description
        "Interface Caps Add Error Count History";
    }
    leaf interface-caps-remove-error-count-hist {
      type uint32;
      description
        "Interface Caps Remove Error Count History";
    }
    leaf interface-attribute-update-error-count-hist {
      type uint32;
      description
        "Interface Attribute Update Error Count History";
    }
    leaf-list client-status-hist {
      type uint8;
      description
        "Interface status history for each client";
    }
    leaf-list client-count-hist {
      type uint32;
      description
        "Session count history per client";
    }
  }

  grouping EVT-HIST-ENTRY {
    description
      "Event history Entry";
    leaf evt-timestamp {
      type string;
      description
        "The timestamp of the event";
    }
    leaf evt-name {
      type string;
      description
        "Event name";
    }
    leaf evt-type {
      type uint8;
      description
        "Event type";
    }
    leaf evt-many {
      type boolean;
      description
        "Multiple instance flag";
    }
    leaf evt-sticky {
      type boolean;
      description
        "Sticky flag";
    }
    leaf-list evt-data {
      type uint32;
      description
        "Optional data";
    }
  }

  grouping EVT-HIST-INFO {
    description
      "Per object event history";
    leaf evt-class-name {
      type string;
      description
        "Class name string";
    }
    list evt-entry {
      description
        "Array of event entries";
      uses EVT-HIST-ENTRY;
    }
  }

  grouping SRG-SHOW-AGT-INTF-CLIENT-STATUS {
    description
      "srg show agt intf client status";
    leaf component {
      type Srg-show-comp;
      description
        "Component";
    }
    leaf srg-show-idb-client-eoms-pending {
      type boolean;
      description
        "SRG SHOW IDB CLIENT EOMS PENDING";
    }
    leaf srg-show-idb-client-sync-eod-pending {
      type boolean;
      description
        "SRG SHOW IDB CLIENT SYNC EOD PENDING";
    }
    leaf session-count {
      type uint32;
      description
        "session count";
    }
  }

  grouping SRG-SHOW-INTF-STATUS {
    description
      "Subscriber Redundancy Interface Status";
    leaf idb-state-fwd-ref {
      type boolean;
      description
        "Interface Forward Referenced";
    }
    leaf idb-state-stale {
      type boolean;
      description
        "Interface State Stale";
    }
    leaf idb-state-registered {
      type boolean;
      description
        "Interface State Registered";
    }
    leaf idb-state-caps-added {
      type boolean;
      description
        "Interface State Caps Added";
    }
    leaf idb-state-owned-re-source {
      type boolean;
      description
        "Interface State Owned Resource";
    }
    leaf idb-client-eoms-pending {
      type boolean;
      description
        "Interface Client EOMS Pending";
    }
    leaf idb-state-p-end-caps-rem {
      type boolean;
      description
        "Interface Caps Remove Pending";
    }
    leaf idb-state-p-end-reg-disable {
      type boolean;
      description
        "Interface Registration Disable Pending";
    }
  }

  grouping SRG-SHOW-INTF-OPER {
    description
      "Subscriber Redundancy Interface Operational
       Status";
    leaf idb-oper-reg-enable {
      type boolean;
      description
        "Operational Registration Enabled";
    }
    leaf idb-oper-reg-disable {
      type boolean;
      description
        "Operational Registration Disabled";
    }
    leaf idb-oper-caps-add {
      type boolean;
      description
        "Operational Caps Add";
    }
    leaf idb-oper-caps-remove {
      type boolean;
      description
        "Operational Caps Remove";
    }
    leaf idb-oper-attr-update {
      type boolean;
      description
        "Operational Attribute Update";
    }
  }

  grouping SRG-SHOW-AGT-INTF-ENTRY {
    description
      "Subscriber Redundancy Agent Interface Information";
    container interface-oper {
      description
        "Interface Batch Operation";
      uses SRG-SHOW-INTF-OPER;
    }
    container interface-status {
      description
        "Interface Status";
      uses SRG-SHOW-INTF-STATUS;
    }
    container event-history {
      description
        "Event history of interface";
      uses EVT-HIST-INFO;
    }
    leaf interface-name {
      type string;
      description
        "Interface Name";
    }
    leaf interface-synchronization-id {
      type uint32;
      description
        "Interface Sync ID";
    }
    leaf group-id {
      type uint32;
      description
        "Group ID";
    }
    leaf role {
      type Srg-show-im-role;
      description
        "SRG Role";
    }
    leaf forward-referenced {
      type boolean;
      description
        "Forward Referenced";
    }
    leaf session-count {
      type uint32;
      description
        "Session Count";
    }
    leaf interface-enable-error-count {
      type uint32;
      description
        "Interface Enable Error Count";
    }
    leaf interface-disable-error-count {
      type uint32;
      description
        "Interface Disable Error Count";
    }
    leaf interface-caps-add-error-count {
      type uint32;
      description
        "Interface Caps Add Error Count";
    }
    leaf interface-caps-remove-error-count {
      type uint32;
      description
        "Interface Caps Remove Error Count";
    }
    leaf interface-attribute-update-error-count {
      type uint32;
      description
        "Interface Attribute Update Error Count";
    }
    list client-status {
      description
        "Interface status for each client";
      uses SRG-SHOW-AGT-INTF-CLIENT-STATUS;
    }
    list history {
      description
        "IDB statistics history";
      uses SRG-SHOW-AGT-INTF-ENTRY-HIST;
    }
  }

  grouping SRG-SHOW-SESSION-ERROR-INFO {
    description
      "Subscriber Redundancy Session Verbose Client
       Error Information";
    leaf sync-error-count {
      type uint16;
      description
        "No. of Errors occured during Synchronization";
    }
    leaf last-error-code {
      type uint32;
      description
        "Last Error Code";
    }
    leaf last-error-type {
      type Srg-show-session-error;
      description
        "Last Error Type";
    }
    leaf last-error-comp {
      type uint32;
      description
        "Last Error Component";
    }
  }

  grouping SRG-SHOW-SESSION-CLIENT {
    description
      "Subscriber Redundancy Session Verbose Client
       Information";
    leaf component {
      type Srg-show-comp;
      description
        "Component";
    }
    leaf operation {
      type Srg-show-session-operation;
      description
        "Operation Code";
    }
    leaf tx-list-queue-fail {
      type boolean;
      description
        "Tx List Queue Failed";
    }
    leaf marked-for-sweeping {
      type boolean;
      description
        "Marked For Sweeping";
    }
    leaf marked-for-cleanup {
      type boolean;
      description
        "Marked For Cleanup";
    }
  }

  grouping SRG-SHOW-SESSION-ENTRY {
    description
      "Subscriber Redundancy Session Information";
    leaf group-id-xr {
      type uint32;
      description
        "Group ID";
    }
    leaf interface-name {
      type string;
      description
        "Interface Name";
    }
    leaf outer-vlan {
      type uint32;
      description
        "Outer VLAN Information";
    }
    leaf inner-vlan {
      type uint32;
      description
        "Inner VLAN Information";
    }
    leaf session-mac-address {
      type string;
      description
        "Session MAC Address";
    }
    leaf pppoe-session-id {
      type uint16;
      description
        "PPPoE Session ID";
    }
    leaf l2tp-tunnel-id {
      type uint32;
      description
        "L2TP Tunnel local ID";
    }
    leaf role-master {
      type boolean;
      description
        "Master Role is Set";
    }
    leaf valid-mac-address {
      type boolean;
      description
        "Holds a Valid MAC Address";
    }
    leaf negative-acknowledgement-update-all {
      type boolean;
      description
        "Negative Acknowledgement Update Flag is Set";
    }
    leaf sir-state {
      type boolean;
      description
        "Subscriber Infra State";
    }
    list session-detailed-information {
      description
        "More Session Information";
      uses SRG-SHOW-SESSION-CLIENT;
    }
    list session-sync-error-information {
      description
        "Session Synchroniation Error Information";
      uses SRG-SHOW-SESSION-ERROR-INFO;
    }
  }

  grouping SRG-SHOW-AGT-PEER-ENTRY {
    description
      "Subscriber Redundancy Agent Peer Summary
       Information";
    leaf name {
      type string;
      description
        "Object Name";
    }
    leaf peer-ipv4-address {
      type inet:ipv4-address;
      description
        "Peer IPv4 Address";
    }
    leaf peer-ipv6-address {
      type inet:ipv6-address;
      description
        "Peer IPv6 Address";
    }
    leaf tcp-port {
      type uint32;
      description
        "TCP port";
    }
    leaf peer-status {
      type Srg-peer-status;
      description
        "Peer Status";
    }
  }

  grouping SRG-SHOW-MGR-INTF-ENTRY {
    description
      "Subscriber Redundancy Manager Interface
       Information";
    leaf interface-name {
      type string;
      description
        "Interface Name";
    }
    leaf interface-mapping-id {
      type uint32;
      description
        "Interface Mapping ID";
    }
    leaf forward-referenced {
      type boolean;
      description
        "Forward Referenced";
    }
    leaf group-id {
      type uint32;
      description
        "Group ID";
    }
    leaf role {
      type Srg-show-im-role;
      description
        "SRG Role";
    }
  }

  grouping SRG-SHOW-MGR-SUMMARY {
    description
      "Subscriber Redundancy Manager Summary Information";
    leaf disabled {
      type boolean;
      description
        "Disabled by Config";
    }
    leaf active-state {
      type boolean;
      description
        "Process Active State";
    }
    leaf preferred-role {
      type Srg-show-role;
      description
        "Preferred Role";
    }
    leaf slave-mode {
      type Srg-show-slave-mode;
      description
        "Slave Mode";
    }
    leaf hold-timer {
      type uint32;
      description
        "Switch Over Hold Time";
    }
    leaf sync-time {
      type uint32;
      description
        "Sync Time";
    }
    leaf source-interface-name {
      type string;
      description
        "Source Interface Name";
    }
    leaf vrf-name {
      type string;
      description
        "VRF Name";
    }
    leaf source-interface-ipv4-address {
      type inet:ipv4-address;
      description
        "Source Interface IPv4 Address";
    }
    leaf source-interface-ipv6-address {
      type inet:ipv6-address;
      description
        "Source Interface IPv6 Address";
    }
    leaf group-count {
      type uint32;
      description
        "No. of Configured Groups";
    }
    leaf disabled-group-count {
      type uint32;
      description
        "No. of Disabled Groups by Config";
    }
    leaf master-group-count {
      type uint32;
      description
        "No. of Master/Active Groups";
    }
    leaf slave-group-count {
      type uint32;
      description
        "No. of Slave Groups";
    }
    leaf interface-count {
      type uint32;
      description
        "No. of Configured Interfaces";
    }
    leaf master-interface-count {
      type uint32;
      description
        "No. of Master/Active Interfaces";
    }
    leaf slave-interface-count {
      type uint32;
      description
        "No. of Slave Interfaces";
    }
  }

  grouping SRG-SHOW-MGR-GROUP-ENTRY {
    description
      "Subscriber Redundancy Manager Group Information";
    leaf group-id {
      type uint32;
      description
        "Group ID";
    }
    leaf description {
      type string;
      description
        "Group Description";
    }
    leaf disabled {
      type boolean;
      description
        "Disabled by Config";
    }
    leaf role {
      type Srg-show-im-role;
      description
        "SRG Role";
    }
    leaf peer-ipv4-address {
      type inet:ipv4-address;
      description
        "Peer IPv4 Address";
    }
    leaf peer-ipv6-address {
      type inet:ipv6-address;
      description
        "Peer IPv6 Address";
    }
    leaf interface-count {
      type uint32;
      description
        "Interface Count";
    }
    leaf preferred-role {
      type Srg-show-role;
      description
        "Preferred Role";
    }
    leaf slave-mode {
      type Srg-show-slave-mode;
      description
        "Slave Mode";
    }
    leaf object-tracking-status {
      type boolean;
      description
        "Object Tracking Status (Enabled/Disabled)";
    }
    leaf virtual-mac-address {
      type string;
      description
        "Virtual MAC Address";
    }
    leaf virtual-mac-address-disable {
      type boolean;
      description
        "Virtual MAC Address Disable";
    }
    leaf node-name {
      type string;
      description
        "Node Information";
    }
  }
}
