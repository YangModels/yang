module Cisco-IOS-XR-asr9k-apm-src-flexr-cfg {
  namespace "http://cisco.com/ns/yang/Cisco-IOS-XR-asr9k-apm-src-flexr-cfg";
  prefix asr9k-apm-src-flexr-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR asr9k-apm-src-flexr package configuration.
     
     This module contains definitions
     for the following management objects:
       hw-module-slice-config: Advanced power management
     
     Copyright (c) 2013-2021 by Cisco Systems, Inc.
     All rights reserved.";

  revision 2021-03-01 {
    description
      "IOS XR 7.4.1 revision.";
    semver:module-version "1.0.0";
  }
  revision 2019-04-05 {
    description
      "Establish semantic version baseline.";
  }
  revision 2015-11-09 {
    description
      "IOS XR 6.0 revision.";
  }

  typedef Slice-power-management-mode {
    type enumeration {
      enum "power-savings" {
        value 1;
        description
          "Shutdown the slice";
      }
      enum "power-down" {
        value 2;
        description
          "Power down the slice";
      }
    }
    description
      "Slice power management mode";
  }

  container hw-module-slice-config {
    description
      "Advanced power management";
    container apm {
      description
        "Advanced power management";
      container nodes {
        description
          "line-card node location";
        list node {
          key "node-name";
          description
            "line-card node location";
          container slices {
            description
              "Slice Table";
            list slice {
              key "slice-number";
              description
                "Slice";
              leaf power-management-mode {
                type Slice-power-management-mode;
                description
                  "Slice power management mode";
              }
              leaf slice-number {
                type uint32 {
                  range "0..9";
                }
                description
                  "Slice number";
              }
            }
          }
          leaf node-name {
            type xr:Node-id;
            description
              "Fully qualified line card specification";
          }
        }
      }
    }
  }
}
