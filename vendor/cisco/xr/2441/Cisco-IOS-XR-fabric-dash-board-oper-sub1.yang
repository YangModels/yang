submodule Cisco-IOS-XR-fabric-dash-board-oper-sub1 {
  belongs-to Cisco-IOS-XR-fabric-dash-board-oper {
    prefix Cisco-IOS-XR-fabric-dash-board-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR fabric-dash-board package operational data.
     
     Copyright (c) 2013-2024 by Cisco Systems, Inc.
     All rights reserved.";

  revision 2024-07-10 {
    description
      "Yang Schema for fabric dash-board";
    semver:module-version "1.0.0";
  }
  revision 2019-04-05 {
    description
      "Establish semantic version baseline.";
  }
  revision 2015-11-09 {
    description
      "IOS XR 6.0 revision.";
  }

  grouping NPU-EDM-FD-ASIC-LINK {
    description
      "NPU EDM FD ASIC LINK";
    leaf fab-port {
      type string {
        length "0..16";
      }
      description
        "Fabric Port - R/S/A/L";
    }
    leaf far-end-port {
      type string {
        length "0..16";
      }
      description
        "Far end fabric port - R/S/A/L";
    }
    leaf oper-state {
      type string {
        length "0..4";
      }
      description
        "Port oper state UP/DN/NA";
    }
    leaf fsm-state {
      type string {
        length "0..17";
      }
      description
        "FSM state of fabric port";
    }
    leaf flap-count {
      type uint16;
      description
        "fabric port flap count";
    }
    leaf high-ber {
      type boolean;
      description
        "Is High BER";
    }
    leaf nz-cw-bin-len {
      type uint8;
      description
        "Non Zero FEC Codeword Bin length";
    }
    leaf uce {
      type uint64;
      description
        "UnCorrectable Error";
    }
    leaf crc {
      type uint64;
      description
        "CRC Error";
    }
    leaf is-snr-valid {
      type boolean;
      description
        "Is SNR Valid";
    }
    leaf snr {
      type uint8;
      description
        "Poorest SNR among all serdes";
    }
    leaf ex-pol-ber {
      type string {
        length "0..16";
      }
      description
        "FEC Extrapolated BER";
    }
    leaf comment {
      type string {
        length "0..32";
      }
      description
        "comment on the fabric port";
    }
  }

  grouping NPU-EDM-FD-ASIC-CAPACITY {
    description
      "NPU EDM FD ASIC CAPACITY";
    leaf asic-name {
      type string;
      description
        "Asic name R/S/A";
    }
    leaf network-bw {
      type uint32;
      units "Gbit/s";
      description
        "Network BW (Gbps) - combined front panel BW";
    }
    leaf req-fabric-bw {
      type uint32;
      units "Gbit/s";
      description
        "Required Fabric BW (Gbps)";
    }
    leaf avail-fabric-bw {
      type uint32;
      units "Gbit/s";
      description
        "Available Fabric BW (Gbps)";
    }
    leaf req-capacity {
      type uint32;
      description
        "Max required(by user) capacity in %";
    }
    leaf avail-capacity {
      type uint32;
      description
        "Available capacity in %";
    }
    leaf is-over-subs {
      type boolean;
      description
        "Is Oversubscribed Y/N";
    }
  }

  grouping NPU-EDM-FD-ASIC-INFO {
    description
      "NPU EDM FD ASIC INFO";
    leaf node-name {
      type string;
      description
        "Node name";
    }
    leaf card-pid {
      type string;
      description
        "Card PID";
    }
    leaf card-sn {
      type string;
      description
        "Card Serial Number";
    }
    leaf npu-fe-inst {
      type string;
      description
        "NPU or FE instance";
    }
    leaf asic-type {
      type string;
      description
        "Asic type";
    }
  }

  grouping NPU-EDM-FABRIC-DATAPATH-INFO {
    description
      "NPU EDM FABRIC DATAPATH INFO";
    leaf cache-time-valid {
      type boolean;
      description
        "Cache time is valid";
    }
    leaf cache-time {
      type uint64;
      description
        "Port state caching time";
    }
    list asic-info {
      description
        "Asic's Type, Card PID, SN..";
      uses NPU-EDM-FD-ASIC-INFO;
    }
    list asic-capacity {
      description
        "Asic's Fabric Capacity";
      uses NPU-EDM-FD-ASIC-CAPACITY;
    }
    list asic-link {
      description
        "Asic's links status/info";
      uses NPU-EDM-FD-ASIC-LINK;
    }
  }
}
