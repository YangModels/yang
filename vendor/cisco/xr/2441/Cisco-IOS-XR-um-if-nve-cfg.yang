module Cisco-IOS-XR-um-if-nve-cfg {
  namespace "http://cisco.com/ns/yang/Cisco-IOS-XR-um-if-nve-cfg";
  prefix um-if-nve-cfg;

  import Cisco-IOS-XR-types {
    prefix xr;
  }
  import ietf-inet-types {
    prefix inet;
  }
  import Cisco-IOS-XR-um-interface-cfg {
    prefix a1;
  }
  import tailf-common {
    prefix tailf;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR if-nve package configuration.
     
     This YANG module augments the
     modules with configuration data.
     
     Copyright (c) 2021-2024 by Cisco Systems, Inc.
     All rights reserved.";

  revision 2024-01-30 {
    description
      "Remove source-port-msb. Add src-port start
       2023-09-02
         Fix source-port-msb help.
       2023-08-16
         Updated source-port-msb help.
       2023-08-14
         removed must end-address from start-address
       2023-08-03
         Updated source-port-msb accepted range and help.
       2023-04-10
         Updated cli help and path.
       2023-03-10
         Removed disable-source-ip-lookup subcommand under
       overlay-encapsulation vxlan. Added peer-ip lookup disable subcommand under
       overlay-encapsulation vxlan
       2023-02-06
         Added support for global policer-rate configuration.
       2023-01-19
         Removed container nve's udp-port source range. Added leaf source-port-msb.
       2022-11-29
         Added disable-source-ip-lookup subcommand under
       overlay-encapsulation vxlan
       2022-11-28
         Added host-reachability protocol static
       2022-11-18
         Added overlay-encapsulation support under container nve
       2022-07-11
         Added missing description statement to nodes
       2022-03-15
         1.Added mpls-udp support under overlay-encapsulation
       2.Added container nve support";
    semver:module-version "1.1.0";
  }
  revision 2021-06-29 {
    description
      "Initial release";
    semver:module-version "1.0.0";
  }

  grouping IF-BODY {
    description
      "Grouping for interface";
    leaf source-interface {
      type xr:Interface-name;
      description
        "Configure source interface for Network Virtualization Endpoint";
    }
    container anycast {
      description
        "Configure anycast mode parameters for this VTEP";
      leaf source-interface {
        type xr:Interface-name;
        description
          "Configure source interface for the anycast mode";
      }
      leaf sync-group {
        type inet:ipv4-address-no-zone;
        must "../source-interface";
        description
          "Assign a BiDir multicast group for sync between anycast gateways";
      }
    }
    container member {
      description
        "Configure NVE member(s)";
      container vni {
        description
          "Configure member VxLAN Network Identfier";
        list vni-range {
          key "vni-start vni-end";
          description
            "Start of VNI range";
          leaf vni-start {
            type uint32 {
              range "1..16777215" {
                description
                  "Start of VNI range";
              }
            }
            description
              "Start of VNI range";
          }
          leaf vni-end {
            type uint32 {
              range "1..16777215" {
                description
                  "End of VNI range";
              }
            }
            description
              "End of VNI range";
          }
          container mcast-group {
            description
              "associate a multicast core group with VxLAN segment(s)";
            leaf start-address {
              type inet:ipv4-address-no-zone;
              description
                "Start of mcast IP range";
            }
            leaf end-address {
              type inet:ipv4-address-no-zone;
              must "../start-address";
              description
                "End of mcast IP range";
            }
          }
          leaf vrf {
            type xr:Cisco-ios-xr-string {
              length "1..800" {
                description
                  "VRF name";
              }
            }
            description
              "Associate a VRF with VxLAN segment";
          }
          container host-reachability {
            description
              "Configure the control protocol for VxLAN tunnel endpoint reachability";
            container protocol {
              description
                "Configure the control protocol for VxLAN tunnel endpoint reachability";
              container bgp {
                presence "Indicates a bgp node is configured.";
                description
                  "Use BGP EVPN for VxLAN tunnel endpoint reachability";
              }
              container static {
                presence "Indicates a static node is configured.";
                description
                  "Use static VxLAN tunnel endpoint reachability";
              }
            }
          }
          container suppress-unknown-unicast-flooding {
            presence "Indicates a suppress-unknown-unicast-flooding node is configured.";
            description
              "Configure the suppression of unknown unicast flooding";
          }
          container load-balance {
            description
              "Configure load balance mode";
            container per-evi {
              presence "Indicates a per-evi node is configured.";
              description
                "Configure per-evi load balance mode (default is per-flow)";
            }
          }
        }
      }
    }
    container overlay-encapsulation {
      description
        "Configure encapsulation for Network Virtualization Endpoint";
      container soft-gre {
        must "not(../vxlan)";
        presence "Indicates a soft-gre node is configured.";
        description
          "Configure Soft GRE encapsulation for Network Virtualization Endpoint";
      }
      container mpls-udp {
        presence "Indicates a mpls-udp node is configured.";
        description
          "Configure mpls-udp encapsulation for Network Virtualization Endpoint";
      }
      container vxlan {
        must "not(../soft-gre)";
        presence "Indicates a vxlan node is configured.";
        description
          "Configure VxLAN encapsulation for Network Virtualization Endpoint";
        container peer-ip {
          description
            "Configure options for peer-ip";
          container lookup {
            description
              "Lookup options of peer-ip from packet header";
            container disable {
              presence "Indicates a disable node is configured.";
              description
                "Disable lookup of peer-ip to accept packets from unknown peers";
            }
          }
        }
      }
    }
    container vxlan-udp-port {
      description
        "Configure UDP port number in VxLAN encapsulation";
      container port-4789 {
        must "not(../port-48879)";
        presence "Indicates a port-4789 node is configured.";
        description
          "IETF defined UDP port number for VxLAN";
      }
      container port-48879 {
        must "not(../port-4789)";
        presence "Indicates a port-48879 node is configured.";
        description
          "UDP port number for iVxLAN";
      }
    }
    container redundancy {
      presence "Indicates a redundancy node is configured.";
      description
        "Redundancy";
      container backbone {
        description
          "Configure ICCP backbone";
        container vxlan {
          presence "Indicates a vxlan node is configured.";
          description
            "ICCP VXLAN backbone";
          container iccp {
            description
              "Inter-Chassis Communication Protocol";
            leaf group {
              type uint32 {
                range "1..4294967295" {
                  description
                    "Enter group number";
                }
              }
              description
                "Configure ICCP group number";
            }
          }
        }
        container mpls {
          presence "Indicates a mpls node is configured.";
          description
            "ICCP MPLS backbone";
          container iccp {
            description
              "Inter-Chassis Communication Protocol";
            leaf group {
              type uint32 {
                range "1..4294967295" {
                  description
                    "Enter group number";
                }
              }
              description
                "Configure ICCP group number";
            }
          }
        }
      }
    }
    container ingress-replication {
      description
        "Configure ingress replication for VxLAN tunnel endpoint";
      container protocol {
        description
          "Configure the control protocol for VxLAN tunnel endpoint ingress replication";
        container bgp {
          presence "Indicates a bgp node is configured.";
          description
            "Use BGP EVPN for VxLAN tunnel endpoint ingress replication";
        }
      }
    }
  }

  augment "/a1:interfaces/a1:interface" {
    when "a1:interface-name[starts-with(text(),'nve')]" {
      tailf:dependency "a1:interface-name";
    }
    description
      "This augment extends active nodes configuration";
    uses IF-BODY;
  }
  augment "/a1:interfaces/a1:interface-preconfigure" {
    when "a1:interface-name[starts-with(text(),'nve')]" {
      tailf:dependency "a1:interface-name";
    }
    description
      "This augment extends preconfigured nodes
       configuration";
    uses IF-BODY;
  }
  container nve {
    presence "Indicates a nve node is configured.";
    description
      "Global nve related configuration";
    container decap-prefix {
      description
        "Prefix Decapsulation";
      container source {
        description
          "Source interface";
        leaf ipv4 {
          type xr:Cisco-ios-xr-string {
            length "1..64" {
              description
                "IPv4 Decap prefix name with maximum 64 characters";
            }
            pattern "[a-z0-9A-Z][-_.:a-z0-9A-Z]*";
          }
          description
            "IPv4";
        }
        leaf object-group {
          type xr:Cisco-ios-xr-string {
            length "1..64" {
              description
                "IPv4 object group name - maximum 64 characters";
            }
            pattern "[a-z0-9A-Z][-_.:a-z0-9A-Z]*";
          }
          description
            "Configure source object-group";
        }
      }
    }
    container overlay-encap {
      description
        "Configure Global Overlay Encapsulation parameters";
      container vxlan {
        presence "Indicates a vxlan node is configured.";
        description
          "Configure Global VxLAN Parameters";
        container udp-port {
          description
            "Configure UDP Port";
          container src-port {
            description
              "Source UDP Port";
            leaf start {
              type uint32 {
                range "1024..65408" {
                  description
                    "Enter udp source port range start value";
                }
              }
              description
                "UDP source port range start";
            }
          }
          leaf destination {
            type uint32 {
              range "0..65535" {
                description
                  "Enter Port Number";
              }
            }
            description
              "Destination UDP Port";
          }
        }
        container vrfs {
          description
            "Configure VRF specific parameters";
          list vrf {
            key "vrf-name";
            description
              "Configure VRF specific parameters";
            leaf vrf-name {
              type xr:Cisco-ios-xr-string {
                length "1..800" {
                  description
                    "VRF name";
                }
              }
              description
                "Configure VRF specific parameters";
            }
            leaf policer-rate {
              type uint32 {
                range "1..4294967295" {
                  description
                    "Specify the rate limiting policer";
                }
              }
              must "../policer-rate-units";
              description
                "Configure a policer";
            }
            leaf policer-rate-units {
              type enumeration {
                enum "bps" {
                  value 1;
                  description
                    "Rate entered in bytes per second [default]";
                }
                enum "kbps" {
                  value 2;
                  description
                    "Rate entered in kilobytes per second";
                }
                enum "mbps" {
                  value 3;
                  description
                    "Rate entered in megabytes per second";
                }
              }
              must "../policer-rate";
              description
                "configure this node";
            }
          }
        }
      }
    }
  }
}
