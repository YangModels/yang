module Cisco-IOS-XR-um-router-rib-cfg {
  namespace "http://cisco.com/ns/yang/Cisco-IOS-XR-um-router-rib-cfg";
  prefix um-router-rib-cfg;

  import cisco-semver {
    prefix semver;
  }
  import Cisco-IOS-XR-types {
    prefix xr;
  }
  import Cisco-IOS-XR-um-vrf-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR router-rib package configuration.
     
     This YANG module augments the
     modules with configuration data.
     
     Copyright (c) 2019, 2022, 2024 by Cisco Systems, Inc.
     All rights reserved.";

  revision 2024-06-20 {
    description
      "Added tag-map container corresponding to CLI router rib tag-map tag
       2024-03-06
         Removed deprecated instrument-set container and added containers for ip-only and preserve-label-forwarding configs
       2022-07-11
         Added missing description statement to nodes";
    semver:module-version "2.0.0";
  }
  revision 2021-03-10 {
    description
      "Added container rump under container address-famility/ipv4 and ipv6.";
    semver:module-version "1.1.0";
  }
  revision 2019-06-10 {
    description
      "Establish semantic version baseline.";
    semver:module-version "1.0.1";
  }
  revision 2019-03-30 {
    description
      "Initial version";
  }

  augment "/a1:address-family/a1:ipv4/a1:unicast" {
    description
      "This augment extends vrf ipv4 unicast nodes
       configuration";
    container maximum {
      description
        "Set maximum prefix limit";
      container prefix {
        presence "Indicates a prefix node is configured.";
        description
          "Set table's maximum prefix limit";
        leaf prefix-limit {
          type uint32 {
            range "32..10000000" {
              description
                "Maximum table's prefix limit";
            }
          }
          mandatory true;
          description
            "Set table's maximum prefix limit";
        }
        leaf mid-thresh {
          type uint32 {
            range "1..100" {
              description
                "mid-thresh (% of max)";
            }
          }
          description
            "mid-thresh (% of max)";
        }
      }
    }
  }
  augment "/a1:address-family/a1:ipv4/a1:multicast/a1:topologies/a1:topology" {
    description
      "This augment extends vrf ipv4 multicast topology nodes
       configuration";
    container maximum {
      description
        "Set maximum prefix limit";
      container prefix {
        presence "Indicates a prefix node is configured.";
        description
          "Set table's maximum prefix limit";
        leaf prefix-limit {
          type uint32 {
            range "32..10000000" {
              description
                "Maximum table's prefix limit";
            }
          }
          mandatory true;
          description
            "Set table's maximum prefix limit";
        }
        leaf mid-thresh {
          type uint32 {
            range "1..100" {
              description
                "mid-thresh (% of max)";
            }
          }
          description
            "mid-thresh (% of max)";
        }
      }
    }
  }
  augment "/a1:address-family/a1:ipv6/a1:unicast" {
    description
      "This augment extends vrf ipv6 unicast nodes
       configuration";
    container maximum {
      description
        "Set maximum prefix limit";
      container prefix {
        presence "Indicates a prefix node is configured.";
        description
          "Set table's maximum prefix limit";
        leaf prefix-limit {
          type uint32 {
            range "32..10000000" {
              description
                "Maximum table's prefix limit";
            }
          }
          mandatory true;
          description
            "Set table's maximum prefix limit";
        }
        leaf mid-thresh {
          type uint32 {
            range "1..100" {
              description
                "mid-thresh (% of max)";
            }
          }
          description
            "mid-thresh (% of max)";
        }
      }
    }
  }
  augment "/a1:address-family/a1:ipv6/a1:multicast/a1:topologies/a1:topology" {
    description
      "This augment extends vrf ipv6 multicast topology nodes
       configuration";
    container maximum {
      description
        "Set maximum prefix limit";
      container prefix {
        presence "Indicates a prefix node is configured.";
        description
          "Set table's maximum prefix limit";
        leaf prefix-limit {
          type uint32 {
            range "32..10000000" {
              description
                "Maximum table's prefix limit";
            }
          }
          mandatory true;
          description
            "Set table's maximum prefix limit";
        }
        leaf mid-thresh {
          type uint32 {
            range "1..100" {
              description
                "mid-thresh (% of max)";
            }
          }
          description
            "mid-thresh (% of max)";
        }
      }
    }
  }
  augment "/a1:vrfs/a1:vrf/a1:address-family/a1:ipv4/a1:unicast" {
    description
      "This augment extends vrf ipv4 unicast nodes
       configuration";
    container maximum {
      description
        "Set maximum prefix limit";
      container prefix {
        presence "Indicates a prefix node is configured.";
        description
          "Set table's maximum prefix limit";
        leaf prefix-limit {
          type uint32 {
            range "32..10000000" {
              description
                "Maximum table's prefix limit";
            }
          }
          mandatory true;
          description
            "Set table's maximum prefix limit";
        }
        leaf mid-thresh {
          type uint32 {
            range "1..100" {
              description
                "mid-thresh (% of max)";
            }
          }
          description
            "mid-thresh (% of max)";
        }
      }
    }
  }
  augment "/a1:vrfs/a1:vrf/a1:address-family/a1:ipv4/a1:multicast" {
    description
      "This augment extends vrf ipv4 multicast nodes
       configuration";
    container maximum {
      description
        "Set maximum prefix limit";
      container prefix {
        presence "Indicates a prefix node is configured.";
        description
          "Set table's maximum prefix limit";
        leaf prefix-limit {
          type uint32 {
            range "32..10000000" {
              description
                "Maximum table's prefix limit";
            }
          }
          mandatory true;
          description
            "Set table's maximum prefix limit";
        }
        leaf mid-thresh {
          type uint32 {
            range "1..100" {
              description
                "mid-thresh (% of max)";
            }
          }
          description
            "mid-thresh (% of max)";
        }
      }
    }
  }
  augment "/a1:vrfs/a1:vrf/a1:address-family/a1:ipv6/a1:unicast" {
    description
      "This augment extends vrf ipv6 unicast nodes
       configuration";
    container maximum {
      description
        "Set maximum prefix limit";
      container prefix {
        presence "Indicates a prefix node is configured.";
        description
          "Set table's maximum prefix limit";
        leaf prefix-limit {
          type uint32 {
            range "32..10000000" {
              description
                "Maximum table's prefix limit";
            }
          }
          mandatory true;
          description
            "Set table's maximum prefix limit";
        }
        leaf mid-thresh {
          type uint32 {
            range "1..100" {
              description
                "mid-thresh (% of max)";
            }
          }
          description
            "mid-thresh (% of max)";
        }
      }
    }
  }
  augment "/a1:vrfs/a1:vrf/a1:address-family/a1:ipv6/a1:multicast" {
    description
      "This augment extends vrf ipv6 multicast nodes
       configuration";
    container maximum {
      description
        "Set maximum prefix limit";
      container prefix {
        presence "Indicates a prefix node is configured.";
        description
          "Set table's maximum prefix limit";
        leaf prefix-limit {
          type uint32 {
            range "32..10000000" {
              description
                "Maximum table's prefix limit";
            }
          }
          mandatory true;
          description
            "Set table's maximum prefix limit";
        }
        leaf mid-thresh {
          type uint32 {
            range "1..100" {
              description
                "mid-thresh (% of max)";
            }
          }
          description
            "mid-thresh (% of max)";
        }
      }
    }
  }
  container router {
    description
      "Enable a routing process";
    container rib {
      description
        "RIB configuration subcommands";
      container address-family {
        description
          "RIB address family configuration subcommands";
        container ipv4 {
          description
            "IPv4 commands";
          container next-hop {
            description
              "Set next-hop configuration";
            container dampening {
              description
                "Set next-hop dampening";
              container disable {
                presence "Indicates a disable node is configured.";
                description
                  "Disable next-hop dampening";
              }
            }
          }
          container segment-routing {
            description
              "Configure segment-routing parameters";
            container mpls {
              description
                "Configure SR-MPLS parameters";
              container preserve-label-forwarding {
                presence "Indicates a preserve-label-forwarding node is configured.";
                description
                  "Maintain SR label forwarding entry in FIB even if another source is preferred for the prefix";
                leaf access-list {
                  type xr:Cisco-ios-xr-string {
                    length "1..64" {
                      description
                        "ACL name";
                    }
                    pattern "[a-z0-9A-Z][-_.:a-z0-9A-Z]*";
                  }
                  description
                    "Access-list to limit the behavior to set of prefixes";
                }
                container apply-inverse {
                  must "../access-list";
                  presence "Indicates an apply-inverse node is configured.";
                  description
                    "Apply ACL inversely (permit becomes deny and vice versa)";
                }
              }
            }
          }
          container redistribution-history {
            description
              "Redistribution history related commands.";
            container size {
              description
                "Number of routes to store in history.";
              leaf bcdl {
                type uint32 {
                  range "10..2000000" {
                    description
                      "Maximum BCDL redistribution history size.";
                  }
                }
                description
                  "BCDL clients only";
              }
              leaf protocols {
                type uint32 {
                  range "10..250000" {
                    description
                      "Maximum protocol redistribution history size.";
                  }
                }
                description
                  "Protocol clients only";
              }
            }
            container keep {
              description
                "Retain redistribution history after disconnect.";
              container bcdl {
                presence "Indicates a bcdl node is configured.";
                description
                  "Retain BCDL history.";
              }
            }
          }
          container rump {
            description
              "RUMP related commands.";
            leaf always-replicate {
              type string {
                length "0..800" {
                  description
                    "Access list";
                }
              }
              description
                "Replicate routes from uRIB to muRIB always.";
            }
          }
        }
        container ipv6 {
          description
            "IPv6 commands";
          container next-hop {
            description
              "Set next-hop configuration";
            container dampening {
              description
                "Set next-hop dampening";
              container disable {
                presence "Indicates a disable node is configured.";
                description
                  "Disable next-hop dampening";
              }
            }
          }
          container segment-routing {
            description
              "Configure segment-routing parameters";
            container mpls {
              description
                "Configure SR-MPLS parameters";
              container preserve-label-forwarding {
                presence "Indicates a preserve-label-forwarding node is configured.";
                description
                  "Maintain SR label forwarding entry in FIB even if another source is preferred for the prefix";
                leaf access-list {
                  type xr:Cisco-ios-xr-string {
                    length "1..64" {
                      description
                        "ACL name";
                    }
                    pattern "[a-z0-9A-Z][-_.:a-z0-9A-Z]*";
                  }
                  description
                    "Access-list to limit the behavior to set of prefixes";
                }
                container apply-inverse {
                  must "../access-list";
                  presence "Indicates an apply-inverse node is configured.";
                  description
                    "Apply ACL inversely (permit becomes deny and vice versa)";
                }
              }
            }
          }
          container redistribution-history {
            description
              "Redistribution history related commands.";
            container size {
              description
                "Number of routes to store in history.";
              leaf bcdl {
                type uint32 {
                  range "10..2000000" {
                    description
                      "Maximum BCDL redistribution history size.";
                  }
                }
                description
                  "BCDL clients only";
              }
              leaf protocols {
                type uint32 {
                  range "10..250000" {
                    description
                      "Maximum protocol redistribution history size.";
                  }
                }
                description
                  "Protocol clients only";
              }
            }
            container keep {
              description
                "Retain redistribution history after disconnect.";
              container bcdl {
                presence "Indicates a bcdl node is configured.";
                description
                  "Retain BCDL history.";
              }
            }
          }
          container rump {
            description
              "RUMP related commands.";
            leaf always-replicate {
              type string {
                length "0..800" {
                  description
                    "Access list";
                }
              }
              description
                "Replicate routes from uRIB to muRIB always.";
            }
          }
        }
      }
      leaf recursion-depth-max {
        type uint32 {
          range "5..16" {
            description
              "Maximum depth for route recursion check.";
          }
        }
        description
          "Set maximum depth for route recursion check.";
      }
      container table {
        description
          "Configure RIB special routing-table parameters";
        container ip-only {
          description
            "Table of routes with IP-only nexthop(s)";
          container activate {
            presence "Indicates an activate node is configured.";
            description
              "Enable and activate the table";
            leaf vrf {
              type xr:Cisco-ios-xr-string {
                length "1..32" {
                  description
                    "IP-only vrf name";
                }
              }
              description
                "Specify ip-only vrf";
            }
          }
        }
      }
      container tag-map {
        description
          "Configure tag-mapping for RIB VRF default IPv4 and IPv6 Unicast tables";
        container tags {
          description
            "Set the tag value of routes for which to map";
          list tag {
            key "tag-id";
            description
              "Set the tag value of routes for which to map";
            leaf tag-id {
              type uint32 {
                range "1..4294967295" {
                  description
                    "The tag value to map";
                }
              }
              description
                "Set the tag value of routes for which to map";
            }
            container map {
              description
                "Set the flag value of route for which to map";
              leaf forwarding-hierarchy {
                type enumeration {
                  enum "level-2-used-as-nexthop" {
                    value 1;
                    description
                      "Set routes with matching tag to this flag";
                  }
                }
                description
                  "Set the flag value of route for which to map";
              }
            }
          }
        }
      }
    }
  }
}
