module Cisco-IOS-XR-Ethernet-SPAN-cfg {
  namespace "http://cisco.com/ns/yang/Cisco-IOS-XR-Ethernet-SPAN-cfg";
  prefix ethernet-span-cfg;

  import ietf-inet-types {
    prefix inet;
  }
  import Cisco-IOS-XR-types {
    prefix xr;
  }
  import cisco-semver {
    prefix semver;
  }
  import Cisco-IOS-XR-Ethernet-SPAN-datatypes {
    prefix dt1;
  }
  import Cisco-IOS-XR-ifmgr-cfg {
    prefix a1;
  }
  import Cisco-IOS-XR-l2vpn-cfg {
    prefix a2;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR Ethernet-SPAN package configuration.
     
     This module contains definitions
     for the following management objects:
       span-monitor-session: none
     
     This YANG module augments the
       Cisco-IOS-XR-ifmgr-cfg,
       Cisco-IOS-XR-l2vpn-cfg
     modules with configuration data.
     
     Copyright (c) 2013-2024 by Cisco Systems, Inc.
     All rights reserved.";

  revision 2024-07-23 {
    description
      "Increasing acl name length to 128 chars
       2024-06-26
         Add filter string support for drops config
       2024-06-12
         Change periodic write interval permitted range
       2024-04-12
         Mark tm-drop and forward-drop as deprecated
       2024-03-01
         Remove unique-port and unique-punt until supported by platform
       2024-01-26
         Add option to mirror all dropped packets
       2024-01-23
         Add support for sFlow destinations
       2023-09-12
         Support a single MPLS ACL under SPAN attachments
       2023-07-24
         Remove support for sflow destination
       2022-09-08
         Add rate-limiting support
       2022-08-19
         Add sflow destination
       2022-08-01
         Add per-session mirror interval
       2022-07-13
         Add MPLS IPv4 and MPLS IPv6 ACLs under SPAN attachments
       2022-06-29
         Change Buffer Drop references to Traffic Management
       2022-06-17
         Added support for ACL merge groups
       2022-04-13
         Added support for mirroring dropped packets
       2021-12-30
         Remove deprecated config schema
       2021-10-06
         Added support for global mirror intervals
       2021-09-15
         Added support for mirror first configured on sessions
       2021-08-20
         Added support for ERSPAN session ID under GRE destinations";
    semver:module-version "5.0.0";
  }
  revision 2021-07-19 {
    description
      "Added extended range of values to mirror interval sampling
       2021-06-02
          Added support for non-default VRFs and router-id";
    semver:module-version "4.0.0";
  }
  revision 2020-12-03 {
    description
      "Added support for multiple attachments per class on an interface
       2020-09-14
           Added support for mirror rx and tx traffic to separate destinations";
    semver:module-version "3.1.0";
  }
  revision 2020-01-30 {
    description
      "Added support for L3 IPv4 and IPv6 ACLs on a L2 ethernet SPAN session
       2019-12-12
         Added support for file format and PCAP filter expressions under file";
    semver:module-version "3.0.0";
  }
  revision 2019-10-31 {
    description
      "Added mandatory nodes.
       2019-05-12
         Added support for file destinations.";
    semver:module-version "2.0.0";
  }
  revision 2019-04-05 {
    description
      "Establish semantic version baseline.";
    semver:module-version "1.0.0";
  }
  revision 2015-11-09 {
    description
      "IOS XR 6.0 revision.";
  }

  typedef Span-capacity-units {
    type enumeration {
      enum "kb" {
        value 1;
        description
          "Capacity units KB";
      }
      enum "mb" {
        value 2;
        description
          "Capacity units MB";
      }
      enum "gb" {
        value 3;
        description
          "Capacity units GB";
      }
    }
    description
      "Span capacity units";
  }

  typedef Span-protocol-capture-direction {
    type enumeration {
      enum "rx" {
        value 16;
        description
          "Rx protocol-capture packet mirroring";
      }
      enum "tx" {
        value 32;
        description
          "Tx protocol-capture packet mirroring";
      }
      enum "rx-tx" {
        value 48;
        description
          "Both Rx and Tx protocol-capture packet
           mirroring";
      }
    }
    description
      "Span protocol capture direction";
  }

  typedef Spantm-drops-direction {
    type enumeration {
      enum "rx" {
        value 4;
        description
          "Rx dropped packet mirroring";
      }
      enum "tx" {
        value 8;
        description
          "Tx dropped packet mirroring";
      }
      enum "rx-tx" {
        value 12;
        description
          "Both Rx and Tx dropped packet mirroring";
      }
    }
    description
      "Spantm drops direction";
  }

  typedef Span-forward-drops-direction {
    type enumeration {
      enum "rx" {
        value 1;
        description
          "Rx dropped packet mirroring";
      }
      enum "tx" {
        value 2;
        description
          "Tx dropped packet mirroring";
      }
      enum "rx-tx" {
        value 3;
        description
          "Both Rx and Tx dropped packet mirroring";
      }
    }
    description
      "Span forward drops direction";
  }

  typedef Span-drops-direction {
    type enumeration {
      enum "both" {
        value 0;
        description
          "Mirror in both directions";
      }
      enum "rx" {
        value 1;
        description
          "Mirror dropped packets in the Rx direction only";
      }
      enum "tx" {
        value 2;
        description
          "Mirror dropped packets in the Tx direction only";
      }
    }
    description
      "Span drops direction";
  }

  typedef Span-traffic-direction {
    type enumeration {
      enum "rx-only" {
        value 1;
        description
          "Replicate only received (ingress) traffic";
      }
      enum "tx-only" {
        value 2;
        description
          "Replicate only transmitted (egress) traffic";
      }
    }
    description
      "Span traffic direction";
  }

  typedef Span-destination {
    type enumeration {
      enum "interface" {
        value 0;
        description
          "Destination Interface";
      }
      enum "pseudowire" {
        value 1;
        description
          "Destination Pseudowire";
      }
      enum "ipv4-address" {
        value 2;
        description
          "Destination next-hop IPv4 address";
      }
      enum "ipv6-address" {
        value 3;
        description
          "Destination next-hop IPv6 address";
      }
      enum "file" {
        value 5;
        description
          "Destination File";
      }
      enum "udp" {
        value 6;
        description
          "Destination IP address over UDP";
      }
      enum "sflow" {
        value 8;
        description
          "Destination is a sFlow device";
      }
    }
    description
      "Span destination";
  }

  typedef Span-buffer {
    type enumeration {
      enum "circular" {
        value 1;
        description
          "File buffer circular";
      }
      enum "linear" {
        value 2;
        description
          "File buffer linear";
      }
    }
    description
      "Span buffer";
  }

  typedef Span-file-format {
    type enumeration {
      enum "pcapng" {
        value 2;
        description
          "File format pcapng";
      }
    }
    description
      "Span file format";
  }

  typedef Span-buffer-size {
    type uint32;
    description
      "Span buffer size";
  }

  grouping SPAN-ATTACHMENT-TABLE {
    description
      "Common node of interface-configuration,
       l2-transport";
    container span-attachments {
      description
        "Monitor Session container for this source
         interface";
      list span-attachment {
        key "session-name";
        description
          "Configuration for a particular Monitor Session";
        container mplsacl {
          presence "Indicates a mplsacl node is configured.";
          description
            "Enable MPLS ACL matching for traffic mirroring";
          leaf acl-enable {
            type empty;
            mandatory true;
            description
              "Enable ACL";
          }
          leaf acl-name {
            type dt1:Span-acl-name;
            description
              "ACL Name";
          }
          leaf merge-group {
            type uint32;
            description
              "merge group";
          }
          leaf priority {
            type uint32;
            description
              "priority";
          }
        }
        container ipv4acl {
          presence "Indicates a ipv4acl node is configured.";
          description
            "Enable IPv4 ACL matching for traffic mirroring";
          leaf acl-enable {
            type empty;
            mandatory true;
            description
              "Enable ACL";
          }
          leaf acl-name {
            type dt1:Span-acl-name;
            description
              "ACL Name";
          }
          leaf merge-group {
            type uint32;
            description
              "merge group";
          }
          leaf priority {
            type uint32;
            description
              "priority";
          }
        }
        container ipv6acl {
          presence "Indicates a ipv6acl node is configured.";
          description
            "Enable IPv6 ACL matching for traffic mirroring";
          leaf acl-enable {
            type empty;
            mandatory true;
            description
              "Enable ACL";
          }
          leaf acl-name {
            type dt1:Span-acl-name;
            description
              "ACL Name";
          }
          leaf merge-group {
            type uint32;
            description
              "merge group";
          }
          leaf priority {
            type uint32;
            description
              "priority";
          }
        }
        leaf drops {
          type boolean;
          description
            "Specify whether or not to mirror dropped
             packets";
        }
        leaf session-name {
          type dt1:Span-session-name;
          description
            "Session Name";
        }
        uses MIRROR-FIRST;
        uses MIRROR-INTERVAL;
        uses ATTACHMENT-CONFIG;
        uses ACL;
      }
    }
  }

  grouping ETHERNET-SPAN-DYN-TMPL-CFG-SPAN-ATTACHMENT-TABLE {
    description
      "Common node of interface-configuration,
       l2-transportCommon node of ip-subscriber, ppp,
       subscriber-service";
    container span-attachments {
      description
        "Monitor Session container for this source
         interface";
      list span-attachment {
        key "session-name";
        description
          "Configuration for a particular Monitor Session";
        leaf session-name {
          type dt1:Span-session-name;
          description
            "Session Name";
        }
        uses MIRROR-FIRST;
        uses MIRROR-INTERVAL;
        uses ATTACHMENT-CONFIG;
        uses ACL;
      }
    }
  }

  grouping MIRROR-INTERVAL {
    description
      "Common node of span-attachment, span-attachment";
    leaf mirror-interval {
      type dt1:Span-mirror-interval;
      description
        "Specify the mirror interval";
    }
  }

  grouping MIRROR-FIRST {
    description
      "Common node of span-attachment, span-attachment";
    leaf mirror-first {
      type uint32 {
        range "1..10000";
      }
      units "byte";
      description
        "Mirror a specified number of bytes from start of
         packet";
    }
  }

  grouping ACL {
    description
      "Common node of span-attachment, span-attachment";
    container acl {
      presence "Indicates a acl node is configured.";
      description
        "Enable ACL matching for traffic mirroring";
      leaf acl-enable {
        type empty;
        mandatory true;
        description
          "Enable ACL";
      }
      leaf acl-name {
        type dt1:Span-acl-name;
        description
          "ACL Name";
      }
      leaf merge-group {
        type uint32;
        description
          "merge group";
      }
      leaf priority {
        type uint32;
        description
          "priority";
      }
    }
  }

  grouping ATTACHMENT-CONFIG {
    description
      "Common node of span-attachment, span-attachment";
    container attachment-config {
      presence "Indicates a attachment-config node is configured.";
      description
        "Attach the interface to a Monitor Session";
      leaf session-class {
        type dt1:Span-session-class;
        mandatory true;
        description
          "Traffic class for the session";
      }
      leaf direction {
        type Span-traffic-direction;
        description
          "Specify the direction of traffic to replicate
           (optional)";
      }
      leaf port-level-enable {
        type empty;
        description
          "Enable port level traffic mirroring";
      }
    }
  }

  augment "/a1:interface-configurations/a1:interface-configuration/a2:l2-transport" {
    description
      "This augment extends the configuration data of
       'Cisco-IOS-XR-l2vpn-cfg'";
    uses SPAN-ATTACHMENT-TABLE;
  }
  augment "/a1:interface-configurations/a1:interface-configuration" {
    description
      "This augment extends the configuration data of
       'Cisco-IOS-XR-ifmgr-cfg'";
    uses SPAN-ATTACHMENT-TABLE;
  }
  container span-monitor-session {
    description
      "none";
    container sessions {
      description
        "Monitor-session configuration commands";
      list session {
        key "session";
        description
          "Configuration for a particular Monitor Session";
        container destination-rx {
          description
            "Specify a destination for Rx direction traffic";
          leaf destination-type {
            type Span-destination;
            description
              "Specify the type of destination";
          }
          leaf destination-interface-name {
            when "../destination-type = 'interface' or ../destination-type = 'udp'" {
              description
                "../DestinationType = Interface or .
                 ./DestinationType = UDP";
            }
            type xr:Interface-name;
            description
              "Specify the destination interface name";
          }
          leaf destination-ipv4-address {
            when "../destination-type = 'ipv4-address' or ../destination-type = 'udp'" {
              description
                "../DestinationType = IPv4Address or .
                 ./DestinationType = UDP";
            }
            type inet:ipv4-address-no-zone;
            description
              "Specify the destination IPv4 address";
          }
          leaf destination-ipv6-address {
            when "../destination-type = 'ipv6-address' or ../destination-type = 'udp'" {
              description
                "../DestinationType = IPv6Address or .
                 ./DestinationType = UDP";
            }
            type inet:ipv6-address-no-zone;
            description
              "Specify the destination IPv6 address";
          }
          leaf destination-buffer-size {
            when "../destination-type = 'file'" {
              description
                "../DestinationType = File";
            }
            type Span-buffer-size;
            units "kilobyte";
            description
              "Specify buffer size in kilobytes for
               destination file";
          }
          leaf destination-buffer-type {
            when "../destination-type = 'file'" {
              description
                "../DestinationType = File";
            }
            type Span-buffer;
            description
              "Specify the buffer type for destination file";
          }
          leaf destination-port {
            when "../destination-type = 'udp'" {
              description
                "../DestinationType = UDP";
            }
            type uint32;
            description
              "Specify the destination port";
          }
          leaf source-ipv4-address {
            when "../destination-type = 'udp'" {
              description
                "../DestinationType = UDP";
            }
            type inet:ipv4-address-no-zone;
            description
              "Specify the source IPv4 address";
          }
          leaf source-ipv6-address {
            when "../destination-type = 'udp'" {
              description
                "../DestinationType = UDP";
            }
            type inet:ipv6-address-no-zone;
            description
              "Specify the source  IPv6 address";
          }
          leaf source-port {
            when "../destination-type = 'udp'" {
              description
                "../DestinationType = UDP";
            }
            type uint32;
            description
              "Specify the source port";
          }
          leaf vrf-name {
            when "../destination-type = 'ipv4-address' or ../destination-type = 'ipv6-address' or ../destination-type = 'udp'" {
              description
                "../DestinationType = IPv4Address or .
                 ./DestinationType = IPv6Address or .
                 ./DestinationType = UDP";
            }
            type string;
            description
              "Specify the VRF name";
          }
          leaf destination-file-format {
            when "../destination-type = 'file'" {
              description
                "../DestinationType = File";
            }
            type Span-file-format;
            description
              "Specify the file format";
          }
          leaf destination-pcap-filter {
            when "../destination-type = 'file'" {
              description
                "../DestinationType = File";
            }
            type string;
            description
              "Specify a pcap filter";
          }
          leaf erspan-session-id {
            when "../destination-type = 'interface'" {
              description
                "../DestinationType = Interface";
            }
            type uint32;
            description
              "Specify an ERSPAN Session ID";
          }
          leaf always-on {
            when "../destination-type = 'file'" {
              description
                "../DestinationType = File";
            }
            type boolean;
            description
              "Specify if packet collection is always on";
          }
          leaf periodic-write-interval {
            when "../destination-type = 'file'" {
              description
                "../DestinationType = File";
            }
            type uint32 {
              range "1..2147483647";
            }
            units "second";
            description
              "Specify the periodic write interval in
               seconds";
          }
          leaf periodic-write-capacity {
            when "../destination-type = 'file'" {
              description
                "../DestinationType = File";
            }
            type uint32;
            description
              "Specify the maximum capacity for periodic
               write files";
          }
          leaf periodic-write-capacity-units {
            when "../destination-type = 'file'" {
              description
                "../DestinationType = File";
            }
            type Span-capacity-units;
            description
              "Specify the units for maximum periodic write
               capacity";
          }
          leaf exporter-map-name {
            when "../destination-type = 'sflow'" {
              description
                "../DestinationType = sflow";
            }
            type string;
            description
              "Specify the exporter-map name";
          }
        }
        container forward-drops {
          status deprecated;
          description
            "Mirror all forwarding-dropped packets";
          leaf direction {
            type Span-forward-drops-direction;
            description
              "Specify the direction to mirror dropped
               packets";
          }
          leaf pcap-filter {
            type string;
            description
              "Specify a pcap filter";
          }
        }
        container rate-limit {
          description
            "Specify the rate limit in pps";
          leaf rate-limit-rx-value {
            type uint32;
            description
              "Specify the Rx rate limit value in pps";
          }
          leaf rate-limit-tx-value {
            type uint32;
            description
              "Specify the Tx rate limit value in pps";
          }
        }
        container tm-drops {
          status deprecated;
          description
            "Mirror all traffic management dropped packets";
          leaf direction {
            type Spantm-drops-direction;
            description
              "Specify the direction to mirror dropped
               packets";
          }
          leaf pcap-filter {
            type string;
            description
              "Specify a pcap filter";
          }
        }
        container drops {
          description
            "Mirror dropped packets";
          leaf direction {
            type Span-drops-direction;
            description
              "Specify the direction to mirror dropped
               packets";
          }
          leaf packet-processing {
            type boolean;
            description
              "Mirror packet-processing drops";
          }
          leaf traffic-management {
            type boolean;
            description
              "Mirror traffic-management drops";
          }
          leaf pcap-filter {
            type string;
            description
              "Specify a pcap filter";
          }
        }
        container cloud-span {
          description
            "CloudSPAN configuration options for this
             session";
          leaf cloud-span-enable {
            type empty;
            description
              "Enable CloudSPAN on this session";
          }
        }
        container destination-tx {
          description
            "Specify a destination for Tx direction traffic";
          leaf destination-type {
            type Span-destination;
            description
              "Specify the type of destination";
          }
          leaf destination-interface-name {
            when "../destination-type = 'interface' or ../destination-type = 'udp'" {
              description
                "../DestinationType = Interface or .
                 ./DestinationType = UDP";
            }
            type xr:Interface-name;
            description
              "Specify the destination interface name";
          }
          leaf destination-ipv4-address {
            when "../destination-type = 'ipv4-address' or ../destination-type = 'udp'" {
              description
                "../DestinationType = IPv4Address or .
                 ./DestinationType = UDP";
            }
            type inet:ipv4-address-no-zone;
            description
              "Specify the destination IPv4 address";
          }
          leaf destination-ipv6-address {
            when "../destination-type = 'ipv6-address' or ../destination-type = 'udp'" {
              description
                "../DestinationType = IPv6Address or .
                 ./DestinationType = UDP";
            }
            type inet:ipv6-address-no-zone;
            description
              "Specify the destination IPv6 address";
          }
          leaf destination-buffer-size {
            when "../destination-type = 'file'" {
              description
                "../DestinationType = File";
            }
            type Span-buffer-size;
            units "kilobyte";
            description
              "Specify buffer size in kilobytes for
               destination file";
          }
          leaf destination-buffer-type {
            when "../destination-type = 'file'" {
              description
                "../DestinationType = File";
            }
            type Span-buffer;
            description
              "Specify the buffer type for destination file";
          }
          leaf destination-port {
            when "../destination-type = 'udp'" {
              description
                "../DestinationType = UDP";
            }
            type uint32;
            description
              "Specify the destination port";
          }
          leaf source-ipv4-address {
            when "../destination-type = 'udp'" {
              description
                "../DestinationType = UDP";
            }
            type inet:ipv4-address-no-zone;
            description
              "Specify the source IPv4 address";
          }
          leaf source-ipv6-address {
            when "../destination-type = 'udp'" {
              description
                "../DestinationType = UDP";
            }
            type inet:ipv6-address-no-zone;
            description
              "Specify the source  IPv6 address";
          }
          leaf source-port {
            when "../destination-type = 'udp'" {
              description
                "../DestinationType = UDP";
            }
            type uint32;
            description
              "Specify the source port";
          }
          leaf vrf-name {
            when "../destination-type = 'ipv4-address' or ../destination-type = 'ipv6-address' or ../destination-type = 'udp'" {
              description
                "../DestinationType = IPv4Address or .
                 ./DestinationType = IPv6Address or .
                 ./DestinationType = UDP";
            }
            type string;
            description
              "Specify the VRF name";
          }
          leaf destination-file-format {
            when "../destination-type = 'file'" {
              description
                "../DestinationType = File";
            }
            type Span-file-format;
            description
              "Specify the file format";
          }
          leaf destination-pcap-filter {
            when "../destination-type = 'file'" {
              description
                "../DestinationType = File";
            }
            type string;
            description
              "Specify a pcap filter";
          }
          leaf erspan-session-id {
            when "../destination-type = 'interface'" {
              description
                "../DestinationType = Interface";
            }
            type uint32;
            description
              "Specify an ERSPAN Session ID";
          }
          leaf always-on {
            when "../destination-type = 'file'" {
              description
                "../DestinationType = File";
            }
            type boolean;
            description
              "Specify if packet collection is always on";
          }
          leaf periodic-write-interval {
            when "../destination-type = 'file'" {
              description
                "../DestinationType = File";
            }
            type uint32 {
              range "1..2147483647";
            }
            units "second";
            description
              "Specify the periodic write interval in
               seconds";
          }
          leaf periodic-write-capacity {
            when "../destination-type = 'file'" {
              description
                "../DestinationType = File";
            }
            type uint32;
            description
              "Specify the maximum capacity for periodic
               write files";
          }
          leaf periodic-write-capacity-units {
            when "../destination-type = 'file'" {
              description
                "../DestinationType = File";
            }
            type Span-capacity-units;
            description
              "Specify the units for maximum periodic write
               capacity";
          }
          leaf exporter-map-name {
            when "../destination-type = 'sflow'" {
              description
                "../DestinationType = sflow";
            }
            type string;
            description
              "Specify the exporter-map name";
          }
        }
        container protocol-capture {
          description
            "Mirror protocol captured packets";
          leaf direction {
            type Span-protocol-capture-direction;
            description
              "Specify the direction to mirror
               protocol-captured packets";
          }
          leaf pcap-filter {
            type string;
            description
              "Specify a pcap filter";
          }
        }
        container destination {
          description
            "Specify a destination";
          leaf destination-type {
            type Span-destination;
            description
              "Specify the type of destination";
          }
          leaf destination-interface-name {
            when "../destination-type = 'interface' or ../destination-type = 'udp'" {
              description
                "../DestinationType = Interface or .
                 ./DestinationType = UDP";
            }
            type xr:Interface-name;
            description
              "Specify the destination interface name";
          }
          leaf destination-ipv4-address {
            when "../destination-type = 'ipv4-address' or ../destination-type = 'udp'" {
              description
                "../DestinationType = IPv4Address or .
                 ./DestinationType = UDP";
            }
            type inet:ipv4-address-no-zone;
            description
              "Specify the destination IPv4 address";
          }
          leaf destination-ipv6-address {
            when "../destination-type = 'ipv6-address' or ../destination-type = 'udp'" {
              description
                "../DestinationType = IPv6Address or .
                 ./DestinationType = UDP";
            }
            type inet:ipv6-address-no-zone;
            description
              "Specify the destination IPv6 address";
          }
          leaf destination-buffer-size {
            when "../destination-type = 'file'" {
              description
                "../DestinationType = File";
            }
            type Span-buffer-size;
            units "kilobyte";
            description
              "Specify buffer size in kilobytes for
               destination file";
          }
          leaf destination-buffer-type {
            when "../destination-type = 'file'" {
              description
                "../DestinationType = File";
            }
            type Span-buffer;
            description
              "Specify the buffer type for destination file";
          }
          leaf destination-port {
            when "../destination-type = 'udp'" {
              description
                "../DestinationType = UDP";
            }
            type uint32;
            description
              "Specify the destination port";
          }
          leaf source-ipv4-address {
            when "../destination-type = 'udp'" {
              description
                "../DestinationType = UDP";
            }
            type inet:ipv4-address-no-zone;
            description
              "Specify the source IPv4 address";
          }
          leaf source-ipv6-address {
            when "../destination-type = 'udp'" {
              description
                "../DestinationType = UDP";
            }
            type inet:ipv6-address-no-zone;
            description
              "Specify the source  IPv6 address";
          }
          leaf source-port {
            when "../destination-type = 'udp'" {
              description
                "../DestinationType = UDP";
            }
            type uint32;
            description
              "Specify the source port";
          }
          leaf vrf-name {
            when "../destination-type = 'ipv4-address' or ../destination-type = 'ipv6-address' or ../destination-type = 'udp'" {
              description
                "../DestinationType = IPv4Address or .
                 ./DestinationType = IPv6Address or .
                 ./DestinationType = UDP";
            }
            type string;
            description
              "Specify the VRF name";
          }
          leaf destination-file-format {
            when "../destination-type = 'file'" {
              description
                "../DestinationType = File";
            }
            type Span-file-format;
            description
              "Specify the file format";
          }
          leaf destination-pcap-filter {
            when "../destination-type = 'file'" {
              description
                "../DestinationType = File";
            }
            type string;
            description
              "Specify a pcap filter";
          }
          leaf erspan-session-id {
            when "../destination-type = 'interface'" {
              description
                "../DestinationType = Interface";
            }
            type uint32;
            description
              "Specify an ERSPAN Session ID";
          }
          leaf always-on {
            when "../destination-type = 'file'" {
              description
                "../DestinationType = File";
            }
            type boolean;
            description
              "Specify if packet collection is always on";
          }
          leaf periodic-write-interval {
            when "../destination-type = 'file'" {
              description
                "../DestinationType = File";
            }
            type uint32 {
              range "1..2147483647";
            }
            units "second";
            description
              "Specify the periodic write interval in
               seconds";
          }
          leaf periodic-write-capacity {
            when "../destination-type = 'file'" {
              description
                "../DestinationType = File";
            }
            type uint32;
            description
              "Specify the maximum capacity for periodic
               write files";
          }
          leaf periodic-write-capacity-units {
            when "../destination-type = 'file'" {
              description
                "../DestinationType = File";
            }
            type Span-capacity-units;
            description
              "Specify the units for maximum periodic write
               capacity";
          }
          leaf exporter-map-name {
            when "../destination-type = 'sflow'" {
              description
                "../DestinationType = sflow";
            }
            type string;
            description
              "Specify the exporter-map name";
          }
        }
        leaf class {
          type dt1:Span-session-class;
          mandatory true;
          description
            "Enable a Monitor Session.  Setting this item
             causes the Monitor Session to be created.";
        }
        leaf mirror-interval {
          type dt1:Span-mirror-interval;
          description
            "Mirror every Nth packet for this session";
        }
        leaf mirror-first {
          type uint32 {
            range "1..10000";
          }
          units "byte";
          description
            "Mirror a specified number of bytes from start
             of packet";
        }
        leaf discard-class {
          type uint32 {
            range "0..7";
          }
          description
            "Specify the discard class value to be set on
             all traffic mirrored to the destination";
        }
        leaf inject-interface {
          type xr:Interface-name;
          description
            "Specify the inject interface name";
        }
        leaf traffic-class {
          type uint32 {
            range "0..7";
          }
          description
            "Specify the traffic class value to be set on
             all traffic mirrored to the destination";
        }
        leaf session {
          type dt1:Span-session-name;
          description
            "Session Name";
        }
      }
    }
    container local-capture-capacity {
      description
        "Set the maximum amount of memory on disk used to
         maintain periodic capture files for all sessions";
      leaf periodic-write-capacity {
        type uint32;
        description
          "Specify the maximum capacity for periodic write
           files";
      }
      leaf periodic-write-capacity-units {
        type Span-capacity-units;
        description
          "Specify the units for maximum periodic write
           capacity";
      }
    }
    leaf router-id {
      type uint32 {
        range "1..255";
      }
      description
        "Specify the Router ID for this router";
    }
    leaf default-capture-disable {
      type empty;
      description
        "Do not configure the default session on startup";
    }
  }
}
