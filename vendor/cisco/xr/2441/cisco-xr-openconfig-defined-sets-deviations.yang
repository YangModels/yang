//*************  DO-NOT EDIT  **************
//*********** Auto-generated file ********** 

 module cisco-xr-openconfig-defined-sets-deviations {

  prefix  "oc-setsdevs";

  namespace "http://cisco.com/ns/yang/cisco-xr-openconfig-defined-sets-deviations";

  import openconfig-defined-sets { prefix oc-sets; }

  organization "Cisco Systems, Inc.";

  contact
    "Cisco Systems, Inc.
     Customer Service

     Postal: 170 West Tasman Drive
     San Jose, CA 95134

     Tel: +1 800 553-NETS

     E-mail: cs-yang@cisco.com";

  description
    "This module contains a set of deviations for 

     openconfig-defined-sets.yang@2022-12-14 

     on Cisco IOS-XR devices.

     Copyright (c) 2017 by Cisco Systems, Inc.
     All rights reserved.";

  revision "2024-09-03" {
    description
      "Initial revision applicable to IOS-XR 6.4.1";
  }


  deviation /oc-sets:defined-sets/oc-sets:ipv4-prefix-sets/oc-sets:ipv4-prefix-set {
    deviate not-supported;
  }

  deviation /oc-sets:defined-sets/oc-sets:ipv6-prefix-sets/oc-sets:ipv6-prefix-set {
    deviate not-supported;
  }

  deviation /oc-sets:defined-sets/oc-sets:port-sets/oc-sets:port-set {
    deviate not-supported;
  }


}
//total deviations:3
