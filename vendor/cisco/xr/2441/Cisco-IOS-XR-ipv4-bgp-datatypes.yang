module Cisco-IOS-XR-ipv4-bgp-datatypes {
  namespace "http://cisco.com/ns/yang/Cisco-IOS-XR-ipv4-bgp-datatypes";
  prefix ipv4-bgp-datatypes;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of generally useful
     derived YANG data types.
     
     Copyright (c) 2013-2022 by Cisco Systems, Inc.
     All rights reserved.";

  revision 2022-09-23 {
    description
      "Added BMP route-monitoring suport for L3VPN inbound post-policy and Local RIB, Deprecated container policy under route-monitoring
       2022-08-05
         Added schema for neighbor AFI/SAFI additional-paths";
    semver:module-version "1.1.0";
  }
  revision 2019-08-31 {
    description
      "Fixing revision error in module.";
    semver:module-version "1.0.0";
  }
  revision 2019-04-05 {
    description
      "Fixing backward compatibility error in module";
    semver:module-version "1.0.0";
  }
  revision 2019-04-05 {
    description
      "Establish semantic version baseline.";
  }
  revision 2017-06-26 {
    description
      "Change identifiers to be more readable.";
  }
  revision 2015-08-27 {
    description
      "IOS XR 5.3.2 revision.";
  }

  typedef Bgp-official-address-family {
    type enumeration {
      enum "ipv4" {
        value 1;
        description
          "IPv4";
      }
      enum "ipv6" {
        value 2;
        description
          "IPv6";
      }
      enum "l2vpn" {
        value 25;
        description
          "L2VPN";
      }
      enum "ls" {
        value 16388;
        description
          "LS";
      }
      enum "all" {
        value 65534;
        description
          "All";
      }
    }
    description
      "Bgp official address family";
  }

  typedef Bgp-extcomm-v4-addr-index {
    type uint32 {
      range "0..65535";
    }
    description
      "Bgp extcomm v4 addr index";
  }

  typedef Bgp-nbr-cap-additional-paths-cfg {
    type enumeration {
      enum "enable" {
        value 1;
        description
          "Enable neighbor additional-paths capability";
      }
      enum "disable" {
        value 2;
        description
          "Disable neighbor additional-paths capability";
      }
    }
    description
      "Bgp nbr cap additional paths cfg";
  }

  typedef Bgp-advertise-local-labeled-route-cfg {
    type enumeration {
      enum "enable" {
        value 1;
        description
          "Enable to advertise routes with local-label via
           Unicast Subsequent address family Indicator";
      }
      enum "disable" {
        value 2;
        description
          "Disable to advertise routes with local-label
           via Unicast Subsequent address family Indicator";
      }
    }
    description
      "Bgp advertise local labeled route cfg";
  }

  typedef Bgp-tos {
    type enumeration {
      enum "precedence" {
        value 0;
        description
          "IP Type of Service (TOS) precedence";
      }
      enum "dscp" {
        value 1;
        description
          "IP Differentiated Services Code Point(DSCP)";
      }
    }
    description
      "Bgp tos";
  }

  typedef Bgp-nbr-af-cap-additional-paths-cfg {
    type enumeration {
      enum "enable" {
        value 1;
        description
          "Enable neighbor address-family additional-paths
           capability";
      }
      enum "disable" {
        value 2;
        description
          "Disable neighbor address-family
           additional-paths capability";
      }
    }
    description
      "Bgp nbr af cap additional paths cfg";
  }

  typedef Bgp-address-family {
    type enumeration {
      enum "ipv4-unicast" {
        value 0;
        description
          "IPv4 unicast address family";
      }
      enum "ipv4-multicast" {
        value 1;
        description
          "IPv4 multicast address family";
      }
      enum "ipv4-labeled-unicast" {
        value 2;
        description
          "IPv4 labeled-unicast address family";
      }
      enum "ipv4-tunnel" {
        value 3;
        description
          "IPv4 tunnel address family";
      }
      enum "vpnv4-unicast" {
        value 4;
        description
          "VPNv4 unicast address family";
      }
      enum "ipv6-unicast" {
        value 5;
        description
          "IPv6 unicast address family";
      }
      enum "ipv6-multicast" {
        value 6;
        description
          "IPv6 multicast address family";
      }
      enum "ipv6-labeled-unicast" {
        value 7;
        description
          "IPv6 labeled-unicast address family";
      }
      enum "vpnv6-unicast" {
        value 8;
        description
          "VPNv6 unicast address family";
      }
      enum "ipv4-mdt" {
        value 9;
        description
          "IPv4 MDT address family";
      }
      enum "l2vpn-vpls" {
        value 10;
        description
          "L2VPN VPLS-VPWS address family";
      }
      enum "ipv4rt-constraint" {
        value 11;
        description
          "IPv4 rt-filter address family";
      }
      enum "ipv4-mvpn" {
        value 12;
        description
          "IPv4 MVPN address family";
      }
      enum "ipv6-mvpn" {
        value 13;
        description
          "IPv6 MVPN address family";
      }
      enum "l2vpn-evpn" {
        value 14;
        description
          "L2VPN EVPN address family";
      }
      enum "lsls" {
        value 15;
        description
          "Link-state link-state address family";
      }
      enum "vpnv4-multicast" {
        value 16;
        description
          "VPNv4 Multicast address family";
      }
      enum "vpnv6-multicast" {
        value 17;
        description
          "VPNv6 Multicast address family";
      }
      enum "ipv4-flowspec" {
        value 18;
        description
          "IPv4 flowspec address family";
      }
      enum "ipv6-flowspec" {
        value 19;
        description
          "IPv6 flowspec address family";
      }
      enum "vpnv4-flowspec" {
        value 20;
        description
          "VPNv4 flowspec address family";
      }
      enum "vpnv6-flowspec" {
        value 21;
        description
          "VPNv6 flowspec address family";
      }
      enum "l2vpn-mspw" {
        value 22;
        description
          "L2VPN MSPW address family";
      }
      enum "ipv4-sr-policy" {
        value 23;
        description
          "IPv4 Segment Routing (SR) policy address family";
      }
      enum "ipv6-sr-policy" {
        value 24;
        description
          "IPv6 Segment Routing (SR) policy address family";
      }
      enum "all-address-family" {
        value 25;
        description
          "All Address Families";
      }
    }
    description
      "Bgp address family";
  }

  typedef Bgp-update-filter-action {
    type enumeration {
      enum "treat-as-withdraw" {
        value 1;
        description
          "Treat the update message as a withdraw";
      }
      enum "discard-attibute" {
        value 2;
        description
          "Discard the attribute in update filter";
      }
    }
    description
      "Bgp update filter action";
  }

  typedef Bgp-attribute-range {
    type uint32 {
      range "0..256";
    }
    description
      "Bgp attribute range";
  }

  typedef Bgp-precedence-dscp {
    type union {
      type enumeration {
        enum "af11" {
          value 10;
          description
            "AF11 dscp (001010)";
        }
        enum "af12" {
          value 12;
          description
            "AF12 dscp (001100)";
        }
        enum "af13" {
          value 14;
          description
            "AF13 dscp (001110)";
        }
        enum "af21" {
          value 18;
          description
            "AF21 dscp (010010)";
        }
        enum "af22" {
          value 20;
          description
            "AF22 dscp (010100)";
        }
        enum "af23" {
          value 22;
          description
            "AF23 dscp (010110)";
        }
        enum "af31" {
          value 26;
          description
            "AF31 dscp (011010)";
        }
        enum "af32" {
          value 28;
          description
            "AF32 dscp (011100)";
        }
        enum "af33" {
          value 30;
          description
            "AF33 dscp (011110)";
        }
        enum "af41" {
          value 34;
          description
            "AF41 dscp (100010)";
        }
        enum "af42" {
          value 36;
          description
            "AF42 dscp (100100)";
        }
        enum "af43" {
          value 38;
          description
            "AF43 dscp (100110)";
        }
        enum "cs1" {
          value 8;
          description
            "CS1 dscp (001000)";
        }
        enum "cs2" {
          value 16;
          description
            "CS2 dscp (010000)";
        }
        enum "cs3" {
          value 24;
          description
            "CS3 dscp (011000)";
        }
        enum "cs4" {
          value 32;
          description
            "CS4 dscp (100000)";
        }
        enum "cs5" {
          value 40;
          description
            "CS5 dscp (101000)";
        }
        enum "cs6" {
          value 48;
          description
            "CS6 dscp (110000)";
        }
        enum "cs7" {
          value 56;
          description
            "CS7 dscp (111000)";
        }
        enum "ef" {
          value 46;
          description
            "EF dscp (101110)";
        }
        enum "critical" {
          value 5;
          description
            "critical precedence (5)";
        }
        enum "flash" {
          value 3;
          description
            "flash precedence (3)";
        }
        enum "flash-override" {
          value 4;
          description
            "flash override precedence (4)";
        }
        enum "immediate" {
          value 2;
          description
            "immediate precedence (2)";
        }
        enum "internet" {
          value 6;
          description
            "internetwork control precedence (6)";
        }
        enum "network" {
          value 7;
          description
            "network control precedence (7)";
        }
        enum "priority" {
          value 1;
          description
            "priority precedence (1)";
        }
        enum "default-or-routine" {
          value 0;
          description
            "default dscp or routine precedence (0)";
        }
      }
      type uint32 {
        range "0..63";
      }
    }
    description
      "Bgp precedence dscp";
  }

  typedef Bgp-af-additional-paths-cfg {
    type enumeration {
      enum "enable" {
        value 1;
        description
          "Enable AF Additional-paths";
      }
      enum "disable" {
        value 2;
        description
          "Disable AF Additional-paths";
      }
    }
    description
      "Bgp af additional paths cfg";
  }

  typedef Bmp-mode {
    type enumeration {
      enum "rmon-inbound-pre-policy" {
        value 0;
        description
          "Pickup routes in the route-monitoring mode in
           the inbound direction from peer before
           application of route-policy";
      }
      enum "rmon-inbound-post-policy" {
        value 1;
        description
          "Pickup routes in the route-monitoring mode in
           the inbound direction from peer after
           application of route-policy";
      }
      enum "rmon-local-rib" {
        value 4;
        description
          "Pickup routes in the route-monitoring mode that
           have been selected by the local BGP speaker's
           decision process";
      }
      enum "rmir-inbound-pre-policy" {
        value 5;
        description
          "Pickup routes in the route-mirroring mode in
           the inbound direction from peer before
           application of route-policy";
      }
    }
    description
      "Bmp mode";
  }

  typedef Bgp-as-range {
    type uint32 {
      range "0..4294967295";
    }
    description
      "Bgp as range";
  }

  typedef Bgp-subsequent-address-family {
    type enumeration {
      enum "unicast" {
        value 1;
        description
          "Unicast subsequent address family";
      }
      enum "multicast" {
        value 2;
        description
          "Multicast subsequent address family";
      }
      enum "labeled-unicast" {
        value 4;
        description
          "Labeled-unicast subsequent address family";
      }
      enum "mvpn" {
        value 5;
        description
          "MVPN subsequent address family";
      }
      enum "mspw" {
        value 6;
        description
          "MSPW subsequent address family";
      }
      enum "tunnel" {
        value 64;
        description
          "Tunnel subsequent address family";
      }
      enum "vpls" {
        value 65;
        description
          "VPLS subsequent address family";
      }
      enum "mdt" {
        value 66;
        description
          "MDT subsequent address family";
      }
      enum "vpws" {
        value 68;
        description
          "VPWS subsequent address family";
      }
      enum "evpn" {
        value 70;
        description
          "EVPN subsequent address family";
      }
      enum "ls" {
        value 71;
        description
          "LS subsequent address family";
      }
      enum "sr-policy" {
        value 73;
        description
          "SRPolicy subsequent address family";
      }
      enum "vpn" {
        value 128;
        description
          "VPN subsequent address family";
      }
      enum "vpn-mcast" {
        value 129;
        description
          "VPN-Multicast subsequent address family";
      }
      enum "rt-filter" {
        value 132;
        description
          "Rt-filter subsequent address family";
      }
      enum "flowspec" {
        value 133;
        description
          "Flowspec subsequent address family";
      }
      enum "vpn-flowspec" {
        value 134;
        description
          "VPN-Flowspec subsequent address family";
      }
      enum "all" {
        value 254;
        description
          "All subsequent address family";
      }
    }
    description
      "Bgp subsequent address family";
  }

  typedef Bgp-srv6-usid-allocation-mode-cfg {
    type enumeration {
      enum "srv6-usid-alloc-mode-default" {
        value 0;
        description
          "SRv6 uSID default allocation";
      }
      enum "srv6-usid-alloc-mode-wlib-enforce" {
        value 1;
        description
          "SRv6 uSID WLIB enforced allocation";
      }
      enum "srv6-usid-alloc-mode-wlib-fallback" {
        value 2;
        description
          "SRv6 uSID WLIB fallback allocation";
      }
    }
    description
      "Bgp srv6 usid allocation mode cfg";
  }

  typedef Bgp-extcomm-asn-index {
    type uint32 {
      range "0..4294967295";
    }
    description
      "Bgp extcomm asn index";
  }
}
