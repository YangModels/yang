module Cisco-IOS-XR-um-hw-module-acl-cfg {
  namespace "http://cisco.com/ns/yang/Cisco-IOS-XR-um-hw-module-acl-cfg";
  prefix um-hw-module-acl-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR hw-module-acl package configuration.
     
     This YANG module augments the
     modules with configuration data.
     
     Copyright (c) 2022 by Cisco Systems, Inc.
     All rights reserved.";

  revision 2022-09-29 {
    description
      "Initial release";
    semver:module-version "1.0.0";
  }

  container hardware {
    description
      "all line cards";
    container access-list {
      description
        "Access-list option";
      container atomic {
        description
          "Update acl method";
        container disable {
          presence "Indicates a disable node is configured.";
          description
            "Disable atomic updates";
        }
      }
      container abf-match-mpls {
        description
          "Configure ABF MPLS match parameters";
        container disable {
          presence "Indicates a disable node is configured.";
          description
            "Disable ABF ACL match for MPLS packets";
        }
      }
      container l3-compression-optimisation {
        presence "Indicates a l3-compression-optimisation node is configured.";
        description
          "Update acl method";
      }
    }
  }
}
