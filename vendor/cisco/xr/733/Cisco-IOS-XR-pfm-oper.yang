module Cisco-IOS-XR-pfm-oper {
  namespace "http://cisco.com/ns/yang/Cisco-IOS-XR-pfm-oper";
  prefix pfm-oper;

  import Cisco-IOS-XR-types {
    prefix xr;
  }
  import cisco-semver {
    prefix semver;
  }
  include Cisco-IOS-XR-pfm-oper-sub1 {
    revision-date 2021-07-10;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR pfm package operational data.
     
     This module contains definitions
     for the following management objects:
       platform-fault-manager: PFM data space
     
     Copyright (c) 2013-2021 by Cisco Systems, Inc.
     All rights reserved.";

  revision 2021-07-10 {
    description
      "IOS-XR 7.3.2 revision.";
    semver:module-version "1.0.0";
  }
  revision 2019-04-05 {
    description
      "Establish semantic version baseline.";
  }
  revision 2017-03-28 {
    description
      "IOS-XR 6.3.1 revision.";
  }
  revision 2015-11-09 {
    description
      "IOS XR 6.0 revision.";
  }

  grouping RACK-TABLE {
    description
      "Common node of platform-fault-manager,
       fault-type1, fault-type2, fault-type3";
    container racks {
      description
        "Table of racks";
      list rack {
        key "rack";
        description
          "Number";
        container slots {
          description
            "Table of slots";
          list slot {
            key "slot";
            description
              "Name";
            container fault-summary {
              description
                "Table of Hardware Summary";
              leaf severity-critical-count {
                type int32;
                description
                  "Fault Severity Critical count";
              }
              leaf severity-emergency-or-alert-count {
                type int32;
                description
                  "Fault Severity Emergency count";
              }
              leaf total {
                type int32;
                description
                  "Faulty Hardware total count";
              }
              leaf severity-error-count {
                type int32;
                description
                  "Fault Severity Error count";
              }
            }
            container hardware-fault-devices {
              description
                "Table of Hardware Failure";
              list hardware-fault-device {
                key "hw-fault-device";
                description
                  "Table of Hardware Failure Device";
                leaf hw-fault-device {
                  type xr:Cisco-ios-xr-string;
                  description
                    "hw fault device list";
                }
                list hardware-fault-type {
                  key "hw-fault-type";
                  description
                    "Table of Hardware Failure Type";
                  container hardware-fault-info {
                    description
                      "Hardware fault info";
                    uses PFM-SHOW-DEV-HW-FAULTS-XML;
                  }
                  leaf condition-description {
                    type string;
                    description
                      "Faulty Hardware Condition Description";
                  }
                  leaf condition-name {
                    type string;
                    description
                      "Faulty Hardware Condition Name";
                  }
                  leaf device-key {
                    type string;
                    description
                      "Faulty Hardware Device Key";
                  }
                  leaf device-version {
                    type int32;
                    description
                      "Faulty Hardware Device Version";
                  }
                  leaf condition-raised-timestamp {
                    type string;
                    description
                      "Fault Raised Timestamp";
                  }
                  leaf process-id {
                    type int32;
                    description
                      "Faulty Hardware Process ID";
                  }
                  leaf device-description {
                    type string;
                    description
                      "Faulty Hardware Device Description";
                  }
                  leaf condition-severity {
                    type string;
                    description
                      "Faulty Hardware Condition Severity";
                  }
                  leaf hw-fault-type {
                    type xr:Cisco-ios-xr-string;
                    description
                      "hw fault type list";
                  }
                }
              }
            }
            leaf slot {
              type xr:Cisco-ios-xr-string;
              description
                "Slot name";
            }
          }
        }
        leaf rack {
          type uint32;
          description
            "Rack number";
        }
      }
    }
  }

  container platform-fault-manager {
    config false;
    description
      "PFM data space";
    container exclude {
      description
        "Exclude specic hw fault ";
      container fault-type1s {
        description
          "Table of Hardware Failure Device";
        list fault-type1 {
          key "hw-fault-type1";
          description
            "Table of Hardware Failure Device";
          container fault-type2s {
            description
              "Table of Hardware Failure Device";
            list fault-type2 {
              key "hw-fault-type2";
              description
                "Table of Hardware Failure Device";
              container fault-type3s {
                description
                  "Table of Hardware Failure Device";
                list fault-type3 {
                  key "hw-fault-type3";
                  description
                    "Table of Hardware Failure Device";
                  leaf hw-fault-type3 {
                    type xr:Cisco-ios-xr-string;
                    description
                      "hw fault 3";
                  }
                  uses RACK-TABLE;
                }
              }
              leaf hw-fault-type2 {
                type xr:Cisco-ios-xr-string;
                description
                  "hw fault 2";
              }
              uses RACK-TABLE;
            }
          }
          leaf hw-fault-type1 {
            type xr:Cisco-ios-xr-string;
            description
              "hw fault 1";
          }
          uses RACK-TABLE;
        }
      }
    }
    uses RACK-TABLE;
  }
}
