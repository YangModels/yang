module Cisco-IOS-XR-evpn-oper {
  namespace "http://cisco.com/ns/yang/Cisco-IOS-XR-evpn-oper";
  prefix evpn-oper;

  import ietf-inet-types {
    prefix inet;
  }
  import ietf-yang-types {
    prefix yang;
  }
  import Cisco-IOS-XR-types {
    prefix xr;
  }
  import cisco-semver {
    prefix semver;
  }
  include Cisco-IOS-XR-evpn-oper-sub1 {
    revision-date 2021-05-12;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR evpn package operational data.
     
     This module contains definitions
     for the following management objects:
       evpn: EVPN Operational Table
     
     Copyright (c) 2013-2021 by Cisco Systems, Inc.
     All rights reserved.";

  revision 2021-05-12 {
    description
      "Added Union Path list buffer
       2021-05-06
         Added union-path-buffer to l2vpn evpn label.";
    semver:module-version "4.1.0";
  }
  revision 2020-05-05 {
    description
      "changes related to treat SRv6 and SID as well-known when parsing XML for yang
       2020-04-02
       EVPN DF Election Synchronization with NTP related changes";
    semver:module-version "4.0.0";
  }
  revision 2019-12-20 {
    description
      "EVPN SRv6 related changes";
    semver:module-version "3.0.0";
  }
  revision 2019-04-05 {
    description
      "Establish semantic version baseline.";
    semver:module-version "2.0.0";
  }
  revision 2018-09-26 {
    description
      "Duplicate detection parameters config moved from l2vpn to l2rib.";
  }
  revision 2017-09-07 {
    description
      "Fixed type translation error.";
  }
  revision 2017-05-01 {
    description
      "Fixing backward compatibility error in module.";
  }
  revision 2015-11-09 {
    description
      "IOS XR 6.0 revision.";
  }

  typedef Rd-addr-index {
    type uint32 {
      range "0..65535";
    }
    description
      "Rd addr index";
  }

  typedef Bgp-route-target-role {
    type enumeration {
      enum "both" {
        value 0;
        description
          "Both Import and export roles";
      }
      enum "import" {
        value 1;
        description
          "Import role";
      }
      enum "export" {
        value 2;
        description
          "Export role";
      }
    }
    description
      "Bgp route target role";
  }

  typedef Evpn-client-source {
    type enumeration {
      enum "local" {
        value 0;
        description
          "Source Local";
      }
      enum "remote" {
        value 1;
        description
          "Source Remote";
      }
    }
    description
      "Evpn client source";
  }

  typedef Evpn-client {
    type enumeration {
      enum "igmpsn" {
        value 0;
        description
          "IGMPSN client";
      }
      enum "igmp" {
        value 1;
        description
          "IGMP client";
      }
    }
    description
      "Evpn client";
  }

  typedef Evpnrdas-display-range {
    type uint32 {
      range "0..4294967295";
    }
    description
      "Evpnrdas display range";
  }

  typedef Rdas-index {
    type uint32 {
      range "0..4294967295";
    }
    description
      "Rdas index";
  }

  typedef Bgp-route-target-format {
    type enumeration {
      enum "none" {
        value 0;
        description
          "No route target";
      }
      enum "two-byte-as" {
        value 1;
        description
          "2 Byte AS:nn format";
      }
      enum "four-byte-as" {
        value 2;
        description
          "4 byte AS:nn format";
      }
      enum "ipv4-address" {
        value 3;
        description
          "IP:nn format";
      }
      enum "es-import" {
        value 1538;
        description
          "a.a.i format";
      }
    }
    description
      "Bgp route target format";
  }

  grouping EVI-TABLE {
    description
      "Common node of active, standby, node";
    container evis {
      description
        "L2VPN EVPN EVI Table";
      list evi {
        description
          "L2VPN EVPN EVI Entry";
        leaf evi {
          type uint32;
          description
            "EVPN id";
        }
        leaf encapsulation {
          type uint32;
          description
            "Encap";
        }
        uses L2VPN-EVPN-EVI-SUMMARY;
      }
    }
  }

  grouping SEGMENT-ROUTING-SRV6 {
    description
      "Common node of active, standby, node";
    container segment-routing-srv6 {
      description
        "L2VPN EVPN Segment Routing SRv6";
      uses L2VPN-EVPN-SRV6;
    }
  }

  grouping AC-ID-TABLE {
    description
      "Common node of active, standby, node";
    container ac-ids {
      description
        "EVPN AC ID table";
      list ac-id {
        description
          "EVPN AC ID table";
        leaf evi {
          type uint32;
          description
            "EVPN id";
        }
        leaf ac-id {
          type uint32;
          description
            "AC ID";
        }
        uses L2VPN-ATOM-ACID;
      }
    }
  }

  grouping EVI-DETAIL {
    description
      "Common node of active, standby, node";
    container evi-detail {
      description
        "L2VPN EVI Detail Table";
      container elements {
        description
          "EVI BGP RT Detail Info Elements";
        list element {
          description
            "EVI BGP RT Detail Info";
          leaf evi {
            type uint32;
            description
              "EVPN id";
          }
          leaf encapsulation {
            type uint32;
            description
              "Encap";
          }
          uses L2VPN-EVPN-EVI-DETAIL;
        }
      }
      container evi-children {
        description
          "Container for all EVI detail info";
        container neighbors {
          description
            "EVPN Neighbor table";
          list neighbor {
            description
              "EVPN Neighbor table";
            leaf evi {
              type uint32;
              description
                "EVPN id";
            }
            leaf encapsulation {
              type uint32;
              description
                "Encap";
            }
            leaf neighbor-ip {
              type inet:ip-address-no-zone;
              description
                "Neighbor IP";
            }
            uses L2VPN-EVPN-NEIGHBOR;
          }
        }
        container ethernet-auto-discoveries {
          description
            "EVPN Ethernet Auto-Discovery table";
          list ethernet-auto-discovery {
            description
              "EVPN Ethernet Auto-Discovery Entry";
            leaf evi {
              type uint32;
              description
                "EVPN id";
            }
            leaf encapsulation {
              type uint32;
              description
                "Encap";
            }
            leaf esi1 {
              type xr:Hex-integer;
              description
                "ES id (part 1/5)";
            }
            leaf esi2 {
              type xr:Hex-integer;
              description
                "ES id (part 2/5)";
            }
            leaf esi3 {
              type xr:Hex-integer;
              description
                "ES id (part 3/5)";
            }
            leaf esi4 {
              type xr:Hex-integer;
              description
                "ES id (part 4/5)";
            }
            leaf esi5 {
              type xr:Hex-integer;
              description
                "ES id (part 5/5)";
            }
            leaf ethernet-tag {
              type uint32;
              description
                "Ethernet Tag ID";
            }
            uses L2VPN-EVPN-EAD;
          }
        }
        container inclusive-multicasts {
          description
            "L2VPN EVPN IMCAST table";
          list inclusive-multicast {
            description
              "L2VPN EVPN IMCAST table";
            leaf evi {
              type uint32;
              description
                "EVPN id";
            }
            leaf encapsulation {
              type uint32;
              description
                "Encap";
            }
            leaf ethernet-tag {
              type uint32;
              description
                "Ethernet Tag";
            }
            leaf originating-ip {
              type inet:ip-address-no-zone;
              description
                "Originating IP";
            }
            uses L2VPN-EVPN-IMCAST;
          }
        }
        container route-targets {
          description
            "L2VPN EVPN EVI RT Child Table";
          list route-target {
            description
              "L2VPN EVPN EVI RT Table";
            leaf evi {
              type uint32;
              description
                "EVPN id";
            }
            leaf encapsulation {
              type uint32;
              description
                "Encap";
            }
            leaf role {
              type Bgp-route-target-role;
              description
                "Role of the route target";
            }
            leaf format {
              type Bgp-route-target-format;
              description
                "Format of the route target";
            }
            leaf as {
              type Evpnrdas-display-range;
              description
                "Two or Four byte AS Number";
            }
            leaf as-index {
              type Rdas-index;
              description
                "RT AS Index";
            }
            leaf addr-index {
              type Rd-addr-index;
              description
                "RT IP Index";
            }
            leaf address {
              type inet:ipv4-address-no-zone;
              description
                "RT IPv4 Address";
            }
            uses L2VPN-EVPN-EVI-BGP-RT;
          }
        }
        container macs {
          description
            "L2VPN EVPN EVI MAC table";
          list mac {
            description
              "L2VPN EVPN MAC table";
            leaf evi {
              type uint32;
              description
                "EVPN id";
            }
            leaf encapsulation {
              type uint32;
              description
                "Encap";
            }
            leaf ethernet-tag {
              type uint32;
              description
                "Ethernet Tag ID";
            }
            leaf mac-address {
              type yang:mac-address;
              description
                "MAC address";
            }
            leaf ip-address {
              type inet:ip-address-no-zone;
              description
                "IP Address";
            }
            uses L2VPN-EVPN-MAC;
          }
        }
      }
    }
  }

  grouping IGMP-TABLE {
    description
      "Common node of active, standby, node";
    container igmps {
      description
        "EVPN IGMP table";
      list igmp {
        description
          "IGMP Route";
        leaf client-type {
          type Evpn-client;
          description
            "Client type";
        }
        leaf source-type {
          type Evpn-client-source;
          description
            "Source type";
        }
        leaf is-leave {
          type boolean;
          description
            "Is leave route type";
        }
        leaf evi {
          type uint32;
          description
            "EVI";
        }
        leaf esi1 {
          type xr:Hex-integer;
          description
            "ES id (part 1/5)";
        }
        leaf esi2 {
          type xr:Hex-integer;
          description
            "ES id (part 2/5)";
        }
        leaf esi3 {
          type xr:Hex-integer;
          description
            "ES id (part 3/5)";
        }
        leaf esi4 {
          type xr:Hex-integer;
          description
            "ES id (part 4/5)";
        }
        leaf esi5 {
          type xr:Hex-integer;
          description
            "ES id (part 5/5)";
        }
        leaf ethernet-tag {
          type uint32;
          description
            "Ethernet Tag ID";
        }
        leaf src-ip {
          type inet:ip-address-no-zone;
          description
            "Source IP Address";
        }
        leaf grp-ip {
          type inet:ip-address-no-zone;
          description
            "Group IP Address";
        }
        leaf bd-id {
          type uint32;
          description
            "BD ID";
        }
        leaf bp-xcid {
          type uint32;
          description
            "BP XCID";
        }
        leaf vrf-id {
          type uint32;
          description
            "VRF ID";
        }
        leaf sub-interface-name {
          type xr:Interface-name;
          description
            "Sub-interface name";
        }
        uses L2VPN-EVPN-IGMP;
      }
    }
  }

  grouping INTERNAL-ID-TABLE {
    description
      "Common node of active, standby, node";
    container internal-ids {
      description
        "EVPN Internal ID Table";
      list internal-id {
        description
          "L2VPN EVPN Internal ID";
        leaf evi {
          type uint32;
          description
            "EVPN id";
        }
        leaf encapsulation {
          type uint32;
          description
            "Encap";
        }
        leaf esi1 {
          type xr:Hex-integer;
          description
            "ES id (part 1/5)";
        }
        leaf esi2 {
          type xr:Hex-integer;
          description
            "ES id (part 2/5)";
        }
        leaf esi3 {
          type xr:Hex-integer;
          description
            "ES id (part 3/5)";
        }
        leaf esi4 {
          type xr:Hex-integer;
          description
            "ES id (part 4/5)";
        }
        leaf esi5 {
          type xr:Hex-integer;
          description
            "ES id (part 5/5)";
        }
        leaf ethernet-tag {
          type uint32;
          description
            "Ethernet Tag ID";
        }
        uses L2VPN-EVPN-LABEL;
      }
    }
  }

  grouping ETHERNET-SEGMENT-TABLE {
    description
      "Common node of active, standby, node";
    container ethernet-segments {
      description
        "EVPN Ethernet-Segment Table";
      list ethernet-segment {
        description
          "EVPN Ethernet-Segment Entry";
        leaf interface-name {
          type xr:Interface-name;
          description
            "Interface";
        }
        leaf esi1 {
          type xr:Hex-integer;
          description
            "ES id (part 1/5)";
        }
        leaf esi2 {
          type xr:Hex-integer;
          description
            "ES id (part 2/5)";
        }
        leaf esi3 {
          type xr:Hex-integer;
          description
            "ES id (part 3/5)";
        }
        leaf esi4 {
          type xr:Hex-integer;
          description
            "ES id (part 4/5)";
        }
        leaf esi5 {
          type xr:Hex-integer;
          description
            "ES id (part 5/5)";
        }
        uses L2VPN-EVPN-ES;
      }
    }
  }

  grouping REMOTE-SHG-TABLE {
    description
      "Common node of active, standby, node";
    container remote-shgs {
      description
        "EVPN Remote SHG table";
      list remote-shg {
        description
          "EVPN Remote SHG";
        leaf evi {
          type uint32;
          description
            "EVPN id";
        }
        leaf esi1 {
          type xr:Hex-integer;
          description
            "ES id (part 1/5)";
        }
        leaf esi2 {
          type xr:Hex-integer;
          description
            "ES id (part 2/5)";
        }
        leaf esi3 {
          type xr:Hex-integer;
          description
            "ES id (part 3/5)";
        }
        leaf esi4 {
          type xr:Hex-integer;
          description
            "ES id (part 4/5)";
        }
        leaf esi5 {
          type xr:Hex-integer;
          description
            "ES id (part 5/5)";
        }
        uses L2VPN-EVPN-REMOTE-SHG;
      }
    }
  }

  grouping CLIENT {
    description
      "Common node of active, standby, node";
    container client {
      description
        "L2VPN EVPN Client";
      uses L2VPN-EVPN-CLIENT;
    }
  }

  grouping TEP-TABLE {
    description
      "Common node of active, standby, node";
    container teps {
      description
        "L2VPN EVPN TEP Table";
      list tep {
        key "tep-id";
        description
          "L2VPN EVPN TEP Entry";
        container tep-notification-entries {
          description
            "L2VPN EVPN TEP Notification Table";
          list tep-notification-entry {
            key "index";
            description
              "L2VPN EVPN TEP Notification Entry";
            leaf index {
              type uint32;
              description
                "TEP notification index";
            }
            uses L2VPN-EVPN-TEP-NOTIFICATION-ENTRY;
          }
        }
        container tep-info {
          description
            "L2VPN EVPN TEP Entry";
          uses L2VPN-EVPN-TEP;
        }
        leaf tep-id {
          type uint32;
          description
            "TEP id";
        }
      }
    }
  }

  grouping SUMMARY {
    description
      "Common node of active, standby, node";
    container summary {
      description
        "L2VPN EVPN Summary";
      uses L2VPN-EVPN-SUMMARY;
    }
  }

  grouping EVPN-GROUP-TABLE {
    description
      "Common node of active, standby, node";
    container evpn-groups {
      description
        "EVPN Group Table";
      list evpn-group {
        key "group-number";
        description
          "EVPN Group information";
        leaf group-number {
          type uint32 {
            range "1..4294967295";
          }
          description
            "EVPN group number";
        }
        uses EVPN-GRP-INFO;
      }
    }
  }

  grouping INTERNAL-LABEL-TABLE {
    description
      "Common node of active, standby, node";
    container internal-labels {
      description
        "EVPN Internal Label Table";
      list internal-label {
        description
          "L2VPN EVPN Internal Label";
        leaf evi {
          type uint32;
          description
            "EVPN id";
        }
        leaf encapsulation {
          type uint32;
          description
            "Encap";
        }
        leaf esi1 {
          type xr:Hex-integer;
          description
            "ES id (part 1/5)";
        }
        leaf esi2 {
          type xr:Hex-integer;
          description
            "ES id (part 2/5)";
        }
        leaf esi3 {
          type xr:Hex-integer;
          description
            "ES id (part 3/5)";
        }
        leaf esi4 {
          type xr:Hex-integer;
          description
            "ES id (part 4/5)";
        }
        leaf esi5 {
          type xr:Hex-integer;
          description
            "ES id (part 5/5)";
        }
        leaf ethernet-tag {
          type uint32;
          description
            "Ethernet Tag ID";
        }
        uses L2VPN-EVPN-LABEL;
      }
    }
  }

  container evpn {
    config false;
    description
      "EVPN Operational Table";
    container nodes {
      description
        "Table of EVPN operational data for a particular
         node";
      list node {
        key "node-id";
        description
          "EVPN operational data for a particular node";
        leaf node-id {
          type xr:Node-id;
          description
            "Location";
        }
        uses EVPN-GROUP-TABLE;
        uses REMOTE-SHG-TABLE;
        uses CLIENT;
        uses IGMP-TABLE;
        uses EVI-TABLE;
        uses SUMMARY;
        uses EVI-DETAIL;
        uses TEP-TABLE;
        uses INTERNAL-LABEL-TABLE;
        uses INTERNAL-ID-TABLE;
        uses SEGMENT-ROUTING-SRV6;
        uses ETHERNET-SEGMENT-TABLE;
        uses AC-ID-TABLE;
      }
    }
    container active {
      description
        "Active EVPN operational data";
      uses EVPN-GROUP-TABLE;
      uses REMOTE-SHG-TABLE;
      uses CLIENT;
      uses IGMP-TABLE;
      uses EVI-TABLE;
      uses SUMMARY;
      uses EVI-DETAIL;
      uses TEP-TABLE;
      uses INTERNAL-LABEL-TABLE;
      uses INTERNAL-ID-TABLE;
      uses SEGMENT-ROUTING-SRV6;
      uses ETHERNET-SEGMENT-TABLE;
      uses AC-ID-TABLE;
    }
    container standby {
      description
        "Standby EVPN operational data";
      uses EVPN-GROUP-TABLE;
      uses REMOTE-SHG-TABLE;
      uses CLIENT;
      uses IGMP-TABLE;
      uses EVI-TABLE;
      uses SUMMARY;
      uses EVI-DETAIL;
      uses TEP-TABLE;
      uses INTERNAL-LABEL-TABLE;
      uses INTERNAL-ID-TABLE;
      uses SEGMENT-ROUTING-SRV6;
      uses ETHERNET-SEGMENT-TABLE;
      uses AC-ID-TABLE;
    }
  }
}
