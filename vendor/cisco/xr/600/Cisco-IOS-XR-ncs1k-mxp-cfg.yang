module Cisco-IOS-XR-ncs1k-mxp-cfg {

  /*** NAMESPACE / PREFIX DEFINITION ***/

  namespace "http://cisco.com/ns/yang/Cisco-IOS-XR-ncs1k-mxp-cfg";


  prefix "ncs1k-mxp-cfg";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ncs1k-mxp package configuration.

     This module contains definitions
     for the following management objects:
       hardware-module: NCS1k HW module config

     Copyright (c) 2013-2015 by Cisco Systems, Inc.
     All rights reserved.";

  revision "2015-11-09" {
    description
      "IOS XR 6.0 revision.";
  }

  typedef Trunk-data-rate {
    type enumeration {
      enum hundred-gig {
        value 2;
        description "HundredGig";
      }
      enum two-hundred-gig {
        value 3;
        description "TwoHundredGig";
      }
      enum two-hundred-fifty-gig {
        value 4;
        description "TwoHundredFiftyGig";
      }
    }
    description "Trunk data rate";
  }
  typedef Client-data-rate {
    type enumeration {
      enum ten-gig {
        value 1;
        description "TenGig";
      }
      enum forty-gig {
        value 2;
        description "FortyGig";
      }
      enum hundred-gig {
        value 3;
        description "HundredGig";
      }
    }
    description "Client data rate";
  }
  typedef Fec {
    type enumeration {
      enum sd7 {
        value 1;
        description "SoftDecision7";
      }
      enum sd20 {
        value 2;
        description "SoftDecision20";
      }
    }
    description "Fec";
  }

  container hardware-module {
    xr:xr-xml-map "mxp_hwmodule:HardwareModule";
    description "NCS1k HW module config";

    list node {
      xr:xr-xml-map "mxp_hwmodule:Node";
      key "location";
      description "Node";

      container values {
        xr:xr-xml-map "mxp_hwmodule:Slice";
        description "Slice to be Provisioned";

        list value {
          xr:xr-xml-map "mxp_hwmodule:Values";
          key "slice-id";
          description "Data rates & FEC";
          leaf slice-id {
            xr:xr-xml-map "mxp_hwmodule:SliceId";
            type xr:Cisco-ios-xr-string;
            description "Set Slice";
          }
          leaf client-rate {
            xr:xr-xml-map "mxp_hwmodule:ClientRate";
            type Client-data-rate;
            description "Client Rate";
          }
          leaf trunk-rate {
            xr:xr-xml-map "mxp_hwmodule:TrunkRate";
            type Trunk-data-rate;
            description "TrunkRate";
          }
          leaf fec {
            xr:xr-xml-map "mxp_hwmodule:Fec";
            type Fec;
            description "FEC";
          }
        }
      }
      leaf location {
        xr:xr-xml-map "mxp_hwmodule:Location";
        type xr:Cisco-ios-xr-string;
        description "Fully qualified line card specification";
      }
    }
  }
}
