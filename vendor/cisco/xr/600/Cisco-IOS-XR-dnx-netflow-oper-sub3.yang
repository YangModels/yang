submodule Cisco-IOS-XR-dnx-netflow-oper-sub3 {

  belongs-to Cisco-IOS-XR-dnx-netflow-oper {
    prefix Cisco-IOS-XR-dnx-netflow-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR dnx-netflow package operational data.

     Copyright (c) 2013-2015 by Cisco Systems, Inc.
     All rights reserved.";

  revision "2015-11-09" {
    description
      "IOS XR 6.0 revision.";
  }

  typedef Nfmgr-fem-edm-exp-ver {
    type enumeration {
      enum v9 {
        description "Version 9 export format";
      }
      enum ip-fix {
        description "IPFIX export format";
      }
    }
    description "Netflow export version";
  }
  typedef Nfmgr-fem-edm-trans-proto {
    type enumeration {
      enum unspecified {
        description "Unspecified transport protocol";
      }
      enum udp {
        description "UDP transport protocol";
      }
    }
    description "Netflow export transport protocol";
  }

  grouping NFMGR-IPFIX-EXP-INFO {
    description "Netflow IPFIX export info";
    leaf sampler-table-export-timeout {
      xr:xr-xml-map "netflow_exporter_types:SamplerTableExportTimeo"+
        "ut";
      type uint32;
      units "second";
      description "Sampler table export timeout in seconds";
    }
    leaf interface-table-export-timeout {
      xr:xr-xml-map "netflow_exporter_types:InterfaceTableExportTim"+
        "eout";
      type uint32;
      units "second";
      description "Interface table export timeout in seconds";
    }
    leaf vrf-table-export-timeout {
      xr:xr-xml-map "netflow_exporter_types:VRFTableExportTimeout";
      type uint32;
      units "second";
      description "VRF table export timeout in seconds";
    }
    leaf options-template-export-timeout {
      xr:xr-xml-map "netflow_exporter_types:OptionsTemplateExportTi"+
        "meout";
      type uint32;
      units "second";
      description "Options template export timeout in seconds";
    }
    leaf data-template-export-timeout {
      xr:xr-xml-map "netflow_exporter_types:DataTemplateExportTimeo"+
        "ut";
      type uint32;
      units "second";
      description "Data template export timeout in seconds";
    }
    leaf common-template-export-timeout {
      xr:xr-xml-map "netflow_exporter_types:CommonTemplateExportTim"+
        "eout";
      type uint32;
      units "second";
      description "Common template export timeout in seconds";
    }
  }

  grouping NFMGR-V9-EXP-INFO {
    description "Netflow version 9 export info";
    leaf sampler-table-export-timeout {
      xr:xr-xml-map "netflow_exporter_types:SamplerTableExportTimeo"+
        "ut";
      type uint32;
      units "second";
      description "Sampler table export timeout in seconds";
    }
    leaf interface-table-export-timeout {
      xr:xr-xml-map "netflow_exporter_types:InterfaceTableExportTim"+
        "eout";
      type uint32;
      units "second";
      description "Interface table export timeout in seconds";
    }
    leaf vrf-table-export-timeout {
      xr:xr-xml-map "netflow_exporter_types:VrfTableExportTimeout";
      type uint32;
      units "second";
      description "VRF table export timeout in seconds";
    }
    leaf options-template-export-timeout {
      xr:xr-xml-map "netflow_exporter_types:OptionsTemplateExportTi"+
        "meout";
      type uint32;
      units "second";
      description "Options template export timeout in seconds";
    }
    leaf data-template-export-timeout {
      xr:xr-xml-map "netflow_exporter_types:DataTemplateExportTimeo"+
        "ut";
      type uint32;
      units "second";
      description "Data template export timeout in seconds";
    }
    leaf common-template-export-timeout {
      xr:xr-xml-map "netflow_exporter_types:CommonTemplateExportTim"+
        "eout";
      type uint32;
      units "second";
      description "Common template export timeout in seconds";
    }
  }

  grouping NFMGR-FEM-EDM-VER-INFO {
    description "Netflow export version info";

    container version9 {
      when "../version = 'v9'" {
        description "../version = 'V9'";
      }
      description "version9";
      uses NFMGR-V9-EXP-INFO;
    }

    container ipfix {
      when "../version = 'ip-fix'" {
        description "../version = 'IP_FIX'";
      }
      description "ipfix";
      uses NFMGR-IPFIX-EXP-INFO;
    }
    leaf version {
      xr:xr-xml-map "netflow_exporter_types:version";
      type Nfmgr-fem-edm-exp-ver;
      description "version";
    }
  }

  grouping NFMGR-FEM-EDM-CLTR-INFO {
    description "Netflow export collector info";
    leaf destination-address {
      xr:xr-xml-map "netflow_exporter_types:DestinationAddress";
      type string;
      description
        "Destination IPv4 address in AAA.BBB.CCC.DDD
        format";
    }
    leaf source-address {
      xr:xr-xml-map "netflow_exporter_types:SourceAddress";
      type string;
      description "Source IPv4 address in AAA.BBB.CCC.DDD format";
    }
    leaf vrf-name {
      xr:xr-xml-map "netflow_exporter_types:VRFName";
      type string;
      description "VRF name";
    }
    leaf source-interface {
      xr:xr-xml-map "netflow_exporter_types:SourceInterface";
      type string;
      description "Source interface name";
    }
    leaf dscp {
      xr:xr-xml-map "netflow_exporter_types:DSCP";
      type uint8;
      description "DSCP";
    }
    leaf transport-protocol {
      xr:xr-xml-map "netflow_exporter_types:TransportProtocol";
      type Nfmgr-fem-edm-trans-proto;
      description "Transport protocol";
    }
    leaf destination-port {
      xr:xr-xml-map "netflow_exporter_types:DestinationPort";
      type uint16;
      description "Transport destination port number";
    }
  }

  grouping NFMGR-FEM-EDM-INFO {
    description "Netflow flow exporter data";

    container version {
      description "Export version data";
      uses NFMGR-FEM-EDM-VER-INFO;
    }
    leaf id {
      xr:xr-xml-map "netflow_exporter_types:ID";
      type uint32;
      description "Unique ID in the global flow exporter ID space";
    }
    leaf name {
      xr:xr-xml-map "netflow_exporter_types:Name";
      type string;
      description "Name of the flow exporter map";
    }

    list collector {
      description "Export collector array";
      uses NFMGR-FEM-EDM-CLTR-INFO;
    }
  }
}
