submodule Cisco-IOS-XR-mpls-static-oper-sub1 {

  belongs-to Cisco-IOS-XR-mpls-static-oper {
    prefix Cisco-IOS-XR-mpls-static-oper;
  }

  /*** LINKAGE (IMPORTS / INCLUDES) ***/

  import ietf-inet-types { prefix "inet"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR mpls-static package operational data.

     Copyright (c) 2013-2015 by Cisco Systems, Inc.
     All rights reserved.";

  revision "2015-11-09" {
    description
      "IOS XR 6.0 revision.";
  }

  typedef Mgmt-static-nh-lbl {
    type enumeration {
      enum out-label {
        description "Next-Hop Label";
      }
      enum out-pop {
        description "Next-Hop Pop";
      }
      enum out-explicit-null {
        description "Next-Hop Explicit-Null";
      }
    }
    description "Mgmt static nh lbl";
  }
  typedef Mgmt-static-path {
    type enumeration {
      enum cross-connect-path {
        description "Crossconnect Path";
      }
      enum pop-lookup-path {
        description "Pop and Lookup Path";
      }
    }
    description "Mgmt static path";
  }
  typedef Static-ipv6-address {
    type inet:ipv6-address;
    description "Static ipv6 address";
  }
  typedef Mgmt-static-addr {
    type enumeration {
      enum ipv4 {
        description "IPv4";
      }
      enum ipv6 {
        description "IPv6";
      }
    }
    description "Mgmt static addr";
  }
  typedef Mgmt-mpls-static-label-status {
    type enumeration {
      enum not-created {
        description "Label Not Created";
      }
      enum vrf-down {
        description "Label without active VRF";
      }
      enum rewrite-vrf-down {
        description "Rewrite without active VRF";
      }
      enum lsd-disconnected {
        description "LSD is disconnected";
      }
      enum lsd-failed {
        description "LSD operation failed";
      }
      enum wait-for-lsd-reply {
        description "Waiting for LSD operation";
      }
      enum label-created {
        description "Label Created";
      }
      enum label-create-failed {
        description "Label Creation Failed";
      }
      enum label-rewrite-failed {
        description "Rewrite Creation Failed";
      }
      enum rewrite-next-hop-interface-missing {
        description "Rewrite NextHop Missing ";
      }
      enum label-discrepancy {
        description "Label Discrepancy ";
      }
      enum rewrite-discrepancy {
        description "Rewrite Discrepancy ";
      }
      enum label-status-unknown {
        description "Label Status Unknown";
      }
    }
    description "Mgmt mpls static label status";
  }
  typedef Mgmt-mpls-static-label-mode {
    type enumeration {
      enum none {
        description "No Label Mode";
      }
      enum per-prefix {
        description "Per-prefix Label";
      }
      enum per-vrf {
        description "Per-VRF label";
      }
      enum cross-connect {
        description "Label with crossconnect";
      }
    }
    description "Mgmt mpls static label mode";
  }

  grouping MPLS-STATIC-SUMMARY {
    description "Summary Information";
    leaf label-count {
      xr:xr-xml-map "mpls_static:LabelCount";
      type uint32;
      description "Total Number of Labels";
    }
    leaf label-error-count {
      xr:xr-xml-map "mpls_static:LabelErrorCount";
      type uint32;
      description "Total Number of Labels with Errors";
    }
    leaf label-discrepancy-count {
      xr:xr-xml-map "mpls_static:LabelDiscrepancyCount";
      type uint32;
      description "Total Number of Labels with Discrepancies";
    }
    leaf vrf-count {
      xr:xr-xml-map "mpls_static:VRFCount";
      type uint32;
      description "Total Number of VRF configured";
    }
    leaf active-vrf-count {
      xr:xr-xml-map "mpls_static:ActiveVRFCount";
      type uint32;
      description "Total Number of Active VRF Active";
    }
    leaf interface-count {
      xr:xr-xml-map "mpls_static:InterfaceCount";
      type uint32;
      description "Total Number of Interface";
    }
    leaf interface-foward-reference-count {
      xr:xr-xml-map "mpls_static:InterfaceFowardReferenceCount";
      type uint32;
      description "Total Number of Active Interface";
    }
    leaf mpls-enabled-interface-count {
      xr:xr-xml-map "mpls_static:MPLSEnabledInterfaceCount";
      type uint32;
      description "Total Number of MPLS enabled Interface";
    }
    leaf lsd-connected {
      xr:xr-xml-map "mpls_static:LSDConnected";
      type boolean;
      description "LSD connection is up";
    }
    leaf im-connected {
      xr:xr-xml-map "mpls_static:IMConnected";
      type boolean;
      description "IM is connected";
    }
    leaf rsi-connected {
      xr:xr-xml-map "mpls_static:RSIConnected";
      type boolean;
      description "RSI is connected";
    }
  }

  grouping MPLS-STATIC-LSP-PATH-INFO {
    description "Path Info";
    leaf path {
      xr:xr-xml-map "mpls_static:Path";
      type uint32;
      description "Path Number";
    }
    leaf type {
      xr:xr-xml-map "mpls_static:Type";
      type Mgmt-static-path;
      description "Path Type";
    }
    leaf next-hop-label-type {
      xr:xr-xml-map "mpls_static:NextHopLabelType";
      type Mgmt-static-nh-lbl;
      description "Next-Hop Label Type";
    }
    leaf next-hop-label {
      xr:xr-xml-map "mpls_static:NextHopLabel";
      type uint32;
      description "Next-Hop Label";
    }
    leaf next-hop-interface-name {
      xr:xr-xml-map "mpls_static:NextHopInterfaceName";
      type string;
      description "Next-Hop Interface Name";
    }
    leaf next-hop-ipv4-address-set {
      xr:xr-xml-map "mpls_static:NextHopIPv4AddressSet";
      type boolean;
      description "Next-Hop Ipv4 Set";
    }
    leaf next-hop-ipv4-address {
      xr:xr-xml-map "mpls_static:NextHopIPv4Address";
      type inet:ipv4-address;
      description "Next-Hop Ipv4 Address";
    }
  }

  grouping MPLS-STATIC-CTX-PREFIX-BAG {
    description "MPLS STATIC CTX PREFIX BAG";
    leaf af-name {
      xr:xr-xml-map "mpls_static:AFName";
      type Mgmt-static-addr;
      description "AFName";
    }
    leaf ipv4-prefix {
      xr:xr-xml-map "mpls_static:IPv4Prefix";
      when "../af-name = 'ipv4'" {
        description "../AFName = 'IPv4'";
      }
      type inet:ipv4-address;
      description "IPv4 context";
    }
    leaf ipv6-prefix {
      xr:xr-xml-map "mpls_static:IPv6Prefix";
      when "../af-name = 'ipv6'" {
        description "../AFName = 'IPv6'";
      }
      type Static-ipv6-address;
      description "IPv6 context";
    }
  }

  grouping MPLS-STATIC-LBL-PREFIX-INFO {
    description "Prefix Information";

    container prefix {
      description "Prefix";
      uses MPLS-STATIC-CTX-PREFIX-BAG;
    }
    leaf prefix-length {
      xr:xr-xml-map "mpls_static:PrefixLength";
      type uint8;
      description "Prefix length";
    }
  }

  grouping MPLS-STATIC-LBL-INFO {
    description "Static Label and Prefix information";

    container prefix {
      description "Prefix Information";
      uses MPLS-STATIC-LBL-PREFIX-INFO;
    }
    leaf label {
      xr:xr-xml-map "mpls_static:Label";
      type uint32;
      description "Label value";
    }
    leaf label-mode {
      xr:xr-xml-map "mpls_static:LabelMode";
      type Mgmt-mpls-static-label-mode;
      description "Label Mode";
    }
    leaf label-status {
      xr:xr-xml-map "mpls_static:LabelStatus";
      type Mgmt-mpls-static-label-status;
      description "Label Status";
    }
    leaf vrf-name {
      xr:xr-xml-map "mpls_static:VRFName";
      type string;
      description "VRF name";
    }

    list path-info {
      description "Path Information";
      uses MPLS-STATIC-LSP-PATH-INFO;
    }
  }
}
