module Cisco-IOS-XR-ethernet-cfm-oper {

  /*** NAMESPACE / PREFIX DEFINITION ***/

  namespace "http://cisco.com/ns"+
    "/yang/Cisco-IOS-XR-ethernet-cfm-oper";


  prefix "ethernet-cfm-oper";

  /*** LINKAGE (IMPORTS / INCLUDES) ***/

  import ietf-yang-types { prefix "yang"; }

  import Cisco-IOS-XR-types { prefix "xr"; }

  import Cisco-IOS-XR-ethernet-cfm-datatypes { prefix "dt1"; }

  import Cisco-IOS-XR-infra-sla-oper { prefix "a1"; }

  include Cisco-IOS-XR-ethernet-cfm-oper-sub4 {
    revision-date 2015-11-09;
  }

  include Cisco-IOS-XR-ethernet-cfm-oper-sub3 {
    revision-date 2015-11-09;
  }

  include Cisco-IOS-XR-ethernet-cfm-oper-sub2 {
    revision-date 2015-11-09;
  }

  include Cisco-IOS-XR-ethernet-cfm-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ethernet-cfm package operational data.

     This module contains definitions
     for the following management objects:
       cfm: CFM operational data

     This YANG module augments the
       Cisco-IOS-XR-infra-sla-oper
     module with state data.

     Copyright (c) 2013-2015 by Cisco Systems, Inc.
     All rights reserved.";

  revision "2015-11-09" {
    description
      "IOS XR 6.0 revision.";
  }

  typedef Cfm-ais-dir {
    type enumeration {
      enum up {
        value 0;
        description "Packets sent inward";
      }
      enum down {
        value 1;
        description "Packets sent outward";
      }
    }
    description "Cfm ais dir";
  }

  container cfm {
    xr:xr-xml-map "cfm_oper:CFM";
    config false;
    description "CFM operational data";

    container nodes {
      xr:xr-xml-map "cfm_oper:NodeTable";
      description "Node table for node-specific operational data";

      list node {
        xr:xr-xml-map "cfm_oper:Node";
        key "node";
        description "Node-specific data for a particular node";

        container interface-aises {
          xr:xr-xml-map "cfm_oper:InterfaceAISTable";
          description "Interface AIS table";

          list interface-ais {
            xr:xr-xml-map "cfm_oper:InterfaceAIS";
            key "interface-name direction";
            description "AIS statistics for a particular interface";
            leaf interface-name {
              xr:xr-xml-map "cfm_oper:InterfaceName";
              type xr:Interface-name;
              description "Interface";
            }
            leaf direction {
              xr:xr-xml-map "cfm_oper:Direction";
              type Cfm-ais-dir;
              description "AIS Direction";
            }
            uses CFM-PM-EFP-AIS-BAG;
          }
        }

        container interface-statistics {
          xr:xr-xml-map "cfm_oper:InterfaceStatisticsTable";
          description "Interface Statistics table";

          list interface-statistic {
            xr:xr-xml-map "cfm_oper:InterfaceStatistics";
            key "interface";
            description "Counters for a particular interface";
            leaf interface {
              xr:xr-xml-map "cfm_oper:Interface";
              type xr:Interface-name;
              description "Interface";
            }
            uses CFM-PM-EFP-STATS-BAG;
          }
        }

        container summary {
          xr:xr-xml-map "cfm_oper:Summary";
          description "Summary";
          uses CFM-MA-SUMMARY;
        }

        container ccm-learning-databases {
          xr:xr-xml-map "cfm_oper:CCMLearningDatabaseTable";
          description "CCMLearningDatabase table";

          list ccm-learning-database {
            xr:xr-xml-map "cfm_oper:CCMLearningDatabase";
            key "domain service mac-address";
            description "CCM Learning Database entry";
            leaf domain {
              xr:xr-xml-map "cfm_oper:Domain";
              type string;
              description "Maintenance Domain";
            }
            leaf service {
              xr:xr-xml-map "cfm_oper:Service";
              type string;
              description "Service (Maintenance Association)";
            }
            leaf mac-address {
              xr:xr-xml-map "cfm_oper:MACAddress";
              type yang:mac-address;
              description "MAC Address";
            }
            uses CFM-PM-CLDB-BAG;
          }
        }
        leaf node {
          xr:xr-xml-map "cfm_oper:Node";
          type xr:Node-id;
          description "Node";
        }
      }
    }

    container global {
      xr:xr-xml-map "cfm_oper:Global";
      description "Global operational data";

      container incomplete-traceroutes {
        xr:xr-xml-map "cfm_oper:IncompleteTracerouteTable";
        description "Incomplete Traceroute table";

        list incomplete-traceroute {
          xr:xr-xml-map "cfm_oper:IncompleteTraceroute";
          key "domain service mep-id interface transaction-id";
          description
            "Information about a traceroute operation that
            has not yet timed out";
          leaf domain {
            xr:xr-xml-map "cfm_oper:Domain";
            type string;
            description "Maintenance Domain";
          }
          leaf service {
            xr:xr-xml-map "cfm_oper:Service";
            type string;
            description "Service (Maintenance Association)";
          }
          leaf mep-id {
            xr:xr-xml-map "cfm_oper:MEP_ID";
            type dt1:Cfm-mep-id;
            description "MEP ID";
          }
          leaf interface {
            xr:xr-xml-map "cfm_oper:Interface";
            type xr:Interface-name;
            description "Interface";
          }
          leaf transaction-id {
            xr:xr-xml-map "cfm_oper:TransactionID";
            type int32;
            description "Transaction ID";
          }
          uses CFM-PM-MEP-INCOMPLETE-TR-BAG;
        }
      }

      container maintenance-points {
        xr:xr-xml-map "cfm_oper:MaintenancePointTable";
        description "Maintenance Points table";

        list maintenance-point {
          xr:xr-xml-map "cfm_oper:MaintenancePoint";
          key "domain service interface";
          description
            "Information about a particular Maintenance
            Point";
          leaf domain {
            xr:xr-xml-map "cfm_oper:Domain";
            type string;
            description "Maintenance Domain";
          }
          leaf service {
            xr:xr-xml-map "cfm_oper:Service";
            type string;
            description "Service (Maintenance Association)";
          }
          leaf interface {
            xr:xr-xml-map "cfm_oper:Interface";
            type xr:Interface-name;
            description "Interface";
          }
          uses CFM-MA-MP-BRIEF;
        }
      }

      container peer-meps {
        xr:xr-xml-map "cfm_oper:PeerMEPTable";
        description "Peer MEPs table";

        list peer-mep {
          xr:xr-xml-map "cfm_oper:PeerMEP";
          key "domain service local-mep-id interface peer-mep-id"+
            " peer-mac-address";
          description
            "Information about a peer MEP for a particular
            local MEP";
          leaf domain {
            xr:xr-xml-map "cfm_oper:Domain";
            type string;
            description "Maintenance Domain";
          }
          leaf service {
            xr:xr-xml-map "cfm_oper:Service";
            type string;
            description "Service (Maintenance Association)";
          }
          leaf local-mep-id {
            xr:xr-xml-map "cfm_oper:LocalMEP_ID";
            type dt1:Cfm-mep-id;
            description "MEP ID of Local MEP";
          }
          leaf interface {
            xr:xr-xml-map "cfm_oper:Interface";
            type xr:Interface-name;
            description "Interface";
          }
          leaf peer-mep-id {
            xr:xr-xml-map "cfm_oper:PeerMEP_ID";
            type dt1:Cfm-mep-id;
            description "MEP ID of Peer MEP";
          }
          leaf peer-mac-address {
            xr:xr-xml-map "cfm_oper:PeerMACAddress";
            type yang:mac-address;
            description "Peer MAC address";
          }
          uses CFM-PM-REMOTE-MEPS-BAG;
        }
      }

      container global-configuration-errors {
        xr:xr-xml-map "cfm_oper:GlobalConfigurationErrorTable";
        description "Global configuration errors table";

        list global-configuration-error {
          xr:xr-xml-map "cfm_oper:GlobalConfigurationError";
          key "domain service";
          description
            "Information about a particular configuration
            error";
          leaf domain {
            xr:xr-xml-map "cfm_oper:Domain";
            type string;
            description "Maintenance Domain";
          }
          leaf service {
            xr:xr-xml-map "cfm_oper:Service";
            type string;
            description "Service (Maintenance Association)";
          }
          uses CGM-CFG-ERRORS;
        }
      }

      container mep-configuration-errors {
        xr:xr-xml-map "cfm_oper:MEPConfigurationErrorTable";
        description "MEP configuration errors table";

        list mep-configuration-error {
          xr:xr-xml-map "cfm_oper:MEPConfigurationError";
          key "domain service interface";
          description
            "Information about a particular configuration
            error";
          leaf domain {
            xr:xr-xml-map "cfm_oper:Domain";
            type string;
            description "Maintenance Domain";
          }
          leaf service {
            xr:xr-xml-map "cfm_oper:Service";
            type string;
            description "Service (Maintenance Association)";
          }
          leaf interface {
            xr:xr-xml-map "cfm_oper:Interface";
            type xr:Interface-name;
            description "Interface";
          }
          uses CFM-MA-MEP-ERRORS;
        }
      }

      container traceroute-caches {
        xr:xr-xml-map "cfm_oper:TracerouteCacheTable";
        description "Traceroute Cache table";

        list traceroute-cache {
          xr:xr-xml-map "cfm_oper:TracerouteCache";
          key "domain service mep-id interface transaction-id";
          description
            "Information about a particular traceroute
            operation";
          leaf domain {
            xr:xr-xml-map "cfm_oper:Domain";
            type string;
            description "Maintenance Domain";
          }
          leaf service {
            xr:xr-xml-map "cfm_oper:Service";
            type string;
            description "Service (Maintenance Association)";
          }
          leaf mep-id {
            xr:xr-xml-map "cfm_oper:MEP_ID";
            type dt1:Cfm-mep-id;
            description "MEP ID";
          }
          leaf interface {
            xr:xr-xml-map "cfm_oper:Interface";
            type xr:Interface-name;
            description "Interface";
          }
          leaf transaction-id {
            xr:xr-xml-map "cfm_oper:TransactionID";
            type int32;
            description "Transaction ID";
          }
          uses CFM-PM-MEP-TR-CACHE-BAG;
        }
      }

      container local-meps {
        xr:xr-xml-map "cfm_oper:LocalMEPTable";
        description "Local MEPs table";

        list local-mep {
          xr:xr-xml-map "cfm_oper:LocalMEP";
          key "domain service mep-id interface";
          description "Information about a particular local MEP";
          leaf domain {
            xr:xr-xml-map "cfm_oper:Domain";
            type string;
            description "Maintenance Domain";
          }
          leaf service {
            xr:xr-xml-map "cfm_oper:Service";
            type string;
            description "Service (Maintenance Association)";
          }
          leaf mep-id {
            xr:xr-xml-map "cfm_oper:MEP_ID";
            type dt1:Cfm-mep-id;
            description "MEP ID";
          }
          leaf interface {
            xr:xr-xml-map "cfm_oper:Interface";
            type xr:Interface-name;
            description "Interface";
          }
          uses CFM-PM-MEP-STATS-BAG;
        }
      }
    }
  }

  augment "/a1:sla/a1:protocols" {

    container ethernet {
      xr:xr-xml-map "cfm_sla_mgmt_sla_oper:Ethernet";
      description "The Ethernet SLA protocol";

      container statistics-on-demand-currents {
        xr:xr-xml-map "cfm_sla_mgmt_sla_oper:StatisticsOnDemandCurr"+
          "entTable";
        description
          "Table of current statistics for SLA on-demand
          operations";

        list statistics-on-demand-current {
          xr:xr-xml-map "cfm_sla_mgmt_sla_oper:StatisticsOnDemandCu"+
            "rrent";
          description
            "Current statistics data for an SLA on-demand
            operation";
          leaf operation-id {
            xr:xr-xml-map "cfm_sla_mgmt_sla_oper:OperationID";
            type uint32 {
              range "1..4294967295";
            }
            description "Operation ID";
          }
          leaf domain-name {
            xr:xr-xml-map "cfm_sla_mgmt_sla_oper:DomainName";
            type string;
            description "Domain name";
          }
          leaf interface-name {
            xr:xr-xml-map "cfm_sla_mgmt_sla_oper:InterfaceName";
            type xr:Interface-name;
            description "Interface name";
          }
          leaf mep-id {
            xr:xr-xml-map "cfm_sla_mgmt_sla_oper:MEP_ID";
            type uint32 {
              range "1..8191";
            }
            description
              "MEP ID in the range 1 to 8191. Either MEP ID
              or MAC address must be specified.";
          }
          leaf mac-address {
            xr:xr-xml-map "cfm_sla_mgmt_sla_oper:MACAddress";
            type yang:mac-address;
            description
              "Unicast MAC Address in xxxx.xxxx.xxxx format.
              Either MEP ID or MAC address must be
              specified.";
          }
          uses SLA-OPER-OPERATION-STATISTICS;
        }
      }

      container operations {
        xr:xr-xml-map "cfm_sla_mgmt_sla_oper:OperationTable";
        description "Table of SLA operations";

        list operation {
          xr:xr-xml-map "cfm_sla_mgmt_sla_oper:Operation";
          description "SLA operation to get operation data for";
          leaf profile-name {
            xr:xr-xml-map "cfm_sla_mgmt_sla_oper:ProfileName";
            type xr:Cisco-ios-xr-string;
            description "Profile Name";
          }
          leaf domain-name {
            xr:xr-xml-map "cfm_sla_mgmt_sla_oper:DomainName";
            type string;
            description "Domain name";
          }
          leaf interface-name {
            xr:xr-xml-map "cfm_sla_mgmt_sla_oper:InterfaceName";
            type xr:Interface-name;
            description "Interface name";
          }
          leaf mep-id {
            xr:xr-xml-map "cfm_sla_mgmt_sla_oper:MEP_ID";
            type uint32 {
              range "1..8191";
            }
            description
              "MEP ID in the range 1 to 8191. Either MEP ID
              or MAC address must be specified.";
          }
          leaf mac-address {
            xr:xr-xml-map "cfm_sla_mgmt_sla_oper:MACAddress";
            type yang:mac-address;
            description
              "Unicast MAC Address in xxxx.xxxx.xxxx format.
              Either MEP ID or MAC address must be
              specified.";
          }
          uses SLA-OPER-OPERATION;
        }
      }

      container statistics-historicals {
        xr:xr-xml-map "cfm_sla_mgmt_sla_oper:StatisticsHistoricalTa"+
          "ble";
        description
          "Table of historical statistics for SLA
          operations";

        list statistics-historical {
          xr:xr-xml-map "cfm_sla_mgmt_sla_oper:StatisticsHistorical";
          description
            "Historical statistics data for an SLA
            configured operation";
          leaf profile-name {
            xr:xr-xml-map "cfm_sla_mgmt_sla_oper:ProfileName";
            type xr:Cisco-ios-xr-string;
            description "Profile Name";
          }
          leaf domain-name {
            xr:xr-xml-map "cfm_sla_mgmt_sla_oper:DomainName";
            type string;
            description "Domain name";
          }
          leaf interface-name {
            xr:xr-xml-map "cfm_sla_mgmt_sla_oper:InterfaceName";
            type xr:Interface-name;
            description "Interface name";
          }
          leaf mep-id {
            xr:xr-xml-map "cfm_sla_mgmt_sla_oper:MEP_ID";
            type uint32 {
              range "1..8191";
            }
            description
              "MEP ID in the range 1 to 8191. Either MEP ID
              or MAC address must be specified.";
          }
          leaf mac-address {
            xr:xr-xml-map "cfm_sla_mgmt_sla_oper:MACAddress";
            type yang:mac-address;
            description
              "Unicast MAC Address in xxxx.xxxx.xxxx format.
              Either MEP ID or MAC address must be
              specified.";
          }
          uses SLA-OPER-OPERATION-STATISTICS;
        }
      }

      container statistics-on-demand-historicals {
        xr:xr-xml-map "cfm_sla_mgmt_sla_oper:StatisticsOnDemandHist"+
          "oricalTable";
        description
          "Table of historical statistics for SLA
          on-demand operations";

        list statistics-on-demand-historical {
          xr:xr-xml-map "cfm_sla_mgmt_sla_oper:StatisticsOnDemandHi"+
            "storical";
          description
            "Historical statistics data for an SLA
            on-demand  operation";
          leaf operation-id {
            xr:xr-xml-map "cfm_sla_mgmt_sla_oper:OperationID";
            type uint32 {
              range "1..4294967295";
            }
            description "Operation ID";
          }
          leaf domain-name {
            xr:xr-xml-map "cfm_sla_mgmt_sla_oper:DomainName";
            type string;
            description "Domain name";
          }
          leaf interface-name {
            xr:xr-xml-map "cfm_sla_mgmt_sla_oper:InterfaceName";
            type xr:Interface-name;
            description "Interface name";
          }
          leaf mep-id {
            xr:xr-xml-map "cfm_sla_mgmt_sla_oper:MEP_ID";
            type uint32 {
              range "1..8191";
            }
            description
              "MEP ID in the range 1 to 8191. Either MEP ID
              or MAC address must be specified.";
          }
          leaf mac-address {
            xr:xr-xml-map "cfm_sla_mgmt_sla_oper:MACAddress";
            type yang:mac-address;
            description
              "Unicast MAC Address in xxxx.xxxx.xxxx format.
              Either MEP ID or MAC address must be
              specified.";
          }
          uses SLA-OPER-OPERATION-STATISTICS;
        }
      }

      container config-errors {
        xr:xr-xml-map "cfm_sla_mgmt_sla_oper:ConfigErrorsTable";
        description
          "Table of SLA configuration errors on configured
          operations";

        list config-error {
          xr:xr-xml-map "cfm_sla_mgmt_sla_oper:ConfigErrors";
          description
            "SLA operation to get configuration errors data
            for";
          leaf profile-name {
            xr:xr-xml-map "cfm_sla_mgmt_sla_oper:ProfileName";
            type xr:Cisco-ios-xr-string;
            description "Profile Name";
          }
          leaf domain-name {
            xr:xr-xml-map "cfm_sla_mgmt_sla_oper:DomainName";
            type string;
            description "Domain name";
          }
          leaf interface-name {
            xr:xr-xml-map "cfm_sla_mgmt_sla_oper:InterfaceName";
            type xr:Interface-name;
            description "Interface name";
          }
          leaf mep-id {
            xr:xr-xml-map "cfm_sla_mgmt_sla_oper:MEP_ID";
            type uint32 {
              range "1..8191";
            }
            description "MEP ID in the range 1 to 8191";
          }
          leaf mac-address {
            xr:xr-xml-map "cfm_sla_mgmt_sla_oper:MACAddress";
            type yang:mac-address;
            description
              "Unicast MAC Address in xxxx.xxxx.xxxx format";
          }
          uses SLA-OPER-CONFIG-ERRORS;
        }
      }

      container on-demand-operations {
        xr:xr-xml-map "cfm_sla_mgmt_sla_oper:OnDemandOperationTable";
        description "Table of SLA on-demand operations";

        list on-demand-operation {
          xr:xr-xml-map "cfm_sla_mgmt_sla_oper:OnDemandOperation";
          description
            "SLA on-demand operation to get operation data
            for";
          leaf operation-id {
            xr:xr-xml-map "cfm_sla_mgmt_sla_oper:OperationID";
            type uint32 {
              range "1..4294967295";
            }
            description "Operation ID";
          }
          leaf domain-name {
            xr:xr-xml-map "cfm_sla_mgmt_sla_oper:DomainName";
            type string;
            description "Domain name";
          }
          leaf interface-name {
            xr:xr-xml-map "cfm_sla_mgmt_sla_oper:InterfaceName";
            type xr:Interface-name;
            description "Interface name";
          }
          leaf mep-id {
            xr:xr-xml-map "cfm_sla_mgmt_sla_oper:MEP_ID";
            type uint32 {
              range "1..8191";
            }
            description
              "MEP ID in the range 1 to 8191. Either MEP ID
              or MAC address must be specified.";
          }
          leaf mac-address {
            xr:xr-xml-map "cfm_sla_mgmt_sla_oper:MACAddress";
            type yang:mac-address;
            description
              "Unicast MAC Address in xxxx.xxxx.xxxx format.
              Either MEP ID or MAC address must be
              specified.";
          }
          uses SLA-OPER-OPERATION;
        }
      }

      container statistics-currents {
        xr:xr-xml-map "cfm_sla_mgmt_sla_oper:StatisticsCurrentTable";
        description
          "Table of current statistics for SLA operations";

        list statistics-current {
          xr:xr-xml-map "cfm_sla_mgmt_sla_oper:StatisticsCurrent";
          description
            "Current statistics data for an SLA configured
            operation";
          leaf profile-name {
            xr:xr-xml-map "cfm_sla_mgmt_sla_oper:ProfileName";
            type xr:Cisco-ios-xr-string;
            description "Profile Name";
          }
          leaf domain-name {
            xr:xr-xml-map "cfm_sla_mgmt_sla_oper:DomainName";
            type string;
            description "Domain name";
          }
          leaf interface-name {
            xr:xr-xml-map "cfm_sla_mgmt_sla_oper:InterfaceName";
            type xr:Interface-name;
            description "Interface name";
          }
          leaf mep-id {
            xr:xr-xml-map "cfm_sla_mgmt_sla_oper:MEP_ID";
            type uint32 {
              range "1..8191";
            }
            description
              "MEP ID in the range 1 to 8191. Either MEP ID
              or MAC address must be specified.";
          }
          leaf mac-address {
            xr:xr-xml-map "cfm_sla_mgmt_sla_oper:MACAddress";
            type yang:mac-address;
            description
              "Unicast MAC Address in xxxx.xxxx.xxxx format.
              Either MEP ID or MAC address must be
              specified.";
          }
          uses SLA-OPER-OPERATION-STATISTICS;
        }
      }
    }
    description
      "This augment extends the operational data of
      'Cisco-IOS-XR-infra-sla-oper'";
  }
}
