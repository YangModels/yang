module Cisco-IOS-XR-ipv4-ospf-oper {

  /*** NAMESPACE / PREFIX DEFINITION ***/

  namespace "http://cisco.com/ns/yang/Cisco-IOS-XR-ipv4-ospf-oper";


  prefix "ipv4-ospf-oper";

  /*** LINKAGE (IMPORTS / INCLUDES) ***/

  import ietf-inet-types { prefix "inet"; }

  import Cisco-IOS-XR-types { prefix "xr"; }

  include Cisco-IOS-XR-ipv4-ospf-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ipv4-ospf package operational data.

     This module contains definitions
     for the following management objects:
       ospf: OSPF operational data

     Copyright (c) 2013-2015 by Cisco Systems, Inc.
     All rights reserved.";

  revision "2015-11-09" {
    description
      "IOS XR 6.0 revision.";
  }

  typedef Ospf-prefix-length {
    type uint32 {
      range "0..32";
    }
    description "Ospf prefix length";
  }
  typedef Ospf-ls {
    type enumeration {
      enum router {
        value 1;
        description "Router LSA";
      }
      enum network {
        value 2;
        description "Network LSA";
      }
      enum summary {
        value 3;
        description "Summary LSA";
      }
      enum asbr-summary {
        value 4;
        description "ASBR-Summary LSA";
      }
      enum external {
        value 5;
        description "External LSA";
      }
      enum nssa-external {
        value 7;
        description "NSSA External LSA";
      }
      enum opaque-link {
        value 9;
        description "Opaque LSALink Scope";
      }
      enum opaque-area {
        value 10;
        description "Opaque LSA Area Scope";
      }
      enum opaque-as {
        value 11;
        description "Opaque LSA AS Scope";
      }
    }
    description "Ospf ls";
  }

  grouping ROUTE {
    description
      "Common node of route-table,
      multicast-intact-route-table";

    list route {
      xr:xr-xml-map "ipv4-ospf_oper:Route";
      description "An OSPF route";
      leaf prefix {
        xr:xr-xml-map "ipv4-ospf_oper:Prefix";
        type inet:ipv4-address-no-zone;
        description "Prefix";
      }
      leaf prefix-length {
        xr:xr-xml-map "ipv4-ospf_oper:PrefixLength";
        type Ospf-prefix-length;
        description "Prefix Length";
      }
      uses OSPF-SH-TOPOLOGY;
    }
  }

  grouping BORDER-ROUTER-TABLE {
    description "Common node of default-vrf, vrf";

    container border-routers {
      xr:xr-xml-map "ipv4-ospf_oper:BorderRouterTable";
      description "Border router table";

      list border-router {
        xr:xr-xml-map "ipv4-ospf_oper:BorderRouter";
        key "border-router-id";
        description "Information for a particular border router";
        leaf border-router-id {
          xr:xr-xml-map "ipv4-ospf_oper:BorderRouterID";
          type inet:ipv4-address-no-zone;
          description "Router address";
        }
        uses OSPF-SH-BORDER-ROUTER;
      }
    }
  }

  grouping AREA-TABLE {
    description "Common node of default-vrf, vrf";

    container areas {
      xr:xr-xml-map "ipv4-ospf_oper:AreaTable";
      description "Area table";

      list area {
        xr:xr-xml-map "ipv4-ospf_oper:Area";
        key "area-id";
        description "Container for per area data";
        leaf area-id {
          xr:xr-xml-map "ipv4-ospf_oper:AreaID";
          type int32;
          description "Area ID";
        }
        uses FLOOD-LIST-TABLE;
        uses NEIGHBOR-TABLE;
        uses INTERFACE-BRIEF-TABLE;
        uses REQUEST-LIST-TABLE;
        uses RETRANSMISSION-LIST-TABLE;
        uses NEIGHBOR-DETAIL-TABLE;
        uses INTERFACE-TABLE;
      }
    }
  }

  grouping OSPF-SUMMARY {
    description "Common node of default-vrf, vrf";

    container ospf-summary {
      xr:xr-xml-map "ipv4-ospf_oper:OSPFSummary";
      description "Fast-reroute topology information";
      uses OSPF-SH-STATS-AGGT;
    }
  }

  grouping PROCESS-INFORMATION {
    description "Common node of default-vrf, vrf";

    container process-information {
      xr:xr-xml-map "ipv4-ospf_oper:ProcessInformation";
      description "Container for OSPF Process information";

      container protocol-areas {
        xr:xr-xml-map "ipv4-ospf_oper:ProtocolAreaTable";
        description "Protocol Area table";

        list protocol-area {
          xr:xr-xml-map "ipv4-ospf_oper:ProtocolArea";
          description "Area information";
          leaf area-id {
            xr:xr-xml-map "ipv4-ospf_oper:AreaID";
            type int32;
            description "Area ID if in integer format";
          }
          leaf address {
            xr:xr-xml-map "ipv4-ospf_oper:Address";
            type inet:ipv4-address-no-zone;
            description "Area ID if in IP address format";
          }
          uses OSPF-SH-PROTO-AREA;
        }
      }

      container protocol-summary {
        xr:xr-xml-map "ipv4-ospf_oper:ProtocolSummary";
        description "Basic OSPF protocol information";
        uses OSPF-SH-PROTOCOL;
      }

      container redistributions {
        xr:xr-xml-map "ipv4-ospf_oper:RedistributionTable";
        description "Redistribution information table";

        list redistribution {
          xr:xr-xml-map "ipv4-ospf_oper:Redistribution";
          description "Redistribution information";
          leaf protocol-name {
            xr:xr-xml-map "ipv4-ospf_oper:ProtocolName";
            type xr:Cisco-ios-xr-string;
            description "Protocol name";
          }
          leaf process-name {
            xr:xr-xml-map "ipv4-ospf_oper:ProcessName";
            type xr:Cisco-ios-xr-string;
            description "Process name";
          }
          uses OSPF-SH-REDIST;
        }
      }

      container process-areas {
        xr:xr-xml-map "ipv4-ospf_oper:ProcessAreaTable";
        description "Process Area table";

        list process-area {
          xr:xr-xml-map "ipv4-ospf_oper:ProcessArea";
          description "Detailed information for a particular area";
          leaf area-id {
            xr:xr-xml-map "ipv4-ospf_oper:AreaID";
            type int32;
            description "Area ID if in integer format";
          }
          leaf address {
            xr:xr-xml-map "ipv4-ospf_oper:Address";
            type inet:ipv4-address-no-zone;
            description "Area ID if in IP address format";
          }
          uses OSPF-SH-AREA;
        }
      }

      container process-summary {
        xr:xr-xml-map "ipv4-ospf_oper:ProcessSummary";
        description "Basic OSPF summary information";
        uses OSPF-SH-SUMMARY;
      }
    }
  }

  grouping ADJACENCY-INFORMATION {
    description "Common node of default-vrf, vrf";

    container adjacency-information {
      xr:xr-xml-map "ipv4-ospf_oper:AdjacencyInformation";
      description "Container for OSPF Interfaces";
      uses NEIGHBOR-TABLE;
      uses REQUEST-LIST-TABLE;
      uses RETRANSMISSION-LIST-TABLE;
      uses NEIGHBOR-DETAIL-TABLE;
    }
  }

  grouping RETRANSMISSION-LIST-TABLE {
    description "Common node of adjacency-information, area";

    container retransmissions {
      xr:xr-xml-map "ipv4-ospf_oper:RetransmissionListTable";
      description "Retransmission list table";

      list retransmission {
        xr:xr-xml-map "ipv4-ospf_oper:RetransmissionList";
        description
          "Retransmission list for a particular adjacency";
        leaf interface-name {
          xr:xr-xml-map "ipv4-ospf_oper:InterfaceName";
          type xr:Interface-name;
          description "Interface name";
        }
        leaf neighbor-address {
          xr:xr-xml-map "ipv4-ospf_oper:NeighborAddress";
          type inet:ipv4-address-no-zone;
          description "Neighbor address";
        }
        uses OSPF-SH-RETRANS-LIST;
      }
    }
  }

  grouping LSA-SUMMARY-TABLE {
    description "Common node of database, database-area";

    container lsa-summaries {
      xr:xr-xml-map "ipv4-ospf_oper:LSASummaryTable";
      description "Link state advertisement summary table";

      list lsa-summary {
        xr:xr-xml-map "ipv4-ospf_oper:LSASummary";
        description "LSA summary information";
        leaf area-id {
          xr:xr-xml-map "ipv4-ospf_oper:AreaID";
          type int32;
          description "Area ID";
        }
        leaf ls-type {
          xr:xr-xml-map "ipv4-ospf_oper:LSType";
          type Ospf-ls;
          description "Link state type";
        }
        leaf ls-id {
          xr:xr-xml-map "ipv4-ospf_oper:LS_ID";
          type inet:ipv4-address-no-zone;
          description "Link state ID";
        }
        leaf advertising-router {
          xr:xr-xml-map "ipv4-ospf_oper:AdvertisingRouter";
          type inet:ipv4-address-no-zone;
          description "Advertising Router ID";
        }
        leaf interface-name {
          xr:xr-xml-map "ipv4-ospf_oper:InterfaceName";
          type xr:Interface-name;
          description "Interface name";
        }
        uses OSPF-SH-DATABASE;
      }
    }
  }

  grouping ROUTE-INFORMATION {
    description "Common node of default-vrf, vrf";

    container route-information {
      xr:xr-xml-map "ipv4-ospf_oper:RouteInformation";
      description "Container for OSPF routing tables";

      container backup-routes {
        xr:xr-xml-map "ipv4-ospf_oper:BackupRouteTable";
        description "OSPF Route Table Including Backup Paths";

        list backup-route {
          xr:xr-xml-map "ipv4-ospf_oper:BackupRoute";
          description "OSPF route including backup paths";
          leaf prefix {
            xr:xr-xml-map "ipv4-ospf_oper:Prefix";
            type inet:ipv4-address-no-zone;
            description "Prefix";
          }
          leaf prefix-length {
            xr:xr-xml-map "ipv4-ospf_oper:PrefixLength";
            type Ospf-prefix-length;
            description "Prefix Length";
          }
          uses OSPF-SH-TOPOLOGY-BACKUP;
        }
      }

      container multicast-intact-route-table {
        xr:xr-xml-map "ipv4-ospf_oper:MulticastIntactRouteTable";
        description
          "OSPF Route Table including multicast-intact
          routes";
        uses ROUTE;
      }

      container summary-information {
        xr:xr-xml-map "ipv4-ospf_oper:SummaryInformation";
        description "OSPF route summary statistics";
        uses OSPF-SH-ROUTE-SUMMARY;
      }

      container connected-routes {
        xr:xr-xml-map "ipv4-ospf_oper:ConnectedRouteTable";
        description "OSPF Connected Route Table";

        list connected-route {
          xr:xr-xml-map "ipv4-ospf_oper:ConnectedRoute";
          description "Connected route";
          leaf prefix {
            xr:xr-xml-map "ipv4-ospf_oper:Prefix";
            type inet:ipv4-address-no-zone;
            description "Prefix";
          }
          leaf prefix-length {
            xr:xr-xml-map "ipv4-ospf_oper:PrefixLength";
            type Ospf-prefix-length;
            description "Prefix Length";
          }
          uses OSPF-SH-TOPOLOGY;
        }
      }

      container local-routes {
        xr:xr-xml-map "ipv4-ospf_oper:LocalRouteTable";
        description "OSPF Local Route Table";

        list local-route {
          xr:xr-xml-map "ipv4-ospf_oper:LocalRoute";
          description "Local route";
          leaf prefix {
            xr:xr-xml-map "ipv4-ospf_oper:Prefix";
            type inet:ipv4-address-no-zone;
            description "Prefix";
          }
          leaf prefix-length {
            xr:xr-xml-map "ipv4-ospf_oper:PrefixLength";
            type Ospf-prefix-length;
            description "Prefix Length";
          }
          uses OSPF-SH-TOPOLOGY;
        }
      }

      container route-areas {
        xr:xr-xml-map "ipv4-ospf_oper:RouteAreaTable";
        description "OSPF Area Route Table";

        list route-area {
          xr:xr-xml-map "ipv4-ospf_oper:RouteArea";
          key "area-id";
          description "OSPF Area Route";

          container connected-route-areas {
            xr:xr-xml-map "ipv4-ospf_oper:ConnectedRouteAreaTable";
            description "OSPF Connected Route Table in an area";

            list connected-route-area {
              xr:xr-xml-map "ipv4-ospf_oper:ConnectedRouteArea";
              description "Connected route";
              leaf prefix {
                xr:xr-xml-map "ipv4-ospf_oper:Prefix";
                type inet:ipv4-address-no-zone;
                description "Prefix";
              }
              leaf prefix-length {
                xr:xr-xml-map "ipv4-ospf_oper:PrefixLength";
                type Ospf-prefix-length;
                description "Prefix Length";
              }
              uses OSPF-SH-TOPOLOGY;
            }
          }

          container backup-route-areas {
            xr:xr-xml-map "ipv4-ospf_oper:BackupRouteAreaTable";
            description
              "OSPF Route Table Including Backup Paths in an
              area";

            list backup-route-area {
              xr:xr-xml-map "ipv4-ospf_oper:BackupRouteArea";
              description "OSPF route including backup paths";
              leaf prefix {
                xr:xr-xml-map "ipv4-ospf_oper:Prefix";
                type inet:ipv4-address-no-zone;
                description "Prefix";
              }
              leaf prefix-length {
                xr:xr-xml-map "ipv4-ospf_oper:PrefixLength";
                type Ospf-prefix-length;
                description "Prefix Length";
              }
              uses OSPF-SH-TOPOLOGY-BACKUP;
            }
          }

          container route-area-informations {
            xr:xr-xml-map "ipv4-ospf_oper:RouteAreaInformationTable";
            description "OSPF Area Route Entry";

            list route-area-information {
              xr:xr-xml-map "ipv4-ospf_oper:RouteAreaInformation";
              description "An OSPF route";
              leaf prefix {
                xr:xr-xml-map "ipv4-ospf_oper:Prefix";
                type inet:ipv4-address-no-zone;
                description "Prefix";
              }
              leaf prefix-length {
                xr:xr-xml-map "ipv4-ospf_oper:PrefixLength";
                type Ospf-prefix-length;
                description "Prefix Length";
              }
              uses OSPF-SH-TOPOLOGY;
            }
          }

          container multicast-intact-route-areas {
            xr:xr-xml-map "ipv4-ospf_oper:MulticastIntactRouteAreaT"+
              "able";
            description
              "OSPF Area multicast-intact included route
              entry";

            list multicast-intact-route-area {
              xr:xr-xml-map "ipv4-ospf_oper:MulticastIntactRouteAre"+
                "a";
              description "A Muliticast OSPF route in an area";
              leaf prefix {
                xr:xr-xml-map "ipv4-ospf_oper:Prefix";
                type inet:ipv4-address-no-zone;
                description "Prefix";
              }
              leaf prefix-length {
                xr:xr-xml-map "ipv4-ospf_oper:PrefixLength";
                type Ospf-prefix-length;
                description "Prefix Length";
              }
              uses OSPF-SH-TOPOLOGY;
            }
          }

          container summary-area-information {
            xr:xr-xml-map "ipv4-ospf_oper:SummaryAreaInformation";
            description "OSPF route summary statistics";
            uses OSPF-SH-ROUTE-SUMMARY;
          }

          container local-route-areas {
            xr:xr-xml-map "ipv4-ospf_oper:LocalRouteAreaTable";
            description "OSPF Local Route Table";

            list local-route-area {
              xr:xr-xml-map "ipv4-ospf_oper:LocalRouteArea";
              description "Local route";
              leaf prefix {
                xr:xr-xml-map "ipv4-ospf_oper:Prefix";
                type inet:ipv4-address-no-zone;
                description "Prefix";
              }
              leaf prefix-length {
                xr:xr-xml-map "ipv4-ospf_oper:PrefixLength";
                type Ospf-prefix-length;
                description "Prefix Length";
              }
              uses OSPF-SH-TOPOLOGY;
            }
          }
          leaf area-id {
            xr:xr-xml-map "ipv4-ospf_oper:AreaID";
            type int32;
            description "Area ID";
          }
        }
      }

      container route-table {
        xr:xr-xml-map "ipv4-ospf_oper:RouteTable";
        description "OSPF Route Table";
        uses ROUTE;
      }

      container external-routes {
        xr:xr-xml-map "ipv4-ospf_oper:ExternalRouteTable";
        description "OSPF External Route Table";

        list external-route {
          xr:xr-xml-map "ipv4-ospf_oper:ExternalRoute";
          description "OSPF external route";
          leaf prefix {
            xr:xr-xml-map "ipv4-ospf_oper:Prefix";
            type inet:ipv4-address-no-zone;
            description "Prefix";
          }
          leaf prefix-length {
            xr:xr-xml-map "ipv4-ospf_oper:PrefixLength";
            type Ospf-prefix-length;
            description "Prefix Length";
          }
          uses OSPF-SH-ROUTE-EXT;
        }
      }
    }
  }

  grouping FAST-REROUTE {
    description "Common node of default-vrf, vrf";

    container fast-reroute {
      xr:xr-xml-map "ipv4-ospf_oper:FastReroute";
      description "Container for FastReroute";

      container topologies {
        xr:xr-xml-map "ipv4-ospf_oper:TopologyTable";
        description "Fast-reroute topology information table";

        list topology {
          xr:xr-xml-map "ipv4-ospf_oper:Topology";
          description "Fast-reroute topology information";
          leaf router-id {
            xr:xr-xml-map "ipv4-ospf_oper:RouterID";
            type inet:ipv4-address-no-zone;
            description "Router ID";
          }
          leaf area-id {
            xr:xr-xml-map "ipv4-ospf_oper:AreaID";
            type int32;
            description "Area ID";
          }
          uses OSPF-SH-IPFRR-TOPO;
        }
      }
    }
  }

  grouping MPLS-TE {
    description "Common node of default-vrf, vrf";

    container mpls-te {
      xr:xr-xml-map "ipv4-ospf_oper:MPLS_TE";
      description "Container for MPLS TE";

      container mpls-te-links {
        xr:xr-xml-map "ipv4-ospf_oper:MPLS_TELinkTable";
        description "MPLS TE link information table";

        list mpls-te-link {
          xr:xr-xml-map "ipv4-ospf_oper:MPLS_TELink";
          key "area-id";
          description "MPLS TE link information";
          leaf area-id {
            xr:xr-xml-map "ipv4-ospf_oper:AreaID";
            type int32;
            description "Area ID";
          }
          uses OSPF-SH-MPLS;
        }
      }

      container mpls-te-fragments {
        xr:xr-xml-map "ipv4-ospf_oper:MPLS_TEFragmentTable";
        description "MPLS TE Fragment information table";

        list mpls-te-fragment {
          xr:xr-xml-map "ipv4-ospf_oper:MPLS_TEFragment";
          key "area-id";
          description "MPLS TE Fragment";
          leaf area-id {
            xr:xr-xml-map "ipv4-ospf_oper:AreaID";
            type int32;
            description "Area ID";
          }
          uses OSPF-SH-MPLS;
        }
      }
    }
  }

  grouping FLOOD-LIST-TABLE {
    description "Common node of default-vrf, vrf, area";

    container floods {
      xr:xr-xml-map "ipv4-ospf_oper:FloodListTable";
      description "Flood list table";

      list flood {
        xr:xr-xml-map "ipv4-ospf_oper:FloodList";
        key "interface-name";
        description "Flooding information for a specific interface";
        leaf interface-name {
          xr:xr-xml-map "ipv4-ospf_oper:InterfaceName";
          type xr:Interface-name;
          description "Interface name";
        }
        uses OSPF-SH-FLOOD-LIST;
      }
    }
  }

  grouping SUMMARY-PREFIX-TABLE {
    description "Common node of default-vrf, vrf";

    container summary-prefixes {
      xr:xr-xml-map "ipv4-ospf_oper:SummaryPrefixTable";
      description "Summary prefix table";

      list summary-prefix {
        xr:xr-xml-map "ipv4-ospf_oper:SummaryPrefix";
        description "Summary prefix information";
        leaf prefix {
          xr:xr-xml-map "ipv4-ospf_oper:Prefix";
          type inet:ipv4-address-no-zone;
          description "Summary Prefix";
        }
        leaf netmask {
          xr:xr-xml-map "ipv4-ospf_oper:Netmask";
          type inet:ipv4-address-no-zone;
          description "Summary Mask";
        }
        uses OSPF-SH-SUMMARY-ADDRESS;
      }
    }
  }

  grouping NEIGHBOR-DETAIL-TABLE {
    description "Common node of adjacency-information, area";

    container neighbor-details {
      xr:xr-xml-map "ipv4-ospf_oper:NeighborDetailTable";
      description "Neighbor detail table";

      list neighbor-detail {
        xr:xr-xml-map "ipv4-ospf_oper:NeighborDetail";
        description "A single neighbor's detail information";
        leaf interface-name {
          xr:xr-xml-map "ipv4-ospf_oper:InterfaceName";
          type xr:Interface-name;
          description "Interface name";
        }
        leaf neighbor-address {
          xr:xr-xml-map "ipv4-ospf_oper:NeighborAddress";
          type inet:ipv4-address-no-zone;
          description "Neighbor address";
        }
        uses OSPF-SH-NEIGHBOR-DETAIL;
      }
    }
  }

  grouping REQUEST-LIST-TABLE {
    description "Common node of adjacency-information, area";

    container requests {
      xr:xr-xml-map "ipv4-ospf_oper:RequestListTable";
      description "Request List table";

      list request {
        xr:xr-xml-map "ipv4-ospf_oper:RequestList";
        description "Request list for a particular adjacency";
        leaf interface-name {
          xr:xr-xml-map "ipv4-ospf_oper:InterfaceName";
          type xr:Interface-name;
          description "Interface";
        }
        leaf neighbor-address {
          xr:xr-xml-map "ipv4-ospf_oper:NeighborAddress";
          type inet:ipv4-address-no-zone;
          description "Neighbor address";
        }
        uses OSPF-SH-REQUEST-LIST;
      }
    }
  }

  grouping INTERFACE-TABLE {
    description "Common node of interface-information, area";

    container interfaces {
      xr:xr-xml-map "ipv4-ospf_oper:InterfaceTable";
      description "OSPF Interface Table";

      list interface {
        xr:xr-xml-map "ipv4-ospf_oper:Interface";
        key "interface-name";
        description "OSPF interface information";
        leaf interface-name {
          xr:xr-xml-map "ipv4-ospf_oper:InterfaceName";
          type xr:Interface-name;
          description "Interface name";
        }
        uses OSPF-SH-INTERFACE;
      }
    }
  }

  grouping INTERFACE-BRIEF-TABLE {
    description "Common node of interface-information, area";

    container interface-briefs {
      xr:xr-xml-map "ipv4-ospf_oper:InterfaceBriefTable";
      description "OSPF Interface Brief Table";

      list interface-brief {
        xr:xr-xml-map "ipv4-ospf_oper:InterfaceBrief";
        key "interface-name";
        description "OSPF interface brief information";
        leaf interface-name {
          xr:xr-xml-map "ipv4-ospf_oper:InterfaceName";
          type xr:Interface-name;
          description "Interface";
        }
        uses OSPF-SH-IF-BRIEF;
      }
    }
  }

  grouping DATABASE {
    description "Common node of default-vrf, vrf";

    container database {
      xr:xr-xml-map "ipv4-ospf_oper:Database";
      description "OSPF Link State Database";

      container database-areas {
        xr:xr-xml-map "ipv4-ospf_oper:DatabaseAreaTable";
        description "Per-Area view of Link state database";

        list database-area {
          xr:xr-xml-map "ipv4-ospf_oper:DatabaseArea";
          key "area-id";
          description "Per-Area Link State Database data";
          leaf area-id {
            xr:xr-xml-map "ipv4-ospf_oper:AreaID";
            type int32;
            description "Area ID";
          }
          uses LSA-TABLE;
          uses LSA-SUMMARY-TABLE;
        }
      }

      container database-summaries {
        xr:xr-xml-map "ipv4-ospf_oper:DatabaseSummaryTable";
        description "Link State database summary table";

        list database-summary {
          xr:xr-xml-map "ipv4-ospf_oper:DatabaseSummary";
          key "area-id";
          description
            "Link State Database summary for a particular
            area";
          leaf area-id {
            xr:xr-xml-map "ipv4-ospf_oper:AreaID";
            type int32;
            description "Area ID";
          }
          uses OSPF-SH-DB-AREA-SUM;
        }
      }

      container database-summary-as {
        xr:xr-xml-map "ipv4-ospf_oper:DatabaseSummaryAS";
        description "Link State Database summary for the AS";
        uses OSPF-SH-DB-AS-SUM;
      }
      uses LSA-TABLE;
      uses LSA-SUMMARY-TABLE;
    }
  }

  grouping INTERFACE-INFORMATION {
    description "Common node of default-vrf, vrf";

    container interface-information {
      xr:xr-xml-map "ipv4-ospf_oper:InterfaceInformation";
      description "Container for OSPF Interfaces/links";

      container virtual-links {
        xr:xr-xml-map "ipv4-ospf_oper:VirtualLinkTable";
        description "Virtual Link table";

        list virtual-link {
          xr:xr-xml-map "ipv4-ospf_oper:VirtualLink";
          key "virtual-link-name";
          description "Information for one Virtual link";
          leaf virtual-link-name {
            xr:xr-xml-map "ipv4-ospf_oper:VirtualLinkName";
            type xr:Cisco-ios-xr-string;
            description "Virtual link";
          }
          uses OSPF-SH-VIRTUAL-LINKS;
        }
      }
      uses INTERFACE-BRIEF-TABLE;
      uses INTERFACE-TABLE;
    }
  }

  grouping NEIGHBOR-TABLE {
    description "Common node of adjacency-information, area";

    container neighbors {
      xr:xr-xml-map "ipv4-ospf_oper:NeighborTable";
      description "Neighbor table";

      list neighbor {
        xr:xr-xml-map "ipv4-ospf_oper:Neighbor";
        description "Neighbor information";
        leaf interface-name {
          xr:xr-xml-map "ipv4-ospf_oper:InterfaceName";
          type xr:Interface-name;
          description "Interface name";
        }
        leaf neighbor-address {
          xr:xr-xml-map "ipv4-ospf_oper:NeighborAddress";
          type inet:ipv4-address-no-zone;
          description "Neighbor address";
        }
        uses OSPF-SH-NEIGHBOR;
      }
    }
  }

  grouping LSA-TABLE {
    description "Common node of database-area, database";

    container lsas {
      xr:xr-xml-map "ipv4-ospf_oper:LSATable";
      description "Link State Database Table";

      list lsa {
        xr:xr-xml-map "ipv4-ospf_oper:LSA";
        description "Link State Advertisement information";
        leaf area-id {
          xr:xr-xml-map "ipv4-ospf_oper:AreaID";
          type int32;
          description "Area ID";
        }
        leaf ls-type {
          xr:xr-xml-map "ipv4-ospf_oper:LSType";
          type Ospf-ls;
          description "Link state type";
        }
        leaf ls-id {
          xr:xr-xml-map "ipv4-ospf_oper:LS_ID";
          type inet:ipv4-address-no-zone;
          description "Link state ID";
        }
        leaf advertising-router {
          xr:xr-xml-map "ipv4-ospf_oper:AdvertisingRouter";
          type inet:ipv4-address-no-zone;
          description "Advertising Router ID";
        }
        leaf interface-name {
          xr:xr-xml-map "ipv4-ospf_oper:InterfaceName";
          type xr:Interface-name;
          description "InterfaceName";
        }
        uses OSPF-SH-DATABASE-DETAIL;
      }
    }
  }

  container ospf {
    xr:xr-xml-map "ipv4-ospf_oper:OSPF";
    config false;
    description "OSPF operational data";

    container processes {
      xr:xr-xml-map "ipv4-ospf_oper:ProcessTable";
      description "Table for each process";

      list process {
        xr:xr-xml-map "ipv4-ospf_oper:Process";
        key "process-name";
        description
          "Operational data for a particular OSPF process";

        container vrfs {
          xr:xr-xml-map "ipv4-ospf_oper:VRFTable";
          description "Table for each VRF";

          list vrf {
            xr:xr-xml-map "ipv4-ospf_oper:VRF";
            key "vrf-name";
            description
              "Operational data for a particular VRF
              (instance) in the OSPF process";

            container interface-vrf-information {
              xr:xr-xml-map "ipv4-ospf_oper:InterfaceVRFInformation";
              description
                "Container for OSPF Interfaces/links under a
                VRF";

              container sham-links {
                xr:xr-xml-map "ipv4-ospf_oper:ShamLinkTable";
                description "Sham Link table";

                list sham-link {
                  xr:xr-xml-map "ipv4-ospf_oper:ShamLink";
                  key "sham-link-name";
                  description "Information for one Sham link";
                  leaf sham-link-name {
                    xr:xr-xml-map "ipv4-ospf_oper:ShamLinkName";
                    type xr:Cisco-ios-xr-string;
                    description "Sham link";
                  }
                  uses OSPF-SH-SHAM-LINKS;
                }
              }
            }
            leaf vrf-name {
              xr:xr-xml-map "ipv4-ospf_oper:VRFName";
              type xr:Cisco-ios-xr-string;
              description "VRF Name";
            }
            uses FLOOD-LIST-TABLE;
            uses MPLS-TE;
            uses ADJACENCY-INFORMATION;
            uses ROUTE-INFORMATION;
            uses INTERFACE-INFORMATION;
            uses BORDER-ROUTER-TABLE;
            uses PROCESS-INFORMATION;
            uses AREA-TABLE;
            uses DATABASE;
            uses SUMMARY-PREFIX-TABLE;
            uses OSPF-SUMMARY;
            uses FAST-REROUTE;
          }
        }

        container default-vrf {
          xr:xr-xml-map "ipv4-ospf_oper:DefaultVRF";
          description
            "Operational data for the default VRF
            (instance) in the OSPF process";
          uses FLOOD-LIST-TABLE;
          uses MPLS-TE;
          uses ADJACENCY-INFORMATION;
          uses ROUTE-INFORMATION;
          uses INTERFACE-INFORMATION;
          uses BORDER-ROUTER-TABLE;
          uses PROCESS-INFORMATION;
          uses AREA-TABLE;
          uses DATABASE;
          uses SUMMARY-PREFIX-TABLE;
          uses OSPF-SUMMARY;
          uses FAST-REROUTE;
        }
        leaf process-name {
          xr:xr-xml-map "ipv4-ospf_oper:ProcessName";
          type xr:Cisco-ios-xr-string;
          description "OSPF process";
        }
      }
    }
  }
}
