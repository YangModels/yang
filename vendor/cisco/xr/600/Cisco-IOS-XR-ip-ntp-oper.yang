module Cisco-IOS-XR-ip-ntp-oper {

  /*** NAMESPACE / PREFIX DEFINITION ***/

  namespace "http://cisco.com/ns/yang/Cisco-IOS-XR-ip-ntp-oper";


  prefix "ip-ntp-oper";

  /*** LINKAGE (IMPORTS / INCLUDES) ***/

  import Cisco-IOS-XR-types { prefix "xr"; }

  include Cisco-IOS-XR-ip-ntp-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ip-ntp package operational data.

     This module contains definitions
     for the following management objects:
       ntp: NTP operational data

     Copyright (c) 2013-2015 by Cisco Systems, Inc.
     All rights reserved.";

  revision "2015-11-09" {
    description
      "IOS XR 6.0 revision.";
  }


  container ntp {
    xr:xr-xml-map "ip_ntp_oper:NTP";
    config false;
    description "NTP operational data";

    container nodes {
      xr:xr-xml-map "ip_ntp_oper:NodeTable";
      description "Node-specific NTP operational data";

      list node {
        xr:xr-xml-map "ip_ntp_oper:Node";
        key "node";
        description "NTP operational data for a particular node";

        container associations-detail {
          xr:xr-xml-map "ip_ntp_oper:AssociationsDetail";
          description "NTP Associations Detail information";
          uses NTP-EDM-ASSOC-DETAIL-RESULT;
        }

        container status {
          xr:xr-xml-map "ip_ntp_oper:Status";
          description "Status of NTP peer(s)";
          uses NTP-EDM-STATUS-RESULT;
        }

        container associations {
          xr:xr-xml-map "ip_ntp_oper:Associations";
          description "NTP Associations information";
          uses NTP-EDM-ASSOC-SUMMARY-RESULT;
        }
        leaf node {
          xr:xr-xml-map "ip_ntp_oper:Node";
          type xr:Node-id;
          description "The node identifier";
        }
      }
    }
  }
}
