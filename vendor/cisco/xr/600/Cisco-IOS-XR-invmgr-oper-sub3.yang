submodule Cisco-IOS-XR-invmgr-oper-sub3 {

  belongs-to Cisco-IOS-XR-invmgr-oper {
    prefix Cisco-IOS-XR-invmgr-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR invmgr package operational data.

     Copyright (c) 2013-2015 by Cisco Systems, Inc.
     All rights reserved.";

  revision "2015-11-09" {
    description
      "IOS XR 6.0 revision.";
  }


  grouping ENVMON-THRESHOLD-INFO {
    description "ENVMON threshold Info";
    leaf threshold-severity {
      xr:xr-xml-map "envmon:ThresholdSeverity";
      type uint32;
      description "Indicates minor, major, critical severities";
    }
    leaf threshold-relation {
      xr:xr-xml-map "envmon:ThresholdRelation";
      type uint32;
      description
        "Indicates relation between sensor value and
        threshold";
    }
    leaf threshold-value {
      xr:xr-xml-map "envmon:ThresholdValue";
      type uint32;
      description "Value of the configured threshold";
    }
    leaf threshold-evaluation {
      xr:xr-xml-map "envmon:ThresholdEvaluation";
      type boolean;
      description
        "Indicates the result of the most recent
        evaluation of the thresholD";
    }
    leaf threshold-notification-enabled {
      xr:xr-xml-map "envmon:ThresholdNotificationEnabled";
      type boolean;
      description
        "Indicates whether or not a notification should
        result, in case of threshold violation";
    }
  }

  grouping ENVMON-SENSOR-INFO {
    description "ENVMON sensor Info";
    leaf field-validity-bitmap {
      xr:xr-xml-map "envmon:FieldValidityBitmap";
      type uint32;
      description "Sensor valid bitmap";
    }
    leaf device-description {
      xr:xr-xml-map "envmon:DeviceDescription";
      type string {
        length "0..50";
      }
      description "Device Name";
    }
    leaf units {
      xr:xr-xml-map "envmon:Units";
      type string {
        length "0..50";
      }
      description "Units of variable being read";
    }
    leaf device-id {
      xr:xr-xml-map "envmon:DeviceId";
      type uint32;
      description "Identifier for this device";
    }
    leaf value {
      xr:xr-xml-map "envmon:Value";
      type uint32;
      description "Current reading of sensor";
    }
    leaf alarm-type {
      xr:xr-xml-map "envmon:AlarmType";
      type uint32;
      description "Indicates threshold violation";
    }
    leaf data-type {
      xr:xr-xml-map "envmon:DataType";
      type uint32;
      description "Sensor data type enums";
    }
    leaf scale {
      xr:xr-xml-map "envmon:Scale";
      type uint32;
      description "Sensor scale enums";
    }
    leaf precision {
      xr:xr-xml-map "envmon:Precision";
      type uint32;
      description "Sensor precision range";
    }
    leaf status {
      xr:xr-xml-map "envmon:Status";
      type uint32;
      description "Sensor operation state enums";
    }
    leaf age-time-stamp {
      xr:xr-xml-map "envmon:AgeTimeStamp";
      type uint32;
      description
        "Age of the sensor value; set to the current time
        if directly access the value from sensor";
    }
    leaf update-rate {
      xr:xr-xml-map "envmon:UpdateRate";
      type uint32;
      description
        "Sensor value update rate;set to 0 if sensor
        value is updated and evaluated immediately";
    }
  }
}
