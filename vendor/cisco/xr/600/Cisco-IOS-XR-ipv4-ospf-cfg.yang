module Cisco-IOS-XR-ipv4-ospf-cfg {

  /*** NAMESPACE / PREFIX DEFINITION ***/

  namespace "http://cisco.com/ns/yang/Cisco-IOS-XR-ipv4-ospf-cfg";


  prefix "ipv4-ospf-cfg";

  /*** LINKAGE (IMPORTS / INCLUDES) ***/

  import ietf-inet-types { prefix "inet"; }

  import Cisco-IOS-XR-types { prefix "xr"; }

  import Cisco-IOS-XR-snmp-agent-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ipv4-ospf package configuration.

     This module contains definitions
     for the following management objects:
       ospf: OSPF configuration data

     This YANG module augments the
       Cisco-IOS-XR-snmp-agent-cfg
     module with configuration data.

     Copyright (c) 2013-2015 by Cisco Systems, Inc.
     All rights reserved.";

  revision "2015-11-09" {
    description
      "IOS XR 6.0 revision.";
  }

  typedef Ospf-sub-address-family {
    type enumeration {
      enum unicast {
        value 1;
        description "Unicast";
      }
    }
    description "Ospf sub address family";
  }
  typedef Ospf-network {
    type enumeration {
      enum broadcast {
        value 1;
        description "Broadcast";
      }
      enum non-broadcast {
        value 2;
        description "NonBroadcast";
      }
      enum point-to-point {
        value 3;
        description "Point to Point";
      }
      enum point-to-multipoint {
        value 4;
        description "Point to Multipoint";
      }
      enum non-broadcast-point-to-multipoint {
        value 5;
        description "NonBroadcast Point to Multipoint";
      }
    }
    description "Ospf network";
  }
  typedef Ospf-authentication {
    type enumeration {
      enum none {
        value 0;
        description "No Authentication";
      }
      enum plain {
        value 1;
        description "Plain Text Authentication";
      }
      enum md5 {
        value 2;
        description "MD5 Message Digest";
      }
    }
    description "Ospf authentication";
  }
  typedef Ospf-eigrp-route {
    type enumeration {
      enum internal {
        value 0;
        description "EIGRP Internal Type";
      }
      enum external {
        value 1;
        description "EIGRP External Type";
      }
    }
    description "Ospf eigrp route";
  }
  typedef Ospf-sid {
    type enumeration {
      enum index {
        value 0;
        description "Index";
      }
      enum absolute {
        value 1;
        description "Absolute";
      }
    }
    description "Ospf sid";
  }
  typedef Ospf-link-state-metric {
    type enumeration {
      enum type1 {
        value 1;
        description "Type 1 External";
      }
      enum type2 {
        value 2;
        description "Type 2 External";
      }
    }
    description "Ospf link state metric";
  }
  typedef Ospf-keychain-auth {
    type enumeration {
      enum none {
        value 0;
        description "No Keychain Authentication";
      }
      enum keychain {
        value 3;
        description "Keychain Authentication";
      }
    }
    description "Ospf keychain auth";
  }
  typedef Ospf-fast-reroute-tiebreakers {
    type enumeration {
      enum downstream {
        value 0;
        description "Downstream";
      }
      enum line-card-disjoint {
        value 1;
        description "LC Disjoint";
      }
      enum lowest-metric {
        value 2;
        description "Lowest metric";
      }
      enum node-protect {
        value 3;
        description "Node protection";
      }
      enum primary-path {
        value 4;
        description "Primary path";
      }
      enum secondary-path {
        value 5;
        description "Secondar path";
      }
      enum srlg-disjoint {
        value 6;
        description "SRLG";
      }
    }
    description "Ospf fast reroute tiebreakers";
  }
  typedef Ospf-uloop-avoidance {
    type enumeration {
      enum protected {
        value 1;
        description "Protected prefixes only";
      }
      enum all {
        value 2;
        description "All prefixes";
      }
    }
    description "Ospf uloop avoidance";
  }
  typedef Ospf-shutdown {
    type enumeration {
      enum full {
        value 1;
        description "Full graceful shutdown";
      }
      enum hostmode {
        value 2;
        description "Enter host only mode";
      }
      enum onreload {
        value 3;
        description "Full graceful shutdown post reload";
      }
    }
    description "Ospf shutdown";
  }
  typedef Ospf-domain-id {
    type enumeration {
      enum type0005 {
        value 5;
        description "Type 0x0005";
      }
      enum type0105 {
        value 261;
        description "Type 0x0105";
      }
      enum type0205 {
        value 517;
        description "Type 0x0205";
      }
      enum type8005 {
        value 32773;
        description "Type 0x8005";
      }
    }
    description "Ospf domain id";
  }
  typedef Ospf-frr-rlfa-tunnel {
    type enumeration {
      enum none {
        value 0;
        description "Disabled";
      }
      enum mpls-ldp {
        value 1;
        description "MPLS LDP";
      }
    }
    description "Ospf frr rlfa tunnel";
  }
  typedef Ospf-log-adj {
    type enumeration {
      enum brief {
        value 0;
        description "Limited output";
      }
      enum detail {
        value 1;
        description "Verbose output";
      }
      enum suppress {
        value 2;
        description "No output";
      }
    }
    description "Ospf log adj";
  }
  typedef Ospf-fast-reroute {
    type enumeration {
      enum none {
        value 0;
        description "None";
      }
      enum per-link {
        value 1;
        description "Per link";
      }
      enum per-prefix {
        value 2;
        description "Per prefix";
      }
    }
    description "Ospf fast reroute";
  }
  typedef Ospf-cisco-nsf {
    type enumeration {
      enum always {
        value 1;
        description "Do not require all neighbors to run NSF";
      }
      enum require-nsf-neighbors {
        value 2;
        description "Require all neighbors to run NSF";
      }
    }
    description "Ospf cisco nsf";
  }
  typedef Ospf-redist-lsa {
    type enumeration {
      enum summary {
        value 3;
        description "Type 3 (summary) LSA";
      }
      enum external {
        value 5;
        description "Type 5 (external) LSA";
      }
    }
    description "Ospf redist lsa";
  }
  typedef Ospf-dist-list-protocol {
    type enumeration {
      enum all {
        value 0;
        description "Default";
      }
      enum connected {
        value 1;
        description "Connected Routes";
      }
      enum static {
        value 3;
        description "Static Routes";
      }
      enum bgp {
        value 4;
        description "BGP";
      }
      enum ospf {
        value 7;
        description "OSPF";
      }
      enum dagr {
        value 9;
        description "DAGR";
      }
    }
    description "Ospf dist list protocol";
  }
  typedef Bfd-enable-mode {
    type enumeration {
      enum disable {
        value 0;
        description "Disable Mode - Prevent inheritance";
      }
      enum default {
        value 1;
        description "Default Mode - Default BFD behavior";
      }
      enum strict {
        value 2;
        description
          "Strict Mode - Hold down adj until BFD sesion up";
      }
    }
    description "Bfd enable mode";
  }
  typedef Ospf-segment-routing-forwarding {
    type enumeration {
      enum disable {
        value 0;
        description "Disable";
      }
      enum mpls {
        value 1;
        description "Mpls";
      }
    }
    description "Ospf segment routing forwarding";
  }
  typedef Ospf-ietf-nsf {
    type enumeration {
      enum all {
        value 3;
        description "Use IETF NSF in planned and unplanned cases";
      }
    }
    description "Ospf ietf nsf";
  }
  typedef Nsr {
    type enumeration {
      enum true {
        value 1;
        description "Enable non-stop routing";
      }
      enum false {
        value 2;
        description "Disable non-stop routing";
      }
    }
    description "Nsr";
  }
  typedef Ospf-redist-protocol {
    type enumeration {
      enum all {
        value 0;
        description "Default";
      }
      enum connected {
        value 1;
        description "Connected Routes";
      }
      enum static {
        value 3;
        description "Static Routes";
      }
      enum bgp {
        value 4;
        description "BGP";
      }
      enum rip {
        value 5;
        description "RIP";
      }
      enum isis {
        value 6;
        description "ISIS";
      }
      enum ospf {
        value 7;
        description "OSPF";
      }
      enum eigrp {
        value 8;
        description "EIGRP";
      }
      enum dagr {
        value 9;
        description "DAGR";
      }
      enum subscriber {
        value 10;
        description "Subscriber Routes";
      }
      enum application {
        value 11;
        description "Application Routes";
      }
      enum mobile {
        value 12;
        description "Mobile Routes";
      }
    }
    description "Ospf redist protocol";
  }
  typedef Ospf-route-level {
    type enumeration {
      enum type1 {
        value 1;
        description "Type 1 only";
      }
      enum type2 {
        value 2;
        description "Type 2 only";
      }
      enum type1-and2 {
        value 3;
        description "Both Type 1 and Type 2";
      }
    }
    description "Ospf route level";
  }
  typedef Ospf-ietf-nsf-support {
    type enumeration {
      enum never {
        value 0;
        description "Do not perform IETF NSF helper role";
      }
    }
    description "Ospf ietf nsf support";
  }
  typedef Ospf-segment-routing {
    type enumeration {
      enum disable {
        value 0;
        description "Disable";
      }
      enum mpls {
        value 1;
        description "Mpls";
      }
    }
    description "Ospf segment routing";
  }
  typedef Ospf-address-family {
    type enumeration {
      enum ipv4 {
        value 1;
        description "IPv4";
      }
    }
    description "Ospf address family";
  }
  typedef Ospf-fast-reroute-priority {
    type enumeration {
      enum critical {
        value 0;
        description "Critical";
      }
      enum high {
        value 2;
        description "High";
      }
      enum medium {
        value 4;
        description "Medium";
      }
      enum low {
        value 6;
        description "low";
      }
    }
    description "Ospf fast reroute priority";
  }

  grouping DISTANCE {
    description "Common node of default-vrf, vrf";

    container distance {
      xr:xr-xml-map "ipv4-ospf_cfg:Distance";
      description "Administrative distance configuration";

      container ospf-distance {
        xr:xr-xml-map "ipv4-ospf_cfg:OSPFDistance";
        description "OSPF distance configuration";
        leaf intra-area {
          xr:xr-xml-map "ipv4-ospf_cfg:IntraArea";
          type uint32 {
            range "1..255";
          }
          default "110";
          description "Distance for intra-area routes";
        }
        leaf inter-area {
          xr:xr-xml-map "ipv4-ospf_cfg:InterArea";
          type uint32 {
            range "1..255";
          }
          default "110";
          description "Distance for inter-area routes";
        }
        leaf external-routes {
          xr:xr-xml-map "ipv4-ospf_cfg:ExternalRoutes";
          type uint32 {
            range "1..255";
          }
          default "110";
          description
            "Distance for external type 5 and type 7 routes";
        }
      }

      container ip-distances {
        xr:xr-xml-map "ipv4-ospf_cfg:IPDistanceTable";
        description
          "IP specific administrative distance
          configuration";

        list ip-distance {
          xr:xr-xml-map "ipv4-ospf_cfg:IPDistance";
          key "address wildcard";
          description
            "Administrative distance configuration for a
            particular IP address";
          leaf address {
            xr:xr-xml-map "ipv4-ospf_cfg:Address";
            type inet:ipv4-address-no-zone;
            description "IP source address";
          }
          leaf wildcard {
            xr:xr-xml-map "ipv4-ospf_cfg:Wildcard";
            type inet:ipv4-address-no-zone;
            description "IP wild card bits -- inverted mask";
          }
          leaf distance {
            xr:xr-xml-map "ipv4-ospf_cfg:Distance";
            type uint32 {
              range "1..255";
            }
            default "110";
            description "Administrative distance";
          }
          leaf access-list-name {
            xr:xr-xml-map "ipv4-ospf_cfg:AccessListName";
            type string;
            description "Access Control List name";
          }
        }
      }
      leaf admin-distance {
        xr:xr-xml-map "ipv4-ospf_cfg:AdminDistance";
        xr:xr-cli-map "ospf <string> vrf <string> distance <number>"+
          " ";
        type uint32 {
          range "1..255";
        }
        default "110";
        description "Define an administrative distance";
      }
    }
  }

  grouping MAX-METRIC {
    description "Common node of default-vrf, vrf";

    container max-metric {
      xr:xr-xml-map "ipv4-ospf_cfg:MaxMetric";
      description "Set maximum metric configuration";

      container max-metric-on-proc-restart {
        xr:xr-xml-map "ipv4-ospf_cfg:MaxMetricOnProcRestart";
        description
          "Set maximum metric on-proc-restart
          configuration";
        leaf wait-for-bgp {
          xr:xr-xml-map "ipv4-ospf_cfg:WaitForBGP";
          type boolean;
          description
            "Let BGP decide when to originate router-LSA
            with normal metric";
        }
        leaf startup-max {
          xr:xr-xml-map "ipv4-ospf_cfg:StartupMax";
          type uint32 {
            range "5..86400";
          }
          units "second";
          description
            "Time in seconds to originate router-LSA with
            max-metric";
        }
        leaf include-stub {
          xr:xr-xml-map "ipv4-ospf_cfg:IncludeStub";
          type boolean;
          description
            "Set maximum metric for stub links in
            router-LSAs";
        }
        leaf summary-lsa {
          xr:xr-xml-map "ipv4-ospf_cfg:SummaryLSA";
          type boolean;
          description
            "Override summary-lsa metric with max-metric
            value";
        }
        leaf summary-lsa-maximum-metric {
          xr:xr-xml-map "ipv4-ospf_cfg:SummaryLSAMaximumMetric";
          type uint32 {
            range "1..16777215";
          }
          description
            "Overriding metric in summary-LSAs (default
            16711680)";
        }
        leaf external-lsa {
          xr:xr-xml-map "ipv4-ospf_cfg:ExternalLSA";
          type boolean;
          description
            "Override external-lsa metric with max-metric
            value";
        }
        leaf external-lsa-maximum-metric {
          xr:xr-xml-map "ipv4-ospf_cfg:ExternalLSAMaximumMetric";
          type uint32 {
            range "1..16777215";
          }
          description
            "Overriding metric in external-LSAs (default
            16711680)";
        }
      }

      container max-metric-on-startup {
        xr:xr-xml-map "ipv4-ospf_cfg:MaxMetricOnStartup";
        description "Set maximum metric on-startup configuration";
        leaf wait-for-bgp {
          xr:xr-xml-map "ipv4-ospf_cfg:WaitForBGP";
          type boolean;
          description
            "Let BGP decide when to originate router-LSA
            with normal metric";
        }
        leaf startup-max {
          xr:xr-xml-map "ipv4-ospf_cfg:StartupMax";
          type uint32 {
            range "5..86400";
          }
          units "second";
          description
            "Time in seconds to originate router-LSA with
            max-metric";
        }
        leaf include-stub {
          xr:xr-xml-map "ipv4-ospf_cfg:IncludeStub";
          type boolean;
          description
            "Set maximum metric for stub links in
            router-LSAs";
        }
        leaf summary-lsa {
          xr:xr-xml-map "ipv4-ospf_cfg:SummaryLSA";
          type boolean;
          description
            "Override summary-lsa metric with max-metric
            value";
        }
        leaf summary-lsa-maximum-metric {
          xr:xr-xml-map "ipv4-ospf_cfg:SummaryLSAMaximumMetric";
          type uint32 {
            range "1..16777215";
          }
          description
            "Overriding metric in summary-LSAs (default
            16711680)";
        }
        leaf external-lsa {
          xr:xr-xml-map "ipv4-ospf_cfg:ExternalLSA";
          type boolean;
          description
            "Override external-lsa metric with max-metric
            value";
        }
        leaf external-lsa-maximum-metric {
          xr:xr-xml-map "ipv4-ospf_cfg:ExternalLSAMaximumMetric";
          type uint32 {
            range "1..16777215";
          }
          description
            "Overriding metric in external-LSAs (default
            16711680)";
        }
      }

      container max-metric-on-proc-migration {
        xr:xr-xml-map "ipv4-ospf_cfg:MaxMetricOnProcMigration";
        description
          "Set maximum metric on-proc-migration
          configuration";
        leaf wait-for-bgp {
          xr:xr-xml-map "ipv4-ospf_cfg:WaitForBGP";
          type boolean;
          description
            "Let BGP decide when to originate router-LSA
            with normal metric";
        }
        leaf startup-max {
          xr:xr-xml-map "ipv4-ospf_cfg:StartupMax";
          type uint32 {
            range "5..86400";
          }
          units "second";
          description
            "Time in seconds to originate router-LSA with
            max-metric";
        }
        leaf include-stub {
          xr:xr-xml-map "ipv4-ospf_cfg:IncludeStub";
          type boolean;
          description
            "Set maximum metric for stub links in
            router-LSAs";
        }
        leaf summary-lsa {
          xr:xr-xml-map "ipv4-ospf_cfg:SummaryLSA";
          type boolean;
          description
            "Override summary-lsa metric with max-metric
            value";
        }
        leaf summary-lsa-maximum-metric {
          xr:xr-xml-map "ipv4-ospf_cfg:SummaryLSAMaximumMetric";
          type uint32 {
            range "1..16777215";
          }
          description
            "Overriding metric in summary-LSAs (default
            16711680)";
        }
        leaf external-lsa {
          xr:xr-xml-map "ipv4-ospf_cfg:ExternalLSA";
          type boolean;
          description
            "Override external-lsa metric with max-metric
            value";
        }
        leaf external-lsa-maximum-metric {
          xr:xr-xml-map "ipv4-ospf_cfg:ExternalLSAMaximumMetric";
          type uint32 {
            range "1..16777215";
          }
          description
            "Overriding metric in external-LSAs (default
            16711680)";
        }
      }

      container max-metric-always {
        xr:xr-xml-map "ipv4-ospf_cfg:MaxMetricAlways";
        description "Set maximum metric always configuration";
        leaf include-stub {
          xr:xr-xml-map "ipv4-ospf_cfg:IncludeStub";
          type boolean;
          description
            "Set maximum metric for stub links in
            router-LSAs";
        }
        leaf summary-lsa {
          xr:xr-xml-map "ipv4-ospf_cfg:SummaryLSA";
          type boolean;
          description
            "Override summary-lsa metric with max-metric
            value";
        }
        leaf summary-lsa-maximum-metric {
          xr:xr-xml-map "ipv4-ospf_cfg:SummaryLSAMaximumMetric";
          type uint32 {
            range "1..16777215";
          }
          description
            "Overriding metric in summary-LSAs (default
            16711680)";
        }
        leaf external-lsa {
          xr:xr-xml-map "ipv4-ospf_cfg:ExternalLSA";
          type boolean;
          description
            "Override external-lsa metric with max-metric
            value";
        }
        leaf external-lsa-maximum-metric {
          xr:xr-xml-map "ipv4-ospf_cfg:ExternalLSAMaximumMetric";
          type uint32 {
            range "1..16777215";
          }
          description
            "Overriding metric in external-LSAs (default
            16711680)";
        }
      }

      container max-metric-on-switchover {
        xr:xr-xml-map "ipv4-ospf_cfg:MaxMetricOnSwitchover";
        description
          "Set maximum metric on-switchover configuration";
        leaf wait-for-bgp {
          xr:xr-xml-map "ipv4-ospf_cfg:WaitForBGP";
          type boolean;
          description
            "Let BGP decide when to originate router-LSA
            with normal metric";
        }
        leaf startup-max {
          xr:xr-xml-map "ipv4-ospf_cfg:StartupMax";
          type uint32 {
            range "5..86400";
          }
          units "second";
          description
            "Time in seconds to originate router-LSA with
            max-metric";
        }
        leaf include-stub {
          xr:xr-xml-map "ipv4-ospf_cfg:IncludeStub";
          type boolean;
          description
            "Set maximum metric for stub links in
            router-LSAs";
        }
        leaf summary-lsa {
          xr:xr-xml-map "ipv4-ospf_cfg:SummaryLSA";
          type boolean;
          description
            "Override summary-lsa metric with max-metric
            value";
        }
        leaf summary-lsa-maximum-metric {
          xr:xr-xml-map "ipv4-ospf_cfg:SummaryLSAMaximumMetric";
          type uint32 {
            range "1..16777215";
          }
          description
            "Overriding metric in summary-LSAs (default
            16711680)";
        }
        leaf external-lsa {
          xr:xr-xml-map "ipv4-ospf_cfg:ExternalLSA";
          type boolean;
          description
            "Override external-lsa metric with max-metric
            value";
        }
        leaf external-lsa-maximum-metric {
          xr:xr-xml-map "ipv4-ospf_cfg:ExternalLSAMaximumMetric";
          type uint32 {
            range "1..16777215";
          }
          description
            "Overriding metric in external-LSAs (default
            16711680)";
        }
      }
      leaf max-metric-no-abr-off {
        xr:xr-xml-map "ipv4-ospf_cfg:MaxMetricNoABROff";
        xr:xr-cli-map "ospf <string> vrf <string> max-metric router"+
          "-lsa no-abr-off ";
        type empty;
        description
          "Block ABR-disable mode entry while in
          max-metric mode";
      }
    }
  }

  grouping DEMAND-CIRCUIT {
    description
      "Common node of process-scope, area-scope,
      name-scope";
    leaf demand-circuit {
      xr:xr-xml-map "ipv4-ospf_cfg:DemandCircuit";
      xr:xr-cli-map "ospf <string> vrf <string> demand-circuit enab"+
        "le ";
      type boolean;
      default "false";
      description "Enable/Disable OSPF demand circuit";
    }
  }

  grouping MAXIMUM-INTERFACES {
    description "Common node of default-vrf, vrf";
    leaf maximum-interfaces {
      xr:xr-xml-map "ipv4-ospf_cfg:MaximumInterfaces";
      xr:xr-cli-map "ospf <string> vrf <string> maximum interfaces "+
        "<number> ";
      type uint32 {
        range "1..4294967295";
      }
      default "1024";
      description
        "Max number of interfaces allowed to be
        configured";
    }
  }

  grouping EXCLUDE-INTERFACE-TABLE {
    description "Common node of per-link, per-prefix, ucmp";

    container exclude-interfaces {
      xr:xr-xml-map "ipv4-ospf_cfg:ExcludeInterfaceTable";
      description
        "Fast-reroute per-link/per-prefix or UCMP exclude
        interface configuration";

      list exclude-interface {
        xr:xr-xml-map "ipv4-ospf_cfg:ExcludeInterface";
        xr:xr-cli-map "ospf <string> vrf <string> fast-reroute per-"+
          "link exclude interface <interface> ";
        xr:xr-cli-map "ospf <string> vrf <string> fast-reroute per-"+
          "prefix exclude interface <interface> ";
        xr:xr-cli-map "ospf <string> vrf <string> ucmp exclude inte"+
          "rface <interface> ";
        key "interface-name";
        description
          "Exclude an interface from becoming a backup or
          UCMP";
        leaf interface-name {
          xr:xr-xml-map "ipv4-ospf_cfg:InterfaceName";
          type xr:Interface-name;
          description "Interface";
        }
      }
    }
  }

  grouping RUNNING {
    description
      "Common node of process, area, name-scope,
      virtual-link-scope, sham-link-scope,
      multi-area-interface-scope";
    leaf running {
      xr:xr-xml-map "ipv4-ospf_cfg:Running";
      type empty;
      description "Enable routing on an IP network";
    }
  }

  grouping TRANSMIT-DELAY {
    description
      "Common node of process-scope, area-scope,
      name-scope, virtual-link-scope, sham-link-scope,
      multi-area-interface-scope";
    leaf transmit-delay {
      xr:xr-xml-map "ipv4-ospf_cfg:TransmitDelay";
      xr:xr-cli-map "ospf <string> vrf <string> transmit-delay <num"+
        "ber> ";
      type uint32 {
        range "1..65535";
      }
      units "second";
      default "1";
      description "Number of seconds to delay transmission of LSAs";
    }
  }

  grouping NO-OPAQUE {
    description "Common node of default-vrf, vrf";
    leaf no-opaque {
      xr:xr-xml-map "ipv4-ospf_cfg:NoOpaque";
      xr:xr-cli-map "ospf <string> vrf <string> capability opaque e"+
        "nable ";
      type empty;
      description "Disable opaque LSAs";
    }
  }

  grouping COST-FALLBACK {
    description
      "Common node of process-scope, area-scope,
      name-scope, multi-area-interface-scope";

    container cost-fallback {
      xr:xr-xml-map "ipv4-ospf_cfg:CostFallback";
      description "Interface fallback cost";
      leaf cost {
        xr:xr-xml-map "ipv4-ospf_cfg:Cost";
        type uint32 {
          range "1..65535";
        }
        description "Fallback cost of link";
      }
      leaf threshold {
        xr:xr-xml-map "ipv4-ospf_cfg:Threshold";
        type uint32 {
          range "1..4294967";
        }
        description "Bandwidth threshold";
      }
    }
  }

  grouping SEGMENT-ROUTING {
    description "Common node of process-scope, area";
    leaf segment-routing {
      xr:xr-xml-map "ipv4-ospf_cfg:SegmentRouting";
      xr:xr-cli-map "ospf <string> vrf <string> segment-routing (mp"+
        "ls)|(disable) ";
      type Ospf-segment-routing;
      description
        "segment-routing configuration Applicable only in
        Default VRF";
    }
  }

  grouping SUMMARY-IN {
    description "Common node of process-scope, area";
    leaf summary-in {
      xr:xr-xml-map "ipv4-ospf_cfg:SummaryIn";
      xr:xr-cli-map "ospf <string> vrf <string> summary-in enable ";
      type boolean;
      description
        "Enable/Disable an OSPF area to advertise
        external prefixes into this area as summary";
    }
  }

  grouping LDP-AUTO-CONFIG {
    description
      "Common node of process-scope, area-scope,
      name-scope";
    leaf ldp-auto-config {
      xr:xr-xml-map "ipv4-ospf_cfg:LDPAutoConfig";
      xr:xr-cli-map "ospf <string> vrf <string> mpls ldp auto-confi"+
        "g ";
      type empty;
      description "Enable MPLS LDP Auto Config";
    }
  }

  grouping PASSIVE {
    description
      "Common node of process-scope, area-scope,
      name-scope, multi-area-interface-scope";
    leaf passive {
      xr:xr-xml-map "ipv4-ospf_cfg:Passive";
      xr:xr-cli-map "ospf <string> vrf <string> passive enable ";
      type boolean;
      default "false";
      description
        "When enabled, prevent sending HELLO packets over
        link";
    }
  }

  grouping AREA-TABLE {
    description "Common node of default-vrf, vrf";

    container area-addresses {
      xr:xr-xml-map "ipv4-ospf_cfg:AreaTable";
      description "Area configuration";

      grouping AREA-CONTENT {
        description "AREA CONTENT";

        container virtual-link-scopes {
          xr:xr-xml-map "ipv4-ospf_cfg:VirtualLinkScopeTable";
          description "Virtual Link scope configurations";

          list virtual-link-scope {
            xr:xr-xml-map "ipv4-ospf_cfg:VirtualLinkScope";
            key "address";
            description "Virtual Link configuration";
            leaf address {
              xr:xr-xml-map "ipv4-ospf_cfg:Address";
              type inet:ipv4-address-no-zone;
              description "Router ID of virtual link neighbor";
            }
            uses AUTHENTICATION;
            uses HELLO-INTERVAL;
            uses TRANSMIT-DELAY;
            uses DEAD-INTERVAL-MINIMAL;
            uses RETRANSMIT-INTERVAL;
            uses RUNNING;
          }
        }

        container sham-link-scopes {
          xr:xr-xml-map "ipv4-ospf_cfg:ShamLinkScopeTable";
          description "Sham Link scope configurations";

          list sham-link-scope {
            xr:xr-xml-map "ipv4-ospf_cfg:ShamLinkScope";
            key "source-address destination-address";
            description "Sham Link configuration";
            leaf source {
              xr:xr-xml-map "ipv4-ospf_cfg:Source";
              type inet:ipv4-address-no-zone;
              description
                "Address of the local sham-link endpoint.
                Enter an IP Address";
            }
            leaf source-address {
              xr:xr-xml-map "ipv4-ospf_cfg:SourceAddress";
              type inet:ipv4-address-no-zone;
              description "Address of the local sham-link endpoint";
            }
            leaf destination-address {
              xr:xr-xml-map "ipv4-ospf_cfg:DestinationAddress";
              type inet:ipv4-address-no-zone;
              description
                "Address of the remote sham-link endpoint";
            }
            uses COST;
            uses AUTHENTICATION;
            uses HELLO-INTERVAL;
            uses TRANSMIT-DELAY;
            uses DEAD-INTERVAL-MINIMAL;
            uses RETRANSMIT-INTERVAL;
            uses RUNNING;
          }
        }

        container area-scope {
          xr:xr-xml-map "ipv4-ospf_cfg:AreaScope";
          description "Area scope configuration";
          uses DISTRIBUTE-LIST;
          uses COST;
          uses BFD;
          uses MTU-IGNORE;
          uses AUTHENTICATION;
          uses LDP-SYNC-IGP-SHORTCUTS;
          uses LDP-AUTO-CONFIG;
          uses SECURITY;
          uses FAST-REROUTE;
          uses NETWORK-TYPE;
          uses HELLO-INTERVAL;
          uses LOOPBACK-STUB-NETWORK;
          uses PREFIX-SUPPRESSION-SECONDARY;
          uses DEMAND-CIRCUIT;
          uses PASSIVE;
          uses TRANSMIT-DELAY;
          uses PACKET-SIZE;
          uses LDP-SYNC;
          uses DATABASE-FILTER;
          uses DEAD-INTERVAL-MINIMAL;
          uses LINK-DOWN-FAST-DETECT;
          uses SEGMENT-ROUTING-FORWARDING;
          uses RETRANSMIT-INTERVAL;
          uses IPV4-OSPF-CFG-PRIORITY;
          uses FLOOD-REDUCTION;
          uses COST-FALLBACK;
        }

        container name-scopes {
          xr:xr-xml-map "ipv4-ospf_cfg:NameScopeTable";
          description "Name scope configurations";

          list name-scope {
            xr:xr-xml-map "ipv4-ospf_cfg:NameScope";
            key "interface-name";
            description "Name scope configuration";

            container prefix-sid {
              xr:xr-xml-map "ipv4-ospf_cfg:PrefixSid";
              presence "Indicates a prefix-sid node is configured.";
              description "Prefix SID";
              leaf sid-value {
                xr:xr-xml-map "ipv4-ospf_cfg:SidValue";
                type uint32 {
                  range "0..1048575";
                }
                mandatory true;
                description "SID value";
              }
              leaf explicit-null {
                xr:xr-xml-map "ipv4-ospf_cfg:Explicit-null";
                type boolean;
                default "false";
                description
                  "Force Penultimate Hop To Send Explicit-Null
                  Label";
              }
              leaf type {
                xr:xr-xml-map "ipv4-ospf_cfg:Type";
                type Ospf-sid;
                mandatory true;
                description "OSPF SID Type";
              }
            }
            leaf interface-name {
              xr:xr-xml-map "ipv4-ospf_cfg:InterfaceName";
              type xr:Interface-name;
              description "Name of Interface to configure";
            }
            uses DISTRIBUTE-LIST;
            uses COST;
            uses BFD;
            uses MTU-IGNORE;
            uses AUTHENTICATION;
            uses LDP-SYNC-IGP-SHORTCUTS;
            uses LDP-AUTO-CONFIG;
            uses SECURITY;
            uses FAST-REROUTE;
            uses NEIGHBOR-TABLE;
            uses NETWORK-TYPE;
            uses HELLO-INTERVAL;
            uses LOOPBACK-STUB-NETWORK;
            uses PREFIX-SUPPRESSION-SECONDARY;
            uses DEMAND-CIRCUIT;
            uses PASSIVE;
            uses TRANSMIT-DELAY;
            uses PACKET-SIZE;
            uses LDP-SYNC;
            uses DATABASE-FILTER;
            uses DEAD-INTERVAL-MINIMAL;
            uses LINK-DOWN-FAST-DETECT;
            uses SEGMENT-ROUTING-FORWARDING;
            uses RETRANSMIT-INTERVAL;
            uses IPV4-OSPF-CFG-PRIORITY;
            uses FLOOD-REDUCTION;
            uses COST-FALLBACK;
            uses RUNNING;
          }
        }

        container multi-area-interface-scopes {
          xr:xr-xml-map "ipv4-ospf_cfg:MultiAreaInterfaceScopeTable";
          description "Multi Area Interface scope configurations";

          list multi-area-interface-scope {
            xr:xr-xml-map "ipv4-ospf_cfg:MultiAreaInterfaceScope";
            key "interface-name";
            description "Multi Area Interface configuration";
            leaf interface-name {
              xr:xr-xml-map "ipv4-ospf_cfg:InterfaceName";
              type xr:Interface-name;
              description
                "Name of Multi Area Interface to configure";
            }
            uses DISTRIBUTE-LIST;
            uses COST;
            uses MTU-IGNORE;
            uses AUTHENTICATION;
            uses NEIGHBOR-TABLE;
            uses HELLO-INTERVAL;
            uses PASSIVE;
            uses TRANSMIT-DELAY;
            uses PACKET-SIZE;
            uses DATABASE-FILTER;
            uses DEAD-INTERVAL-MINIMAL;
            uses RETRANSMIT-INTERVAL;
            uses COST-FALLBACK;
            uses RUNNING;
          }
        }

        container area-ranges {
          xr:xr-xml-map "ipv4-ospf_cfg:AreaRangeTable";
          description
            "Summarize routes matching address/mask (border
            routers only)";

          list area-range {
            xr:xr-xml-map "ipv4-ospf_cfg:AreaRange";
            key "address netmask";
            description "Ordering index";
            leaf not-advertise {
              xr:xr-xml-map "ipv4-ospf_cfg:NotAdvertise";
              type boolean;
              description "Do not advertise this range";
            }
            leaf address {
              xr:xr-xml-map "ipv4-ospf_cfg:Address";
              type inet:ipv4-address-no-zone;
              description "IP address to match";
            }
            leaf netmask {
              xr:xr-xml-map "ipv4-ospf_cfg:Netmask";
              type inet:ipv4-address-no-zone;
              description "IP netmask for address";
            }
          }
        }

        container nssa {
          xr:xr-xml-map "ipv4-ospf_cfg:NSSA";
          description "Specify area as a NSSA area";
          leaf no-redistribution {
            xr:xr-xml-map "ipv4-ospf_cfg:NoRedistribution";
            type boolean;
            default "false";
            description "No redistribution into this NSSA area";
          }
          leaf default-info-originate {
            xr:xr-xml-map "ipv4-ospf_cfg:DefaultInfoOriginate";
            type boolean;
            default "false";
            description "Originate Type 7 default into NSSA area";
          }
          leaf no-summary {
            xr:xr-xml-map "ipv4-ospf_cfg:NoSummary";
            type boolean;
            default "false";
            description "Do not send summary LSA into NSSA";
          }
          leaf nssa-def-metric {
            xr:xr-xml-map "ipv4-ospf_cfg:NSSADefMetric";
            type uint32 {
              range "1..16777214";
            }
            description "OSPF default metric";
          }
          leaf metric-type {
            xr:xr-xml-map "ipv4-ospf_cfg:MetricType";
            type Ospf-link-state-metric;
            default "type2";
            description "OSPF External metric type";
          }
        }
        leaf route-policy-in {
          xr:xr-xml-map "ipv4-ospf_cfg:RoutePolicyIn";
          type string;
          description
            "Configure a route policy for inbound type-3
            lsa filtering";
        }
        leaf default-cost {
          xr:xr-xml-map "ipv4-ospf_cfg:DefaultCost";
          type uint32 {
            range "1..16777215";
          }
          default "1";
          description
            "Set the summary default-cost of a NSSA/stub
            area";
        }
        leaf route-policy-out {
          xr:xr-xml-map "ipv4-ospf_cfg:RoutePolicyOut";
          type string;
          description
            "Configure a route policy for outbound type-3
            lsa filtering";
        }
        leaf stub {
          xr:xr-xml-map "ipv4-ospf_cfg:Stub";
          type boolean;
          description
            "Specify the area as a stub area (send summary
            LSA stub area)";
        }
        leaf mpls-traffic-eng {
          xr:xr-xml-map "ipv4-ospf_cfg:MPLSTrafficEng";
          type empty;
          description
            "Configure an OSPF area to run MPLS Traffic
            Engineering";
        }
        uses EXTERNAL-OUT;
        uses SUMMARY-IN;
        uses SEGMENT-ROUTING;
        uses RUNNING;
      }

      list area-address {
        key "address";
        description "Configuration for a particular area";
        leaf address {
          xr:xr-xml-map "ipv4-ospf_cfg:Address";
          type inet:ipv4-address-no-zone;
          description "Area ID if in IP address format";
        }
        uses AREA-CONTENT;
      }

      list area-area-id {
        key "area-id";
        description "Configuration for a particular area";
        leaf area-id {
          xr:xr-xml-map "ipv4-ospf_cfg:AreaID";
          type int32;
          description "Area ID if in integer format";
        }
        uses AREA-CONTENT;
      }
    }
  }

  grouping AUTO-COST {
    description "Common node of default-vrf, vrf";

    container auto-cost {
      xr:xr-xml-map "ipv4-ospf_cfg:AutoCost";
      description "Controls automatic cost based on bandwidth";
      leaf disable {
        xr:xr-xml-map "ipv4-ospf_cfg:Disable";
        type boolean;
        default "false";
        description "Disabling auto costing";
      }
      leaf bandwidth {
        xr:xr-xml-map "ipv4-ospf_cfg:Bandwidth";
        type uint32 {
          range "1..4294967";
        }
        units "Mbit/s";
        default "100";
        description
          "The reference bandwidth in terms of Mbits per
          second";
      }
    }
  }

  grouping TIMERS {
    description "Common node of default-vrf, vrf";

    container timers {
      xr:xr-xml-map "ipv4-ospf_cfg:Timers";
      description "Adjust routing timers";

      container spf-timer {
        xr:xr-xml-map "ipv4-ospf_cfg:SPFTimer";
        description "OSPF SPF timers (in milliseconds)";
        leaf initial-delay {
          xr:xr-xml-map "ipv4-ospf_cfg:InitialDelay";
          type uint32 {
            range "1..600000";
          }
          units "millisecond";
          default "5000";
          description "Number of milliseconds before first SPF run";
        }
        leaf backoff-increment {
          xr:xr-xml-map "ipv4-ospf_cfg:BackoffIncrement";
          type uint32 {
            range "1..600000";
          }
          units "millisecond";
          default "10000";
          description
            "Number of milliseconds delay between
            successive SPF runs";
        }
        leaf max-delay {
          xr:xr-xml-map "ipv4-ospf_cfg:MaxDelay";
          type uint32 {
            range "1..600000";
          }
          units "millisecond";
          default "10000";
          description
            "Max number of milliseconds between consecutive
            SPF calculations";
        }
      }

      container lsa-generation-timer {
        xr:xr-xml-map "ipv4-ospf_cfg:LSAGenerationTimer";
        description "OSPF LSA timers (in milliseconds)";
        leaf initial-delay {
          xr:xr-xml-map "ipv4-ospf_cfg:InitialDelay";
          type uint32 {
            range "0..600000";
          }
          units "millisecond";
          default "50";
          description
            "Number of milliseconds before generating first
            LSA";
        }
        leaf backoff-increment {
          xr:xr-xml-map "ipv4-ospf_cfg:BackoffIncrement";
          type uint32 {
            range "1..600000";
          }
          units "millisecond";
          default "200";
          description
            "Number of milliseconds delay between
            successive LSA builds";
        }
        leaf max-delay {
          xr:xr-xml-map "ipv4-ospf_cfg:MaxDelay";
          type uint32 {
            range "1..600000";
          }
          units "millisecond";
          default "200";
          description
            "Max number of milliseconds between consecutive
            LSA builds ";
        }
      }
      leaf lsa-pacing-flood {
        xr:xr-xml-map "ipv4-ospf_cfg:LSAPacingFlood";
        xr:xr-cli-map "ospf <string> vrf <string> timers pacing flo"+
          "od <number> ";
        type uint32 {
          range "5..100";
        }
        units "second";
        description
          "Seconds between group of LSAs being refreshed
          or maxaged";
      }
      leaf fast-reroute-timer {
        xr:xr-xml-map "ipv4-ospf_cfg:FastRerouteTimer";
        xr:xr-cli-map "ospf <string> vrf <string> timers throttle f"+
          "ast-reroute <number> ";
        type uint32 {
          range "50..600000";
        }
        units "millisecond";
        default "500";
        description
          "Number of ms between end of SPF and start of
          IPFRR computation";
      }
      leaf lsa-refresh {
        xr:xr-xml-map "ipv4-ospf_cfg:LSARefresh";
        xr:xr-cli-map "ospf <string> vrf <string> timers lsa refres"+
          "h <number> ";
        type uint32 {
          range "1800..2700";
        }
        units "second";
        default "1800";
        description
          "How often self-originated LSAs should be
          refreshed";
      }
      leaf lsa-group-pacing {
        xr:xr-xml-map "ipv4-ospf_cfg:LSAGroupPacing";
        xr:xr-cli-map "ospf <string> vrf <string> timers lsa-group-"+
          "pacing <number> ";
        type uint32 {
          range "10..1800";
        }
        units "second";
        default "240";
        description
          "LSA group pacing timer (Seconds between group
          of LSAs being refreshed or maxaged)";
      }
      leaf lsa-min-arrival {
        xr:xr-xml-map "ipv4-ospf_cfg:LSAMinArrival";
        xr:xr-cli-map "ospf <string> vrf <string> timers lsa-arriva"+
          "l <number> ";
        type uint32 {
          range "0..600000";
        }
        units "millisecond";
        default "100";
        description
          "MinLSArrival timer (minimum interval in
          milliseconds between accepting the same LSA)";
      }
    }
  }

  grouping NETWORK-TYPE {
    description
      "Common node of process-scope, area-scope,
      name-scope";
    leaf network-type {
      xr:xr-xml-map "ipv4-ospf_cfg:NetworkType";
      xr:xr-cli-map "ospf <string> vrf <string> network (broadcast)"+
        "|(non-broadcast)|(point-to-point)|(point-to-multipoint [no"+
        "n-broadcast]) ";
      type Ospf-network;
      description "Type of attached network";
    }
  }

  grouping REDISTRIBUTION {
    description "Common node of default-vrf, vrf";

    container redistribution {
      xr:xr-xml-map "ipv4-ospf_cfg:Redistribution";
      description "Redistribute configurations";

      container redistributes {
        xr:xr-xml-map "ipv4-ospf_cfg:RedistributeTable";
        description
          "Redistribute information from another routing
          protocol";

        list redistribute {
          xr:xr-xml-map "ipv4-ospf_cfg:Redistribute";
          must "connected-or-static-or-dagr-or-subscriber-or-mobile"+
            "-or-rip or application-or-isis-or-ospf or bgp or eigrp" {
            description
              "Connected-or-Static-or-DAGR-or-Subscriber-or-Mobile-or-RIP or Application-or-ISIS-or-OSPF or BGP or EIGRP must be present.";
          }
          key "protocol-name";
          description
            "Redistribute information from another routing
            protocol";

          grouping REDISTRIBUTE-CONTENT {
            description "REDISTRIBUTE CONTENT";
            leaf classful {
              xr:xr-xml-map "ipv4-ospf_cfg:Classful";
              type boolean;
              default "false";
              description "Disallow subnetting";
            }
            leaf default-redistributed-route-metric {
              xr:xr-xml-map "ipv4-ospf_cfg:DefaultRedistributedRout"+
                "eMetric";
              type uint32 {
                range "1..16777214";
              }
              description
                "Default metric for routes being
                redistributed into OSPF";
            }
            leaf tag {
              xr:xr-xml-map "ipv4-ospf_cfg:Tag";
              type int32;
              description
                "Set tag for routes redistributed into OSPF";
            }
            leaf metric-type {
              xr:xr-xml-map "ipv4-ospf_cfg:MetricType";
              type Ospf-link-state-metric;
              description "Set OSPF External metric type";
            }
            leaf eigrp-route-type {
              xr:xr-xml-map "ipv4-ospf_cfg:EIGRPRouteType";
              type Ospf-eigrp-route;
              description "EIGRP route type";
            }
            leaf isis-levels {
              xr:xr-xml-map "ipv4-ospf_cfg:ISISLevels";
              type Ospf-route-level;
              description "Levels of ISIS routes";
            }
            leaf ospf-internal {
              xr:xr-xml-map "ipv4-ospf_cfg:OSPFInternal";
              type boolean;
              description "OSPF_Internal route type";
            }
            leaf ospf-external {
              xr:xr-xml-map "ipv4-ospf_cfg:OSPFExternal";
              type Ospf-route-level;
              description "OSPF external route types";
            }
            leaf ospf-nssa-level {
              xr:xr-xml-map "ipv4-ospf_cfg:OSPF_NSSALevel";
              type Ospf-route-level;
              description "OSPF NSSA external route types";
            }
            leaf route-policy-name {
              xr:xr-xml-map "ipv4-ospf_cfg:RoutePolicyName";
              type string;
              description "Routing policy name";
            }
            leaf bgp-preserve-med {
              xr:xr-xml-map "ipv4-ospf_cfg:BGPPreserveMED";
              type boolean;
              description "Preserve MED of BGP routes";
            }
            leaf bgp-preserve-default-info {
              xr:xr-xml-map "ipv4-ospf_cfg:BGPPreserveDefaultInfo";
              type boolean;
              description
                "Preserve Metric and Metric Type of BGP
                Default Route";
            }
            leaf ospf-redist-lsa-type {
              xr:xr-xml-map "ipv4-ospf_cfg:OSPFRedistLSAType";
              type Ospf-redist-lsa;
              default "external";
              description "LSA type for redistributed routes";
            }
            leaf ospfnssa-only {
              xr:xr-xml-map "ipv4-ospf_cfg:OSPFNSSAOnly";
              type boolean;
              description "Only redistribute to NSSA areas";
            }
          }

          container "connected-or-static-or-dagr-or-subscriber-or"+
            "-mobile-or-rip" {
            xr:xr-cli-map "ospf <string> vrf <string> redistribute "+
              "[connected [instance <string>] [metric <number>|tag "+
              "<number>|metric-type <enum>|lsa-type summary|(subnet"+
              "s)|(classful)|(route-policy (<string>)|(<text>))|(po"+
              "licy (<string>)|(<text>))|nssa-only]|static [metric "+
              "<number>|tag <number>|metric-type <enum>|lsa-type su"+
              "mmary|(subnets)|(classful)|(route-policy (<string>)|"+
              "(<text>))|(policy (<string>)|(<text>))|nssa-only]|da"+
              "gr [metric <number>|tag <number>|metric-type <enum>|"+
              "lsa-type summary|(subnets)|(classful)|(route-policy "+
              "(<string>)|(<text>))|(policy (<string>)|(<text>))|ns"+
              "sa-only]|subscriber [metric <number>|tag <number>|me"+
              "tric-type <enum>|lsa-type summary|(subnets)|(classfu"+
              "l)|(route-policy (<string>)|(<text>))|(policy (<stri"+
              "ng>)|(<text>))|nssa-only]|mobile [metric <number>|ta"+
              "g <number>|metric-type <enum>|lsa-type summary|(subn"+
              "ets)|(classful)|(route-policy (<string>)|(<text>))|("+
              "policy (<string>)|(<text>))|nssa-only]|application <"+
              "string> [metric <number>|tag <number>|metric-type <e"+
              "num>|lsa-type summary|(subnets)|(classful)|(route-po"+
              "licy (<string>)|(<text>))|(policy (<string>)|(<text>"+
              "))|nssa-only]|eigrp <number> [match (internal)|(exte"+
              "rnal)|metric <number>|tag <number>|metric-type <enum"+
              ">|lsa-type summary|(subnets)|(classful)|(route-polic"+
              "y (<string>)|(<text>))|(policy (<string>)|(<text>))|"+
              "nssa-only]|rip [metric <number>|tag <number>|metric-"+
              "type <enum>|lsa-type summary|(subnets)|(classful)|(r"+
              "oute-policy (<string>)|(<text>))|(policy (<string>)|"+
              "(<text>))|nssa-only]|bgp (<number>)|(<number>)|(<num"+
              "ber> <number>) [preserve-med|preserve-bgp-default-in"+
              "fo|metric <number>|tag <number>|metric-type <enum>|l"+
              "sa-type summary|(subnets)|(classful)|(route-policy ("+
              "<string>)|(<text>))|(policy (<string>)|(<text>))|nss"+
              "a-only]|isis <string> [[level-1]|level-2|level-1-2|l"+
              "evel <number>|metric <number>|tag <number>|metric-ty"+
              "pe <enum>|lsa-type summary|(subnets)|(classful)|(rou"+
              "te-policy (<string>)|(<text>))|(policy (<string>)|(<"+
              "text>))|nssa-only]|ospf <string> [match (internal)|("+
              "(external (1)|(2))|(external))|((nssa-external (1)|("+
              "2))|(nssa-external))|metric <number>|tag <number>|me"+
              "tric-type <enum>|lsa-type summary|(subnets)|(classfu"+
              "l)|(route-policy (<string>)|(<text>))|(policy (<stri"+
              "ng>)|(<text>))|nssa-only]] ";
            when "../protocol-name = 'connected' or"+
              " ../protocol-name = 'static' or ../protocol-name ="+
              " 'dagr' or ../protocol-name = 'subscriber' or"+
              " ../protocol-name = 'mobile' or ../protocol-name ="+
              " 'rip'" {
                description
                  "../ProtocolName = Connected or .
                  ./ProtocolName = Static or ../ProtocolName
                  = DAGR or ../ProtocolName = Subscriber or .
                  ./ProtocolName = Mobile or ../ProtocolName
                  = RIP";
            }
            presence "Indicates that this node is configured.";
            description
              "connected or static or dagr or subscriber or
              mobile or rip";
            uses REDISTRIBUTE-CONTENT;
          }
          leaf protocol-name {
            xr:xr-xml-map "ipv4-ospf_cfg:ProtocolName";
            type Ospf-redist-protocol;
            description "Distribute list protocol type";
          }

          list application-or-isis-or-ospf {
            xr:xr-cli-map "ospf <string> vrf <string> redistribute "+
              "[connected [instance <string>] [metric <number>|tag "+
              "<number>|metric-type <enum>|lsa-type summary|(subnet"+
              "s)|(classful)|(route-policy (<string>)|(<text>))|(po"+
              "licy (<string>)|(<text>))|nssa-only]|static [metric "+
              "<number>|tag <number>|metric-type <enum>|lsa-type su"+
              "mmary|(subnets)|(classful)|(route-policy (<string>)|"+
              "(<text>))|(policy (<string>)|(<text>))|nssa-only]|da"+
              "gr [metric <number>|tag <number>|metric-type <enum>|"+
              "lsa-type summary|(subnets)|(classful)|(route-policy "+
              "(<string>)|(<text>))|(policy (<string>)|(<text>))|ns"+
              "sa-only]|subscriber [metric <number>|tag <number>|me"+
              "tric-type <enum>|lsa-type summary|(subnets)|(classfu"+
              "l)|(route-policy (<string>)|(<text>))|(policy (<stri"+
              "ng>)|(<text>))|nssa-only]|mobile [metric <number>|ta"+
              "g <number>|metric-type <enum>|lsa-type summary|(subn"+
              "ets)|(classful)|(route-policy (<string>)|(<text>))|("+
              "policy (<string>)|(<text>))|nssa-only]|application <"+
              "string> [metric <number>|tag <number>|metric-type <e"+
              "num>|lsa-type summary|(subnets)|(classful)|(route-po"+
              "licy (<string>)|(<text>))|(policy (<string>)|(<text>"+
              "))|nssa-only]|eigrp <number> [match (internal)|(exte"+
              "rnal)|metric <number>|tag <number>|metric-type <enum"+
              ">|lsa-type summary|(subnets)|(classful)|(route-polic"+
              "y (<string>)|(<text>))|(policy (<string>)|(<text>))|"+
              "nssa-only]|rip [metric <number>|tag <number>|metric-"+
              "type <enum>|lsa-type summary|(subnets)|(classful)|(r"+
              "oute-policy (<string>)|(<text>))|(policy (<string>)|"+
              "(<text>))|nssa-only]|bgp (<number>)|(<number>)|(<num"+
              "ber> <number>) [preserve-med|preserve-bgp-default-in"+
              "fo|metric <number>|tag <number>|metric-type <enum>|l"+
              "sa-type summary|(subnets)|(classful)|(route-policy ("+
              "<string>)|(<text>))|(policy (<string>)|(<text>))|nss"+
              "a-only]|isis <string> [[level-1]|level-2|level-1-2|l"+
              "evel <number>|metric <number>|tag <number>|metric-ty"+
              "pe <enum>|lsa-type summary|(subnets)|(classful)|(rou"+
              "te-policy (<string>)|(<text>))|(policy (<string>)|(<"+
              "text>))|nssa-only]|ospf <string> [match (internal)|("+
              "(external (1)|(2))|(external))|((nssa-external (1)|("+
              "2))|(nssa-external))|metric <number>|tag <number>|me"+
              "tric-type <enum>|lsa-type summary|(subnets)|(classfu"+
              "l)|(route-policy (<string>)|(<text>))|(policy (<stri"+
              "ng>)|(<text>))|nssa-only]] ";
            when "../protocol-name = 'application' or"+
              " ../protocol-name = 'isis' or ../protocol-name ="+
              " 'ospf'" {
                description
                  "../ProtocolName = Application or .
                  ./ProtocolName = ISIS or ../ProtocolName =
                  OSPF";
            }
            key "instance-name";
            description "application or isis or ospf";
            leaf instance-name {
              xr:xr-xml-map "ipv4-ospf_cfg:InstanceName";
              type xr:Cisco-ios-xr-string;
              description
                "OSPF or ISIS process name or protocol name:
                bgp, eigrp, connected";
            }
            uses REDISTRIBUTE-CONTENT;
          }

          list bgp {
            xr:xr-cli-map "ospf <string> vrf <string> redistribute "+
              "[connected [instance <string>] [metric <number>|tag "+
              "<number>|metric-type <enum>|lsa-type summary|(subnet"+
              "s)|(classful)|(route-policy (<string>)|(<text>))|(po"+
              "licy (<string>)|(<text>))|nssa-only]|static [metric "+
              "<number>|tag <number>|metric-type <enum>|lsa-type su"+
              "mmary|(subnets)|(classful)|(route-policy (<string>)|"+
              "(<text>))|(policy (<string>)|(<text>))|nssa-only]|da"+
              "gr [metric <number>|tag <number>|metric-type <enum>|"+
              "lsa-type summary|(subnets)|(classful)|(route-policy "+
              "(<string>)|(<text>))|(policy (<string>)|(<text>))|ns"+
              "sa-only]|subscriber [metric <number>|tag <number>|me"+
              "tric-type <enum>|lsa-type summary|(subnets)|(classfu"+
              "l)|(route-policy (<string>)|(<text>))|(policy (<stri"+
              "ng>)|(<text>))|nssa-only]|mobile [metric <number>|ta"+
              "g <number>|metric-type <enum>|lsa-type summary|(subn"+
              "ets)|(classful)|(route-policy (<string>)|(<text>))|("+
              "policy (<string>)|(<text>))|nssa-only]|application <"+
              "string> [metric <number>|tag <number>|metric-type <e"+
              "num>|lsa-type summary|(subnets)|(classful)|(route-po"+
              "licy (<string>)|(<text>))|(policy (<string>)|(<text>"+
              "))|nssa-only]|eigrp <number> [match (internal)|(exte"+
              "rnal)|metric <number>|tag <number>|metric-type <enum"+
              ">|lsa-type summary|(subnets)|(classful)|(route-polic"+
              "y (<string>)|(<text>))|(policy (<string>)|(<text>))|"+
              "nssa-only]|rip [metric <number>|tag <number>|metric-"+
              "type <enum>|lsa-type summary|(subnets)|(classful)|(r"+
              "oute-policy (<string>)|(<text>))|(policy (<string>)|"+
              "(<text>))|nssa-only]|bgp (<number>)|(<number>)|(<num"+
              "ber> <number>) [preserve-med|preserve-bgp-default-in"+
              "fo|metric <number>|tag <number>|metric-type <enum>|l"+
              "sa-type summary|(subnets)|(classful)|(route-policy ("+
              "<string>)|(<text>))|(policy (<string>)|(<text>))|nss"+
              "a-only]|isis <string> [[level-1]|level-2|level-1-2|l"+
              "evel <number>|metric <number>|tag <number>|metric-ty"+
              "pe <enum>|lsa-type summary|(subnets)|(classful)|(rou"+
              "te-policy (<string>)|(<text>))|(policy (<string>)|(<"+
              "text>))|nssa-only]|ospf <string> [match (internal)|("+
              "(external (1)|(2))|(external))|((nssa-external (1)|("+
              "2))|(nssa-external))|metric <number>|tag <number>|me"+
              "tric-type <enum>|lsa-type summary|(subnets)|(classfu"+
              "l)|(route-policy (<string>)|(<text>))|(policy (<stri"+
              "ng>)|(<text>))|nssa-only]] ";
            when "../protocol-name = 'bgp'" {
              description "../ProtocolName = BGP";
            }
            key "instance-name as-xx as-yy";
            description "bgp";
            leaf instance-name {
              xr:xr-xml-map "ipv4-ospf_cfg:InstanceName";
              type xr:Cisco-ios-xr-string;
              description
                "OSPF or ISIS process name or protocol name:
                bgp, eigrp, connected";
            }
            leaf as-xx {
              xr:xr-xml-map "ipv4-ospf_cfg:AS_XX";
              type uint32 {
                range "0..65535";
              }
              description
                "First half of BGP AS number in XX.YY format.
                Mandatory if Protocol is BGP and must not be
                specified otherwise. Must be a non-zero
                value if second half is zero.";
            }
            leaf as-yy {
              xr:xr-xml-map "ipv4-ospf_cfg:AS_YY";
              type uint32 {
                range "0..4294967295";
              }
              description
                "Second half of BGP AS number in XX.YY format
                . Mandatory if Protocol is BGP or EIGRP and
                must not be specified otherwise. Must be a
                non-zero value if first half is zero.";
            }
            uses REDISTRIBUTE-CONTENT;
          }

          list eigrp {
            xr:xr-cli-map "ospf <string> vrf <string> redistribute "+
              "[connected [instance <string>] [metric <number>|tag "+
              "<number>|metric-type <enum>|lsa-type summary|(subnet"+
              "s)|(classful)|(route-policy (<string>)|(<text>))|(po"+
              "licy (<string>)|(<text>))|nssa-only]|static [metric "+
              "<number>|tag <number>|metric-type <enum>|lsa-type su"+
              "mmary|(subnets)|(classful)|(route-policy (<string>)|"+
              "(<text>))|(policy (<string>)|(<text>))|nssa-only]|da"+
              "gr [metric <number>|tag <number>|metric-type <enum>|"+
              "lsa-type summary|(subnets)|(classful)|(route-policy "+
              "(<string>)|(<text>))|(policy (<string>)|(<text>))|ns"+
              "sa-only]|subscriber [metric <number>|tag <number>|me"+
              "tric-type <enum>|lsa-type summary|(subnets)|(classfu"+
              "l)|(route-policy (<string>)|(<text>))|(policy (<stri"+
              "ng>)|(<text>))|nssa-only]|mobile [metric <number>|ta"+
              "g <number>|metric-type <enum>|lsa-type summary|(subn"+
              "ets)|(classful)|(route-policy (<string>)|(<text>))|("+
              "policy (<string>)|(<text>))|nssa-only]|application <"+
              "string> [metric <number>|tag <number>|metric-type <e"+
              "num>|lsa-type summary|(subnets)|(classful)|(route-po"+
              "licy (<string>)|(<text>))|(policy (<string>)|(<text>"+
              "))|nssa-only]|eigrp <number> [match (internal)|(exte"+
              "rnal)|metric <number>|tag <number>|metric-type <enum"+
              ">|lsa-type summary|(subnets)|(classful)|(route-polic"+
              "y (<string>)|(<text>))|(policy (<string>)|(<text>))|"+
              "nssa-only]|rip [metric <number>|tag <number>|metric-"+
              "type <enum>|lsa-type summary|(subnets)|(classful)|(r"+
              "oute-policy (<string>)|(<text>))|(policy (<string>)|"+
              "(<text>))|nssa-only]|bgp (<number>)|(<number>)|(<num"+
              "ber> <number>) [preserve-med|preserve-bgp-default-in"+
              "fo|metric <number>|tag <number>|metric-type <enum>|l"+
              "sa-type summary|(subnets)|(classful)|(route-policy ("+
              "<string>)|(<text>))|(policy (<string>)|(<text>))|nss"+
              "a-only]|isis <string> [[level-1]|level-2|level-1-2|l"+
              "evel <number>|metric <number>|tag <number>|metric-ty"+
              "pe <enum>|lsa-type summary|(subnets)|(classful)|(rou"+
              "te-policy (<string>)|(<text>))|(policy (<string>)|(<"+
              "text>))|nssa-only]|ospf <string> [match (internal)|("+
              "(external (1)|(2))|(external))|((nssa-external (1)|("+
              "2))|(nssa-external))|metric <number>|tag <number>|me"+
              "tric-type <enum>|lsa-type summary|(subnets)|(classfu"+
              "l)|(route-policy (<string>)|(<text>))|(policy (<stri"+
              "ng>)|(<text>))|nssa-only]] ";
            when "../protocol-name = 'eigrp'" {
              description "../ProtocolName = EIGRP";
            }
            key "instance-name as-xx";
            description "eigrp";
            leaf instance-name {
              xr:xr-xml-map "ipv4-ospf_cfg:InstanceName";
              type xr:Cisco-ios-xr-string;
              description
                "OSPF or ISIS process name or protocol name:
                bgp, eigrp, connected";
            }
            leaf as-xx {
              xr:xr-xml-map "ipv4-ospf_cfg:AS_XX";
              type uint32 {
                range "0..65535";
              }
              description
                "First half of BGP AS number in XX.YY format.
                Mandatory if Protocol is BGP and must not be
                specified otherwise. Must be a non-zero
                value if second half is zero.";
            }
            uses REDISTRIBUTE-CONTENT;
          }
        }
      }
    }
  }

  grouping EXTERNAL-OUT {
    description "Common node of process-scope, area";
    leaf external-out {
      xr:xr-xml-map "ipv4-ospf_cfg:ExternalOut";
      xr:xr-cli-map "ospf <string> vrf <string> external-out enable"+
        " ";
      type boolean;
      description
        "Enable/Disable an OSPF area to advertise
        intra-area prefixes out of this area as external";
    }
  }

  grouping AF {
    description "Common node of default-vrf, vrf";

    container af {
      xr:xr-xml-map "ipv4-ospf_cfg:AF";
      presence "Indicates a af node is configured.";
      description "OSPF address family";
      leaf af-name {
        xr:xr-xml-map "ipv4-ospf_cfg:AFName";
        type Ospf-address-family;
        mandatory true;
        description "Address family";
      }
      leaf saf-name {
        xr:xr-xml-map "ipv4-ospf_cfg:SAFName";
        type Ospf-sub-address-family;
        description "Sub-Address family";
      }
    }
  }

  grouping DEFAULT-INFORMATION {
    description "Common node of default-vrf, vrf";

    container default-information {
      xr:xr-xml-map "ipv4-ospf_cfg:DefaultInformation";
      description "Control distribution of default information";
      leaf always-advertise {
        xr:xr-xml-map "ipv4-ospf_cfg:AlwaysAdvertise";
        type boolean;
        default "false";
        description "Always advertise default route";
      }
      leaf metric {
        xr:xr-xml-map "ipv4-ospf_cfg:Metric";
        type uint32 {
          range "1..16777214";
        }
        default "1";
        description "OSPF metric";
      }
      leaf metric-type {
        xr:xr-xml-map "ipv4-ospf_cfg:MetricType";
        type Ospf-link-state-metric;
        default "type2";
        description "OSPF External metric type";
      }
      leaf route-policy-name {
        xr:xr-xml-map "ipv4-ospf_cfg:RoutePolicyName";
        type string;
        description "Routing policy name";
      }
    }
  }

  grouping PREFIX-SUPPRESSION-SECONDARY {
    description
      "Common node of process-scope, area-scope,
      name-scope";
    leaf prefix-suppression-secondary {
      xr:xr-xml-map "ipv4-ospf_cfg:PrefixSuppressionSecondary";
      xr:xr-cli-map "ospf <string> vrf <string> prefix-suppression "+
        "secondary-address enable ";
      type boolean;
      default "false";
      description
        "Enable/Disable prefix suppression for secondary
        addresses";
    }
  }

  grouping MAXIMUM-PATHS {
    description "Common node of default-vrf, vrf";
    leaf maximum-paths {
      xr:xr-xml-map "ipv4-ospf_cfg:MaximumPaths";
      xr:xr-cli-map "ospf <string> vrf <string> maximum-paths <numb"+
        "er> ";
      type uint32 {
        range "1..64";
      }
      description
        "Forward packets over multiple paths (number of
        paths)";
    }
  }

  grouping DATABASE-FILTER {
    description
      "Common node of process-scope, area-scope,
      name-scope, multi-area-interface-scope";
    leaf database-filter {
      xr:xr-xml-map "ipv4-ospf_cfg:DatabaseFilter";
      xr:xr-cli-map "ospf <string> vrf <string> database-filter all"+
        " out enable ";
      type boolean;
      default "false";
      description
        "Filter OSPF LSA during synchronization and
        flooding";
    }
  }

  grouping LINK-DOWN-FAST-DETECT {
    description
      "Common node of process-scope, area-scope,
      name-scope";
    leaf link-down-fast-detect {
      xr:xr-xml-map "ipv4-ospf_cfg:LinkDownFastDetect";
      xr:xr-cli-map "ospf <string> vrf <string> link-down fast-dete"+
        "ct ";
      type boolean;
      default "false";
      description
        "Enable/Disable registration for early interface
        down notifications";
    }
  }

  grouping LDP-SYNC-IGP-SHORTCUTS {
    description
      "Common node of process-scope, area-scope,
      name-scope";
    leaf ldp-sync-igp-shortcuts {
      xr:xr-xml-map "ipv4-ospf_cfg:LDPSyncIGPShortcuts";
      xr:xr-cli-map "ospf <string> vrf <string> mpls ldp sync-igp-s"+
        "hortcuts ";
      type boolean;
      description "Enable/Disable MPLS LDP sync for igp-shortcuts";
    }
  }

  grouping MICROLOOP {
    description "Common node of default-vrf, vrf";

    container microloop {
      xr:xr-xml-map "ipv4-ospf_cfg:Microloop";
      description "Microloop configuration";

      container avoidance {
        xr:xr-xml-map "ipv4-ospf_cfg:Avoidance";
        description "Microloop avoidance configuration";
        leaf enable {
          xr:xr-xml-map "ipv4-ospf_cfg:Enable";
          xr:xr-cli-map "ospf <string> vrf <string> microloop avoid"+
            "ance [protected] ";
          type Ospf-uloop-avoidance;
          default "all";
          description
            "MicroLoop avoidance feature enable
            configuration";
        }
        leaf rib-update-delay {
          xr:xr-xml-map "ipv4-ospf_cfg:RibUpdateDelay";
          xr:xr-cli-map "ospf <string> vrf <string> microloop avoid"+
            "ance rib-update-delay <number> ";
          type uint32 {
            range "1..600000";
          }
          units "millisecond";
          default "5000";
          description
            "Delay to introduce between SPF and RIB update
            in msecs";
        }
      }
    }
  }

  grouping DEAD-INTERVAL-MINIMAL {
    description
      "Common node of process-scope, area-scope,
      name-scope, virtual-link-scope, sham-link-scope,
      multi-area-interface-scope";

    container dead-interval-minimal {
      xr:xr-xml-map "ipv4-ospf_cfg:DeadIntervalMinimal";
      description
        "Interval after which a neighbor is declared dead";
      leaf interval {
        xr:xr-xml-map "ipv4-ospf_cfg:Interval";
        type uint32 {
          range "1..65535";
        }
        units "second";
        description
          "Interval size in seconds after which a neighbor
          is declared dead";
      }
      leaf multiplier {
        xr:xr-xml-map "ipv4-ospf_cfg:Multiplier";
        type uint32 {
          range "3..20";
        }
        description "Number of Hellos in one second";
      }
    }
  }

  grouping CANDIDATE-INTERFACE-TABLE {
    description "Common node of per-link, per-prefix";

    container candidate-interfaces {
      xr:xr-xml-map "ipv4-ospf_cfg:CandidateInterfaceTable";
      description
        "Fast-reroute per-link/per-prefix candidate
        interface configuration";

      list candidate-interface {
        xr:xr-xml-map "ipv4-ospf_cfg:CandidateInterface";
        xr:xr-cli-map "ospf <string> vrf <string> fast-reroute per-"+
          "link lfa-candidate interface <interface> ";
        xr:xr-cli-map "ospf <string> vrf <string> fast-reroute per-"+
          "prefix lfa-candidate interface <interface> ";
        key "interface-name";
        description "Candidate backup interface";
        leaf interface-name {
          xr:xr-xml-map "ipv4-ospf_cfg:InterfaceName";
          type xr:Interface-name;
          description "Interface";
        }
      }
    }
  }

  grouping QUEUE {
    description "Common node of default-vrf, vrf";

    container queue {
      xr:xr-xml-map "ipv4-ospf_cfg:Queue";
      description
        "Adjust OSPF input queue sizes and processing
        quantums";
      leaf dispatch-rate-limited-flush {
        xr:xr-xml-map "ipv4-ospf_cfg:DispatchRateLimitedFlush";
        xr:xr-cli-map "ospf <string> vrf <string> queue dispatch fl"+
          "ush-lsa <number> ";
        type uint32 {
          range "30..3000";
        }
        default "150";
        description
          "Maximum number of continuous rate-limited LSAs
          processed for FLUSH";
      }
      leaf limit-high {
        xr:xr-xml-map "ipv4-ospf_cfg:LimitHigh";
        xr:xr-cli-map "ospf <string> vrf <string> queue limit high "+
          "<number> ";
        type uint32 {
          range "1000..30000";
        }
        default "9500";
        description
          "Hello events are dropped when incoming event
          queue exceeds this";
      }
      leaf dispatch-spf-lsa-limit {
        xr:xr-xml-map "ipv4-ospf_cfg:DispatchSPF_LSALimit";
        xr:xr-cli-map "ospf <string> vrf <string> queue dispatch sp"+
          "f-lsa-limit <number> ";
        type uint32 {
          range "30..3000";
        }
        default "150";
        description
          "Maximum number of continuous summary or
          external LSAs processed";
      }
      leaf limit-low {
        xr:xr-xml-map "ipv4-ospf_cfg:LimitLow";
        xr:xr-cli-map "ospf <string> vrf <string> queue limit low <"+
          "number> ";
        type uint32 {
          range "1000..30000";
        }
        default "8000";
        description
          "DBDs/Updates are dropped when incoming event
          queue exceeds this";
      }
      leaf dispatch-rate-limited {
        xr:xr-xml-map "ipv4-ospf_cfg:DispatchRateLimited";
        xr:xr-cli-map "ospf <string> vrf <string> queue dispatch ra"+
          "te-limited-lsa <number> ";
        type uint32 {
          range "30..3000";
        }
        default "150";
        description
          "Maximum number of continuous rate-limited LSAs
          processed";
      }
      leaf limit-medium {
        xr:xr-xml-map "ipv4-ospf_cfg:LimitMedium";
        xr:xr-cli-map "ospf <string> vrf <string> queue limit mediu"+
          "m <number> ";
        type uint32 {
          range "1000..30000";
        }
        default "9000";
        description
          "LSA ACKs are dropped when incoming event queue
          exceeds this";
      }
      leaf dispatch-incoming {
        xr:xr-xml-map "ipv4-ospf_cfg:DispatchIncoming";
        xr:xr-cli-map "ospf <string> vrf <string> queue dispatch in"+
          "coming <number> ";
        type uint32 {
          range "30..3000";
        }
        default "300";
        description
          "Maximum number of continuous incoming
          packet-related events processed";
      }
    }
  }

  grouping AUTHENTICATION {
    description
      "Common node of process-scope, area-scope,
      name-scope, virtual-link-scope, sham-link-scope,
      multi-area-interface-scope";

    container authentication {
      xr:xr-xml-map "ipv4-ospf_cfg:Authentication";
      description "Authentication";

      container type {
        xr:xr-xml-map "ipv4-ospf_cfg:Type";
        description "Authentication type";
        leaf authen-type {
          xr:xr-xml-map "ipv4-ospf_cfg:AuthenType";
          type Ospf-authentication;
          description "Authentication type code ";
        }
        leaf keychain-authen-type {
          xr:xr-xml-map "ipv4-ospf_cfg:KeychainAuthenType";
          type Ospf-keychain-auth;
          description "Keychain authentication type";
        }
        leaf keychain-name {
          xr:xr-xml-map "ipv4-ospf_cfg:KeychainName";
          type string;
          description "Keychain name";
        }
      }

      container message-digest-keies {
        xr:xr-xml-map "ipv4-ospf_cfg:MessageDigestKeyTable";
        description
          "Message digest authentication password (key)
          configurations, first 16 chars used";

        list message-digest-key {
          xr:xr-xml-map "ipv4-ospf_cfg:MessageDigestKey";
          xr:xr-cli-map "ospf <string> vrf <string> message-digest-"+
            "key <number> md5 ([0] <text>)|(clear)|((7)|(encrypted)"+
            " <text>)|(<text>) ";
          key "key-id";
          description
            "Message digest authentication password (key)
            configuration";
          leaf key-id {
            xr:xr-xml-map "ipv4-ospf_cfg:KeyID";
            type uint32 {
              range "1..255";
            }
            description "Key ID";
          }
          leaf password {
            xr:xr-xml-map "ipv4-ospf_cfg:Password";
            type xr:Proprietary-password;
            mandatory true;
            description "Password";
          }
        }
      }
      leaf key {
        xr:xr-xml-map "ipv4-ospf_cfg:Key";
        xr:xr-cli-map "ospf <string> vrf <string> authentication-ke"+
          "y ([0] <text>)|(clear)|((7)|(encrypted) <text>)|(<text>)"+
          " ";
        type xr:Proprietary-password;
        description "Authentication key configuration";
      }
    }
  }

  grouping MAXIMUM-REDISTRIBUTE-PREFIX {
    description "Common node of default-vrf, vrf";

    container maximum-redistribute-prefix {
      xr:xr-xml-map "ipv4-ospf_cfg:MaximumRedistributePrefix";
      description
        "Maximum number of prefixes redistributed into
        OSPF";
      leaf number-of-prefixes {
        xr:xr-xml-map "ipv4-ospf_cfg:NumberOfPrefixes";
        type uint32 {
          range "1..4294967295";
        }
        description "Maximum number of prefixes redistributed";
      }
      leaf threshold {
        xr:xr-xml-map "ipv4-ospf_cfg:Threshold";
        type uint32 {
          range "1..100";
        }
        description
          "Threshold value (%) at which to generate a
          warning msg";
      }
      leaf warning-only {
        xr:xr-xml-map "ipv4-ospf_cfg:WarningOnly";
        type boolean;
        description
          "Only give warning messsage when limit is
          exceeded";
      }
    }
  }

  grouping SEGMENT-ROUTING-FORWARDING {
    description
      "Common node of process-scope, area-scope,
      name-scope";
    leaf segment-routing-forwarding {
      xr:xr-xml-map "ipv4-ospf_cfg:SegmentRoutingForwarding";
      xr:xr-cli-map "ospf <string> vrf <string> segment-routing for"+
        "warding (mpls)|(disable) ";
      type Ospf-segment-routing-forwarding;
      description
        "segment-routing forwarding configuration
        Applicableonly in Default VRF";
    }
  }

  grouping DISTRIBUTE-LIST {
    description
      "Common node of process-scope, area-scope,
      name-scope, multi-area-interface-scope";

    container distribute-list {
      xr:xr-xml-map "ipv4-ospf_cfg:DistributeList";
      must "(access-list-name and not(route-policy-name)) or"+
        " (not(access-list-name) and route-policy-name)" {
        description "Describes valid combinations of leafs";
      }
      presence "enable distribute-list";
      description
        "Filter networks intalled to RIB (disable as ACL
        name means filtering is disabled)";
      leaf access-list-name {
        xr:xr-xml-map "ipv4-ospf_cfg:AccessListName";
        type string;
        description "Access Control List name";
      }
      leaf route-policy-name {
        xr:xr-xml-map "ipv4-ospf_cfg:RoutePolicyName";
        type string;
        description "Route Policy name";
      }
    }
  }

  grouping COST {
    description
      "Common node of process-scope, area-scope,
      name-scope, multi-area-interface-scope,
      sham-link-scope";
    leaf cost {
      xr:xr-xml-map "ipv4-ospf_cfg:Cost";
      xr:xr-cli-map "ospf <string> vrf <string> cost <number> ";
      type uint32 {
        range "1..65535";
      }
      description "Interface cost";
    }
  }

  grouping PACKET-SIZE {
    description
      "Common node of process-scope, area-scope,
      name-scope, multi-area-interface-scope";
    leaf packet-size {
      xr:xr-xml-map "ipv4-ospf_cfg:PacketSize";
      xr:xr-cli-map "ospf <string> vrf <string> packet-size <number"+
        "> ";
      type uint32 {
        range "576..10000";
      }
      description "Customize size of OSPF packets upto MTU";
    }
  }

  grouping FAST-REROUTE {
    description
      "Common node of process-scope, area-scope,
      name-scope";

    container fast-reroute {
      xr:xr-xml-map "ipv4-ospf_cfg:FastReroute";
      description "Fast-reroute configuration";

      container per-link {
        xr:xr-xml-map "ipv4-ospf_cfg:PerLink";
        description "Fast-reroute per-link configuration";
        uses CANDIDATE-INTERFACE-TABLE;
        uses FAST-REROUTE-USE-CANDIDATE-ONLY;
        uses EXCLUDE-INTERFACE-TABLE;
      }

      container per-prefix {
        xr:xr-xml-map "ipv4-ospf_cfg:PerPrefix";
        description "Fast-reroute per-prefix configuration";

        container remote-lfa {
          xr:xr-xml-map "ipv4-ospf_cfg:RemoteLFA";
          description "Remote LFA configuration";
          leaf tunnel {
            xr:xr-xml-map "ipv4-ospf_cfg:Tunnel";
            xr:xr-cli-map "ospf <string> vrf <string> fast-reroute "+
              "per-prefix remote-lfa (tunnel [mpls-ldp])|(disable) ";
            type Ospf-frr-rlfa-tunnel;
            description "Enable/Disable remote LFA computation";
          }
          leaf maximum-cost {
            xr:xr-xml-map "ipv4-ospf_cfg:MaximumCost";
            xr:xr-cli-map "ospf <string> vrf <string> fast-reroute "+
              "per-prefix remote-lfa maximum-cost <number> ";
            type uint32 {
              range "1..4294967295";
            }
            description "Maximum path cost to remote LFA";
          }
        }
        leaf topology-independent-lfa {
          xr:xr-xml-map "ipv4-ospf_cfg:TopologyIndependentLFA";
          xr:xr-cli-map "ospf <string> vrf <string> fast-reroute pe"+
            "r-prefix ti-lfa [enable|disable] ";
          type boolean;
          description "Topology Independet LFA configuration";
        }
        uses CANDIDATE-INTERFACE-TABLE;
        uses FAST-REROUTE-USE-CANDIDATE-ONLY;
        uses EXCLUDE-INTERFACE-TABLE;
      }
      leaf fast-reroute-enable {
        xr:xr-xml-map "ipv4-ospf_cfg:FastRerouteEnable";
        xr:xr-cli-map "ospf <string> vrf <string> fast-reroute (per"+
          "-link [enable|disable])|(per-prefix)|(disable) ";
        type Ospf-fast-reroute;
        description
          "Enable/Disable Fast-reroute per-link or
          per-prefix";
      }
    }
  }

  grouping IPV4-OSPF-INSTANCE-CFG-FAST-REROUTE {
    description "Common node of default-vrf, vrf";

    container fast-reroute {
      xr:xr-xml-map "ipv4-ospf_instance_cfg:FastReroute";
      description "Fast-reroute instance scoped parameters";

      container per-link {
        xr:xr-xml-map "ipv4-ospf_instance_cfg:PerLink";
        description "Fast-reroute per-link global configuration";
        uses PRIORITY;
      }

      container per-prefix {
        xr:xr-xml-map "ipv4-ospf_instance_cfg:PerPrefix";
        description "Fast-reroute per-prefix global configuration";

        container tiebreakers {
          xr:xr-xml-map "ipv4-ospf_instance_cfg:TiebreakerTable";
          description "Fast-reroute tiebreakers configurations";

          list tiebreaker {
            xr:xr-xml-map "ipv4-ospf_instance_cfg:Tiebreaker";
            xr:xr-cli-map "ospf <string> vrf <string> fast-reroute "+
              "per-prefix tiebreaker (downstream)|(lc-disjoint)|(lo"+
              "west-backup-metric)|(node-protecting)|(primary-path)"+
              "|(secondary-path)|(srlg-disjoint) index <number> ";
            key "tiebreaker-type";
            description "Fast-reroute tiebreakers configuration";
            leaf tiebreaker-type {
              xr:xr-xml-map "ipv4-ospf_instance_cfg:TiebreakerType";
              type Ospf-fast-reroute-tiebreakers;
              description "Tiebreaker type";
            }
            leaf tiebreaker-index {
              xr:xr-xml-map "ipv4-ospf_instance_cfg:TiebreakerIndex";
              type uint32 {
                range "1..255";
              }
              mandatory true;
              description "Index value for a tiebreaker";
            }
          }
        }
        leaf load-sharing-disable {
          xr:xr-xml-map "ipv4-ospf_instance_cfg:LoadSharingDisable";
          xr:xr-cli-map "ospf <string> vrf <string> fast-reroute pe"+
            "r-prefix load-sharing disable ";
          type empty;
          description
            "Disable load sharing between multiple backups";
        }
        uses PRIORITY;
      }
    }
  }

  grouping SUMMARY-PREFIX-TABLE {
    description "Common node of default-vrf, vrf";

    container summary-prefixes {
      xr:xr-xml-map "ipv4-ospf_cfg:SummaryPrefixTable";
      description "Configure IP prefix summary";

      grouping SUMMARY-PREFIX-CONTENT {
        description "Content grouping.";
        leaf not-advertise {
          xr:xr-xml-map "ipv4-ospf_cfg:NotAdvertise";
          type boolean;
          default "false";
          description
            "Do not advertise when translating OSPF type-7
            LSA";
        }
        leaf tag {
          xr:xr-xml-map "ipv4-ospf_cfg:Tag";
          type int32;
          description "32-bit tag value";
        }
      }

      container summary-prefix-data {
        xr:xr-xml-map "ipv4-ospf_cfg:SummaryPrefix";
        xr:xr-cli-map "ospf <string> vrf <string> (summary-address)"+
          "|(summary-prefix) <IP address mask> [not-advertise|tag <"+
          "number>] ";
        description "Data container.";
        uses SUMMARY-PREFIX-CONTENT;
      }

      list prefix-and-netmask {
        xr:xr-xml-map "ipv4-ospf_cfg:SummaryPrefix";
        xr:xr-cli-map "ospf <string> vrf <string> (summary-address)"+
          "|(summary-prefix) <IP address mask> [not-advertise|tag <"+
          "number>] ";
        key "prefix netmask";
        description "keys: prefix, netmask";
        leaf prefix {
          xr:xr-xml-map "ipv4-ospf_cfg:Prefix";
          type inet:ipv4-address-no-zone;
          description "IP summary prefix";
        }
        leaf netmask {
          xr:xr-xml-map "ipv4-ospf_cfg:Netmask";
          type inet:ipv4-address-no-zone;
          description "Summary netmask";
        }
        uses SUMMARY-PREFIX-CONTENT;
      }

      list prefix {
        xr:xr-xml-map "ipv4-ospf_cfg:SummaryPrefix";
        xr:xr-cli-map "ospf <string> vrf <string> (summary-address)"+
          "|(summary-prefix) <IP address mask> [not-advertise|tag <"+
          "number>] ";
        key "prefix";
        description "keys: prefix";
        leaf prefix {
          xr:xr-xml-map "ipv4-ospf_cfg:Prefix";
          type inet:ipv4-address-no-zone;
          description "IP summary prefix";
        }
        uses SUMMARY-PREFIX-CONTENT;
      }

      list netmask {
        xr:xr-xml-map "ipv4-ospf_cfg:SummaryPrefix";
        xr:xr-cli-map "ospf <string> vrf <string> (summary-address)"+
          "|(summary-prefix) <IP address mask> [not-advertise|tag <"+
          "number>] ";
        key "netmask";
        description "keys: netmask";
        leaf netmask {
          xr:xr-xml-map "ipv4-ospf_cfg:Netmask";
          type inet:ipv4-address-no-zone;
          description "Summary netmask";
        }
        uses SUMMARY-PREFIX-CONTENT;
      }
    }
  }

  grouping SECURITY {
    description
      "Common node of process-scope, area-scope,
      name-scope";

    container security {
      xr:xr-xml-map "ipv4-ospf_cfg:Security";
      description
        "Container class for security related
        configuration parameters";

      container ttl {
        xr:xr-xml-map "ipv4-ospf_cfg:TTL";
        description "Enabling turns on TTL security";
        leaf enable {
          xr:xr-xml-map "ipv4-ospf_cfg:Enable";
          type boolean;
          description "Enable TTL security";
        }
        leaf hop-count {
          xr:xr-xml-map "ipv4-ospf_cfg:HopCount";
          type uint32 {
            range "1..254";
          }
          description "Hop count";
        }
      }
    }
  }

  grouping HELLO-INTERVAL {
    description
      "Common node of process-scope, area-scope,
      name-scope, virtual-link-scope, sham-link-scope,
      multi-area-interface-scope";
    leaf hello-interval {
      xr:xr-xml-map "ipv4-ospf_cfg:HelloInterval";
      xr:xr-cli-map "ospf <string> vrf <string> hello-interval <num"+
        "ber> ";
      type uint32 {
        range "1..65535";
      }
      units "second";
      description "Interval between HELLO packets in seconds";
    }
  }

  grouping ADJACENCY-CHANGES {
    description "Common node of default-vrf, vrf";
    leaf adjacency-changes {
      xr:xr-xml-map "ipv4-ospf_cfg:AdjacencyChanges";
      xr:xr-cli-map "ospf <string> vrf <string> log adjacency chang"+
        "es (detail)|(disable) ";
      type Ospf-log-adj;
      description "Log changes in adjacency state";
    }
  }

  grouping PROCESS-SCOPE {
    description "Common node of default-vrf, vrf";

    container process-scope {
      xr:xr-xml-map "ipv4-ospf_cfg:ProcessScope";
      description "Process scope configuration";

      container srgb {
        xr:xr-xml-map "ipv4-ospf_cfg:SRGB";
        presence "Indicates a srgb node is configured.";
        description "Segment Routing Global Block configuration";
        leaf lower-bound {
          xr:xr-xml-map "ipv4-ospf_cfg:LowerBound";
          type uint32 {
            range "16000..1048575";
          }
          mandatory true;
          description "The lower bound of the SRGB";
        }
        leaf upper-bound {
          xr:xr-xml-map "ipv4-ospf_cfg:UpperBound";
          type uint32 {
            range "16000..1048575";
          }
          mandatory true;
          description "The upper bound of the SRGB";
        }
      }
      uses DISTRIBUTE-LIST;
      uses COST;
      uses BFD;
      uses EXTERNAL-OUT;
      uses MTU-IGNORE;
      uses AUTHENTICATION;
      uses LDP-SYNC-IGP-SHORTCUTS;
      uses LDP-AUTO-CONFIG;
      uses SECURITY;
      uses FAST-REROUTE;
      uses SUMMARY-IN;
      uses NETWORK-TYPE;
      uses HELLO-INTERVAL;
      uses LOOPBACK-STUB-NETWORK;
      uses PREFIX-SUPPRESSION-SECONDARY;
      uses DEMAND-CIRCUIT;
      uses SEGMENT-ROUTING;
      uses PASSIVE;
      uses TRANSMIT-DELAY;
      uses PACKET-SIZE;
      uses LDP-SYNC;
      uses DATABASE-FILTER;
      uses DEAD-INTERVAL-MINIMAL;
      uses LINK-DOWN-FAST-DETECT;
      uses SEGMENT-ROUTING-FORWARDING;
      uses RETRANSMIT-INTERVAL;
      uses IPV4-OSPF-CFG-PRIORITY;
      uses FLOOD-REDUCTION;
      uses COST-FALLBACK;
    }
  }

  grouping UCMP {
    description "Common node of default-vrf, vrf";

    container ucmp {
      xr:xr-xml-map "ipv4-ospf_cfg:UCMP";
      description "Unequal Cost Multi-ptah configuration";

      container enable {
        xr:xr-xml-map "ipv4-ospf_cfg:Enable";
        description "UCMP feature enable configuration";
        leaf variance {
          xr:xr-xml-map "ipv4-ospf_cfg:Variance";
          type uint32 {
            range "101..10000";
          }
          default "200";
          description "Value of variance";
        }
        leaf prefix-list-name {
          xr:xr-xml-map "ipv4-ospf_cfg:PrefixListName";
          type string;
          description "Name of the Prefix List";
        }
      }
      leaf delay-interval {
        xr:xr-xml-map "ipv4-ospf_cfg:DelayInterval";
        xr:xr-cli-map "ospf <string> vrf <string> ucmp delay-interv"+
          "al <number> ";
        type uint32 {
          range "1..5000";
        }
        units "millisecond";
        default "100";
        description
          "Delay in msecs between primary SPF and UCMP
          computation";
      }
      uses EXCLUDE-INTERFACE-TABLE;
    }
  }

  grouping NSF {
    description "Common node of default-vrf, vrf";

    container nsf {
      xr:xr-xml-map "ipv4-ospf_cfg:NSF";
      description "Non Stop Forwarding configuration";
      leaf lifetime {
        xr:xr-xml-map "ipv4-ospf_cfg:Lifetime";
        xr:xr-cli-map "ospf <string> vrf <string> nsf lifetime <num"+
          "ber> ";
        type uint32 {
          range "90..1800";
        }
        units "second";
        default "90";
        description
          "Maximum route lifetime following restart in
          seconds";
      }
      leaf ietf {
        xr:xr-xml-map "ipv4-ospf_cfg:IETF";
        xr:xr-cli-map "ospf <string> vrf <string> nsf ietf ";
        type Ospf-ietf-nsf;
        description "Enable IETF Non Stop Forwarding";
      }
      leaf ietf-support-role {
        xr:xr-xml-map "ipv4-ospf_cfg:IETFSupportRole";
        xr:xr-cli-map "ospf <string> vrf <string> nsf ietf [helper "+
          "(disable)|(planned-only)] ";
        type Ospf-ietf-nsf-support;
        description
          "Disable helper support role for IETF Non Stop
          Forwarding";
      }
      leaf cisco {
        xr:xr-xml-map "ipv4-ospf_cfg:Cisco";
        xr:xr-cli-map "ospf <string> vrf <string> nsf enforce globa"+
          "l ";
        type Ospf-cisco-nsf;
        description "Enable Cisco Non Stop Forwarding";
      }
      leaf interval {
        xr:xr-xml-map "ipv4-ospf_cfg:Interval";
        xr:xr-cli-map "ospf <string> vrf <string> nsf interval <num"+
          "ber> ";
        type uint32 {
          range "90..3600";
        }
        units "second";
        default "90";
        description
          "Minimum interval between Non Stop Forwarding
          restarts in seconds";
      }
      leaf flush-delay-time {
        xr:xr-xml-map "ipv4-ospf_cfg:FlushDelayTime";
        xr:xr-cli-map "ospf <string> vrf <string> nsf flush-delay-t"+
          "ime <number> ";
        type uint32 {
          range "1..3600";
        }
        units "second";
        default "60";
        description
          "Maximum time allowed for external route
          learning (seconds)";
      }
      leaf ietf-strict-lsa-checking {
        xr:xr-xml-map "ipv4-ospf_cfg:IETFStrictLSAChecking";
        xr:xr-cli-map "ospf <string> vrf <string> nsf ietf strict-l"+
          "sa-checking ";
        type empty;
        description "Enable Strict LSA checking of IETF NSF";
      }
    }
  }

  grouping MTU-IGNORE {
    description
      "Common node of process-scope, area-scope,
      name-scope, multi-area-interface-scope";
    leaf mtu-ignore {
      xr:xr-xml-map "ipv4-ospf_cfg:MTUIgnore";
      xr:xr-cli-map "ospf <string> vrf <string> mtu-ignore enable ";
      type boolean;
      default "false";
      description "Enable/Disable ignoring of MTU in DBD packets";
    }
  }

  grouping FAST-REROUTE-USE-CANDIDATE-ONLY {
    description "Common node of per-link, per-prefix";
    leaf fast-reroute-use-candidate-only {
      xr:xr-xml-map "ipv4-ospf_cfg:FastRerouteUseCandidateOnly";
      xr:xr-cli-map "ospf <string> vrf <string> fast-reroute per-li"+
        "nk use-candidate-only enable ";
      xr:xr-cli-map "ospf <string> vrf <string> fast-reroute per-pr"+
        "efix use-candidate-only enable ";
      type boolean;
      default "false";
      description
        "Use only interfaces on the candidate list as a
        backup path";
    }
  }

  grouping BFD {
    description
      "Common node of process-scope, area-scope,
      name-scope";

    container bfd {
      xr:xr-xml-map "ipv4-ospf_cfg:BFD";
      description "BFD configuration";
      leaf interval {
        xr:xr-xml-map "ipv4-ospf_cfg:Interval";
        xr:xr-cli-map "ospf <string> vrf <string> bfd minimum-inter"+
          "val <number> ";
        type uint32 {
          range "3..30000";
        }
        units "millisecond";
        description
          "Hello interval for BFD sessions created by OSPF";
      }
      leaf detection-multiplier {
        xr:xr-xml-map "ipv4-ospf_cfg:DetectionMultiplier";
        xr:xr-cli-map "ospf <string> vrf <string> bfd multiplier <n"+
          "umber> ";
        type uint32 {
          range "2..50";
        }
        description
          "Detection multiplier for BFD sessions created
          by OSPF";
      }
      leaf fast-detect-mode {
        xr:xr-xml-map "ipv4-ospf_cfg:FastDetectMode";
        xr:xr-cli-map "ospf <string> vrf <string> bfd fast-detect s"+
          "trict-mode ";
        type Bfd-enable-mode;
        description " use of Bidirectional Forwarding Detection";
      }
    }
  }

  grouping LOOPBACK-STUB-NETWORK {
    description
      "Common node of process-scope, area-scope,
      name-scope";
    leaf loopback-stub-network {
      xr:xr-xml-map "ipv4-ospf_cfg:LoopbackStubNetwork";
      xr:xr-cli-map "ospf <string> vrf <string> loopback stub-netwo"+
        "rk [enable|disable] ";
      type boolean;
      default "false";
      description
        "Enable/Disable advertising loopback as a stub
        network";
    }
  }

  grouping FLOOD-REDUCTION {
    description
      "Common node of process-scope, area-scope,
      name-scope";
    leaf flood-reduction {
      xr:xr-xml-map "ipv4-ospf_cfg:FloodReduction";
      xr:xr-cli-map "ospf <string> vrf <string> flood-reduction ena"+
        "ble ";
      type boolean;
      default "false";
      description "Enable/Disable OSPF flood reduction";
    }
  }

  grouping MAX-LSA {
    description "Common node of default-vrf, vrf";

    container max-lsa {
      xr:xr-xml-map "ipv4-ospf_cfg:MaxLSA";
      presence "Indicates a max-lsa node is configured.";
      description "Set max-lsa configuration";
      leaf max-lsa-limit {
        xr:xr-xml-map "ipv4-ospf_cfg:MaxLSALimit";
        type uint32 {
          range "1..4294967294";
        }
        mandatory true;
        description "Set maximum number of non self-generated LSAs";
      }
      leaf max-lsa-threshold {
        xr:xr-xml-map "ipv4-ospf_cfg:MaxLSAThreshold";
        type uint32 {
          range "1..100";
        }
        description
          "Set max-lsa threshold for generating a warning
          message";
      }
      leaf max-lsa-warning-only {
        xr:xr-xml-map "ipv4-ospf_cfg:MaxLSAWarningOnly";
        type boolean;
        description
          "Only give warning message when limit is
          exceeded";
      }
      leaf max-lsa-ignore-time {
        xr:xr-xml-map "ipv4-ospf_cfg:MaxLSAIgnoreTime";
        type uint32 {
          range "1..35791394";
        }
        description
          "Set time during which all adjacencies are
          suppressed";
      }
      leaf max-lsa-ignore-count {
        xr:xr-xml-map "ipv4-ospf_cfg:MaxLSAIgnoreCount";
        type uint32 {
          range "1..4294967294";
        }
        description
          "Set count on how many times adjacencies can be
          suppressed";
      }
      leaf max-lsa-reset-time {
        xr:xr-xml-map "ipv4-ospf_cfg:MaxLSAResetTime";
        type uint32 {
          range "2..71582788";
        }
        units "minute";
        description
          "Set number of minutes after which ignore-count
          is reset to zero";
      }
    }
  }

  grouping OUTGOING-ROUTE-UPDATE-TABLE {
    description "Common node of default-vrf, vrf";

    container outgoing-route-updates {
      xr:xr-xml-map "ipv4-ospf_cfg:OutgoingRouteUpdateTable";
      description "Filter outgoing routing updates";

      list outgoing-route-update {
        xr:xr-xml-map "ipv4-ospf_cfg:OutgoingRouteUpdate";
        xr:xr-cli-map "ospf <string> vrf <string> distribute-list <"+
          "string> out [connected|static|dagr|bgp (<number>)|(<numb"+
          "er>)|(<number> <number>)|ospf <string>] ";
        key "protocol-name";
        description
          "Filter outgoing routing updates for a
          particular protocol";
        leaf protocol-name {
          xr:xr-xml-map "ipv4-ospf_cfg:ProtocolName";
          type Ospf-dist-list-protocol;
          description "Distribute list protocol type";
        }
        leaf access-list-name {
          xr:xr-xml-map "ipv4-ospf_cfg:AccessListName";
          type string;
          description "Access Control List name";
        }
        leaf as-xx {
          xr:xr-xml-map "ipv4-ospf_cfg:AS_XX";
          type uint32 {
            range "0..65535";
          }
          description
            "First half of BGP AS number in XX.YY format. 
            Mandatory if Protocol is BGP and must not be
            specified otherwise. Must be a non-zero value
            if second half is zero.";
        }
        leaf as-yy {
          xr:xr-xml-map "ipv4-ospf_cfg:AS_YY";
          type uint32 {
            range "0..4294967295";
          }
          description
            "Second half of BGP AS number in XX.YY format.
            Mandatory if Protocol is BGP and must not be
            specified otherwise. Must be a non-zero value
            if first half is zero.";
        }
        leaf ospf-process-name {
          xr:xr-xml-map "ipv4-ospf_cfg:OSPFProcessName";
          type string;
          description "OSPF process name";
        }
      }
    }
  }

  grouping LDP-SYNC {
    description
      "Common node of process-scope, area-scope,
      name-scope";
    leaf ldp-sync {
      xr:xr-xml-map "ipv4-ospf_cfg:LDPSync";
      xr:xr-cli-map "ospf <string> vrf <string> mpls ldp sync ";
      type boolean;
      description "Enable/Disable MPLS LDP sync";
    }
  }

  grouping IGNORE-MOSPF {
    description "Common node of default-vrf, vrf";
    leaf ignore-mospf {
      xr:xr-xml-map "ipv4-ospf_cfg:IgnoreMOSPF";
      xr:xr-cli-map "ospf <string> vrf <string> ignore lsa mospf ";
      type empty;
      description "Ignore MOSPF (Type 6) LSAs";
    }
  }

  grouping NEIGHBOR-TABLE {
    description
      "Common node of name-scope,
      multi-area-interface-scope";

    container neighbors {
      xr:xr-xml-map "ipv4-ospf_cfg:NeighborTable";
      description "Neighbor router configuration information";

      list neighbor {
        xr:xr-xml-map "ipv4-ospf_cfg:Neighbor";
        key "neighbor-address";
        description
          "Router configuration information for a
          particular neighbor";
        leaf neighbor-address {
          xr:xr-xml-map "ipv4-ospf_cfg:NeighborAddress";
          type inet:ipv4-address-no-zone;
          description "Neighbor IP address";
        }
        leaf priority {
          xr:xr-xml-map "ipv4-ospf_cfg:Priority";
          type uint32 {
            range "0..255";
          }
          default "0";
          description "OSPF priority of non-broadcast neighbor";
        }
        leaf poll-interval {
          xr:xr-xml-map "ipv4-ospf_cfg:PollInterval";
          type uint32 {
            range "0..65535";
          }
          units "second";
          default "40";
          description "OSPF dead router poll-interval in seconds";
        }
        leaf cost {
          xr:xr-xml-map "ipv4-ospf_cfg:Cost";
          type uint32 {
            range "1..65535";
          }
          default "1";
          description "OSPF cost for point-to-multipoint neighbor";
        }
        leaf database-filter {
          xr:xr-xml-map "ipv4-ospf_cfg:DatabaseFilter";
          type boolean;
          default "false";
          description
            "Database filter: Filter OSPF LSA during
            synchronization and flooding for
            point-to-multipoint";
        }
      }
    }
  }

  grouping TYPE7 {
    description "Common node of default-vrf, vrf";
    leaf type7 {
      xr:xr-xml-map "ipv4-ospf_cfg:Type7";
      xr:xr-cli-map "ospf <string> vrf <string> capability type7 pr"+
        "efer ";
      type empty;
      description "Prefer type7 externals over type5";
    }
  }

  grouping SPF-PREFIX-PRIORITY {
    description "Common node of default-vrf, vrf";
    leaf spf-prefix-priority {
      xr:xr-xml-map "ipv4-ospf_cfg:SPFPrefixPriority";
      xr:xr-cli-map "ospf <string> vrf <string> spf prefix-priority"+
        " route-policy (<string>)|(<text>) ";
      type string;
      description
        "Configure a route-policy for prioritizing RIB
        route install.";
    }
  }

  grouping SNMP-CONTEXT {
    description "Common node of default-vrf, vrf";
    leaf snmp-context {
      xr:xr-xml-map "ipv4-ospf_cfg:SNMPContext";
      xr:xr-cli-map "ospf <string> vrf <string> snmp context <strin"+
        "g> ";
      type string;
      description "OSPF SNMP context configuration";
    }
  }

  grouping ROUTER-ID {
    description "Common node of default-vrf, vrf";
    leaf router-id {
      xr:xr-xml-map "ipv4-ospf_cfg:RouterID";
      xr:xr-cli-map "ospf <string> vrf <string> router-id <IPv4 add"+
        "ress> ";
      type inet:ipv4-address-no-zone;
      description
        "Router ID for this OSPF process. Enter an IP
        Address.";
    }
  }

  grouping ADJACENCY-STAGGER {
    description "Common node of default-vrf, vrf";

    container adjacency-stagger {
      xr:xr-xml-map "ipv4-ospf_cfg:AdjacencyStagger";
      description "Staggering OSPF adjacency bring up";
      leaf disable {
        xr:xr-xml-map "ipv4-ospf_cfg:Disable";
        type empty;
        description "Disable OSPF adjacency stagger";
      }
      leaf initial-nbr {
        xr:xr-xml-map "ipv4-ospf_cfg:InitialNbr";
        type uint32 {
          range "1..65535";
        }
        default "2";
        description
          "Adjacency Stagger: Initial number of neighbors
          to bring up per area";
      }
      leaf max-nbr {
        xr:xr-xml-map "ipv4-ospf_cfg:MaxNbr";
        type uint32 {
          range "1..65535";
        }
        default "64";
        description
          "Adjacency Stagger: Subsequent simultaneous
          number of neighbors to bring up";
      }
    }
  }

  grouping DEFAULT-METRIC {
    description "Common node of default-vrf, vrf";
    leaf default-metric {
      xr:xr-xml-map "ipv4-ospf_cfg:DefaultMetric";
      xr:xr-cli-map "ospf <string> vrf <string> default-metric <num"+
        "ber> ";
      type uint32 {
        range "1..16777214";
      }
      default "1";
      description "Set default metric of redistributed routes";
    }
  }

  grouping RETRANSMIT-INTERVAL {
    description
      "Common node of process-scope, area-scope,
      name-scope, virtual-link-scope, sham-link-scope,
      multi-area-interface-scope";
    leaf retransmit-interval {
      xr:xr-xml-map "ipv4-ospf_cfg:RetransmitInterval";
      xr:xr-cli-map "ospf <string> vrf <string> retransmit-interval"+
        " <number> ";
      type uint32 {
        range "1..65535";
      }
      units "second";
      default "5";
      description
        "Time in seconds between retransmitting lost link
        state advertisements";
    }
  }

  grouping PRIORITY {
    description "Common node of per-link, per-prefix";
    leaf priority {
      xr:xr-xml-map "ipv4-ospf_instance_cfg:Priority";
      xr:xr-cli-map "ospf <string> vrf <string> fast-reroute per-li"+
        "nk priority-limit (critical)|(high)|(medium) ";
      xr:xr-cli-map "ospf <string> vrf <string> fast-reroute per-pr"+
        "efix priority-limit (critical)|(high)|(medium) ";
      type Ospf-fast-reroute-priority;
      description
        "Fast-reroute per-link/per-prefix priority-limit
        command";
    }
  }

  grouping IPV4-OSPF-CFG-PRIORITY {
    description
      "Common node of process-scope, area-scope,
      name-scope";
    leaf priority {
      xr:xr-xml-map "ipv4-ospf_cfg:Priority";
      xr:xr-cli-map "ospf <string> vrf <string> priority <number> ";
      type uint32 {
        range "0..255";
      }
      default "1";
      description "Router priority for DR and BDR election";
    }
  }

  container ospf {
    xr:xr-xml-map "ipv4-ospf_cfg:OSPF";
    description "OSPF configuration data";

    container processes {
      xr:xr-xml-map "ipv4-ospf_cfg:ProcessTable";
      description "Process related configuration";

      list process {
        xr:xr-xml-map "ipv4-ospf_cfg:Process";
        key "process-name";
        description
          "Configuration for a particular OSPF process and
          associated default VRF";

        container snmp {
          xr:xr-xml-map "ipv4-ospf_cfg:SNMP";
          description "OSPF SNMP configuration";

          container trap-rate-limit {
            xr:xr-xml-map "ipv4-ospf_cfg:TrapRateLimit";
            presence "Indicates a trap-rate-limit node is"+
              " configured.";
            description "Per OSPF process SNMP trap rate-limit";
            leaf window-size {
              xr:xr-xml-map "ipv4-ospf_cfg:WindowSize";
              type uint32 {
                range "2..60";
              }
              mandatory true;
              description "Trap rate limit sliding window size";
            }
            leaf max-window-traps {
              xr:xr-xml-map "ipv4-ospf_cfg:MaxWindowTraps";
              type uint32 {
                range "0..300";
              }
              mandatory true;
              description
                "Max number of traps to send in window time";
            }
          }
        }

        container distribute {
          xr:xr-xml-map "ipv4-ospf_cfg:Distribute";
          presence "enable distribute";
          description "Enable distribution of LSAs into BGP";
          leaf throttle {
            xr:xr-xml-map "ipv4-ospf_cfg:Throttle";
            type uint32 {
              range "1..3600";
            }
            units "second";
            description "Seconds";
          }
          leaf instance-id {
            xr:xr-xml-map "ipv4-ospf_cfg:InstanceId";
            type uint32 {
              range "1..65535";
            }
            description "Instance ID";
          }
        }

        container vrfs {
          xr:xr-xml-map "ipv4-ospf_cfg:VRFTable";
          description "VRF related configuration";

          list vrf {
            xr:xr-xml-map "ipv4-ospf_cfg:VRF";
            key "vrf-name";
            description "Configuration for a particular OSPF vrf";

            container domain-id {
              xr:xr-xml-map "ipv4-ospf_cfg:DomainID";
              description "OSPF Domain ID";

              container primary-domain-id {
                xr:xr-xml-map "ipv4-ospf_cfg:PrimaryDomainID";
                description "OSPF Primary domain ID";
                leaf domain-id-type {
                  xr:xr-xml-map "ipv4-ospf_cfg:DomainIDType";
                  type Ospf-domain-id;
                  description "Primary domain ID type";
                }
                leaf domain-id-name {
                  xr:xr-xml-map "ipv4-ospf_cfg:DomainIDName";
                  type string;
                  description "Primary domain ID value";
                }
              }

              container secondary-domain-ids {
                xr:xr-xml-map "ipv4-ospf_cfg:SecondaryDomainIDTable";
                description "Secondary domain ID Table";

                list secondary-domain-id {
                  xr:xr-xml-map "ipv4-ospf_cfg:SecondaryDomainID";
                  xr:xr-cli-map "ospf <string> vrf <string> domain-"+
                    "id secondary type <enum> value <string> ";
                  key "domain-id-type domain-id-name";
                  description "OSPF Secondary domain ID";
                  leaf domain-id-type {
                    xr:xr-xml-map "ipv4-ospf_cfg:DomainIDType";
                    type Ospf-domain-id;
                    description "Secondary domain ID type";
                  }
                  leaf domain-id-name {
                    xr:xr-xml-map "ipv4-ospf_cfg:DomainIDName";
                    type xr:Cisco-ios-xr-string;
                    description "Secondary domain ID value";
                  }
                }
              }
            }
            leaf vrf-start {
              xr:xr-xml-map "ipv4-ospf_cfg:VRFStart";
              type empty;
              description "Start OSPF VRF configuration";
            }
            leaf snmp-trap-enabled {
              xr:xr-xml-map "ipv4-ospf_cfg:SNMPTrapEnabled";
              xr:xr-cli-map "ospf <string> vrf <string> snmp trap ";
              type boolean;
              default "false";
              description "Enable/disable OSPF SNMP trap";
            }
            leaf domain-tag {
              xr:xr-xml-map "ipv4-ospf_cfg:DomainTag";
              xr:xr-cli-map "ospf <string> vrf <string> domain-tag "+
                "<number> ";
              type uint32 {
                range "1..4294967295";
              }
              description "32 bit Domain tag value";
            }
            leaf vrf-lite {
              xr:xr-xml-map "ipv4-ospf_cfg:VRFLite";
              xr:xr-cli-map "ospf <string> vrf <string> capability "+
                "vrf-lite ";
              type empty;
              description "VRF lite capability";
            }
            leaf disable-dn-bit-check {
              xr:xr-xml-map "ipv4-ospf_cfg:DisableDNBitCheck";
              xr:xr-cli-map "ospf <string> vrf <string> disable-dn-"+
                "bit-check ";
              type empty;
              description "Disable DN bit check";
            }
            leaf vrf-name {
              xr:xr-xml-map "ipv4-ospf_cfg:VRFName";
              type xr:Cisco-ios-xr-string;
              description "Name for this vrf";
            }
            uses MICROLOOP;
            uses IGNORE-MOSPF;
            uses MAXIMUM-REDISTRIBUTE-PREFIX;
            uses DEFAULT-INFORMATION;
            uses AF;
            uses QUEUE;
            uses ROUTER-ID;
            uses TYPE7;
            uses MAX-METRIC;
            uses SNMP-CONTEXT;
            uses MAXIMUM-INTERFACES;
            uses NO-OPAQUE;
            uses NSF;
            uses PROCESS-SCOPE;
            uses SPF-PREFIX-PRIORITY;
            uses REDISTRIBUTION;
            uses ADJACENCY-STAGGER;
            uses MAX-LSA;
            uses AUTO-COST;
            uses UCMP;
            uses MAXIMUM-PATHS;
            uses IPV4-OSPF-INSTANCE-CFG-FAST-REROUTE;
            uses SUMMARY-PREFIX-TABLE;
            uses ADJACENCY-CHANGES;
            uses OUTGOING-ROUTE-UPDATE-TABLE;
            uses DISTANCE;
            uses AREA-TABLE;
            uses TIMERS;
            uses DEFAULT-METRIC;
          }
        }

        container default-vrf {
          xr:xr-xml-map "ipv4-ospf_cfg:DefaultVRF";
          description "Default VRF related configuration";

          container monitor-convergence {
            xr:xr-xml-map "ipv4-ospf_cfg:MonitorConvergence";
            description "Enable convergence monitoring";
            leaf enable {
              xr:xr-xml-map "ipv4-ospf_cfg:Enable";
              type empty;
              description "Enable convergence monitoring";
            }
            leaf prefix-list {
              xr:xr-xml-map "ipv4-ospf_cfg:PrefixList";
              type string;
              description
                "Enable the monitoring of individual prefixes
                (prefix list name)";
            }
            leaf track-ip-frr {
              xr:xr-xml-map "ipv4-ospf_cfg:TrackIpFrr";
              type empty;
              description
                "Enable the Tracking of IP-Frr Convergence";
            }
            leaf track-external-routes {
              xr:xr-xml-map "ipv4-ospf_cfg:TrackExternalRoutes";
              type empty;
              description
                "Enable the monitoring of External routes";
            }
            leaf track-summary-routes {
              xr:xr-xml-map "ipv4-ospf_cfg:TrackSummaryRoutes";
              type empty;
              description "Enable the monitoring of Summary routes";
            }
          }

          container segment-routing {
            xr:xr-xml-map "ipv4-ospf_instance_cfg:SegmentRouting";
            description
              "Segment Routing instance scoped parameters";

            container sr-prefer {
              xr:xr-xml-map "ipv4-ospf_instance_cfg:SrPrefer";
              description
                "Prefer segment routing labels over LDP
                labels";
              leaf enable {
                xr:xr-xml-map "ipv4-ospf_instance_cfg:Enable";
                type boolean;
                description
                  "Enable SR labels to be preferred over LDP
                  labels";
              }
              leaf prefix-list-name {
                xr:xr-xml-map "ipv4-ospf_instance_cfg:PrefixListNam"+
                  "e";
                type string;
                description "Name of the Prefix List";
              }
            }
            leaf prefix-sid-map-receive-disable {
              xr:xr-xml-map "ipv4-ospf_instance_cfg:PrefixSidMapRec"+
                "eiveDisable";
              type empty;
              description "Disable prefix-SID mapping client";
            }
            leaf prefix-sid-map-advertise-local {
              xr:xr-xml-map "ipv4-ospf_instance_cfg:PrefixSidMapAdv"+
                "ertiseLocal";
              type empty;
              description
                "Enable advertisement of local SRMS entries";
            }
          }

          container mpls {
            xr:xr-xml-map "ipv4-ospf_cfg:MPLS";
            description
              "Configure MPLS routing protocol parameters";

            container mpls-router-id {
              xr:xr-xml-map "ipv4-ospf_cfg:MPLSRouterID";
              description
                "MPLS-TE stable loopback address for this
                OSPF process.Enter either as IP Address or
                Interface name, but not both. Unused field
                must be nil";
              leaf address {
                xr:xr-xml-map "ipv4-ospf_cfg:Address";
                type inet:ipv4-address-no-zone;
                description
                  "MPLS-TE stable IP address for this OSPF
                  process";
              }
              leaf interface-name {
                xr:xr-xml-map "ipv4-ospf_cfg:InterfaceName";
                type xr:Interface-name;
                description
                  "MPLS-TE stable loopback interface for this
                  OSPF process";
              }
            }
            leaf igp-intact {
              xr:xr-xml-map "ipv4-ospf_cfg:IGPIntact";
              type empty;
              description "Enable igp-intact mode in OSPF";
            }
            leaf ldp-sync-update {
              xr:xr-xml-map "ipv4-ospf_cfg:LDPSyncUpdate";
              type empty;
              description
                "Enable LDP sync induced metric propagation";
            }
            leaf multicast-intact {
              xr:xr-xml-map "ipv4-ospf_cfg:MulticastIntact";
              type empty;
              description "Enable multicast-intact mode in OSPF";
            }
            leaf autoroute-exclude {
              xr:xr-xml-map "ipv4-ospf_cfg:AutorouteExclude";
              type string;
              description
                "Exclude IP destinations from using TE
                tunnels";
            }
          }
          uses MICROLOOP;
          uses IGNORE-MOSPF;
          uses MAXIMUM-REDISTRIBUTE-PREFIX;
          uses DEFAULT-INFORMATION;
          uses AF;
          uses QUEUE;
          uses ROUTER-ID;
          uses TYPE7;
          uses MAX-METRIC;
          uses SNMP-CONTEXT;
          uses MAXIMUM-INTERFACES;
          uses NO-OPAQUE;
          uses NSF;
          uses PROCESS-SCOPE;
          uses SPF-PREFIX-PRIORITY;
          uses REDISTRIBUTION;
          uses ADJACENCY-STAGGER;
          uses MAX-LSA;
          uses AUTO-COST;
          uses UCMP;
          uses MAXIMUM-PATHS;
          uses IPV4-OSPF-INSTANCE-CFG-FAST-REROUTE;
          uses SUMMARY-PREFIX-TABLE;
          uses ADJACENCY-CHANGES;
          uses OUTGOING-ROUTE-UPDATE-TABLE;
          uses DISTANCE;
          uses AREA-TABLE;
          uses TIMERS;
          uses DEFAULT-METRIC;
        }
        leaf start {
          xr:xr-xml-map "ipv4-ospf_cfg:Start";
          type empty;
          description "Start OSPF configuration";
        }
        leaf nsr {
          xr:xr-xml-map "ipv4-ospf_cfg:NSR";
          xr:xr-cli-map "ospf <string> nsr disable ";
          type Nsr;
          default "true";
          description "Enable non-stop routing";
        }
        leaf protocol-shutdown {
          xr:xr-xml-map "ipv4-ospf_cfg:ProtocolShutdown";
          xr:xr-cli-map "ospf <string> protocol shutdown (host-mode"+
            ")|(on-reload) ";
          type Ospf-shutdown;
          description "Type of protocol shutdown";
        }
        leaf process-name {
          xr:xr-xml-map "ipv4-ospf_cfg:ProcessName";
          type xr:Cisco-ios-xr-string;
          description "Name for this OSPF process";
        }
        uses RUNNING;
      }
    }

    container global {
      xr:xr-xml-map "ipv4-ospf_cfg:Global";
      description "OSPF global configuration data";
      leaf dns-name-lookup {
        xr:xr-xml-map "ipv4-ospf_cfg:DNSNameLookup";
        xr:xr-cli-map "ospf name-lookup ";
        type empty;
        description "Display OSPF router ids as DNS names";
      }
    }
  }

  augment "/a1:snmp/a1:notification" {

    container ospf {
      xr:xr-xml-map "ospfmib_cfg:OSPF";
      description "OSPF-MIB notification configuration";

      container lsa {
        xr:xr-xml-map "ospfmib_cfg:LSA";
        description "SNMP notifications related to LSAs";
        leaf max-age-lsa {
          xr:xr-xml-map "ospfmib_cfg:MaxAgeLSA";
          type empty;
          description "Enable ospfMaxAgeLsa notification";
        }
        leaf originate-lsa {
          xr:xr-xml-map "ospfmib_cfg:OriginateLSA";
          type empty;
          description "Enable ospfOriginateLsa notification";
        }
      }

      container state-change {
        xr:xr-xml-map "ospfmib_cfg:StateChange";
        description "SNMP notifications for OSPF state change";
        leaf interface {
          xr:xr-xml-map "ospfmib_cfg:Interface";
          type empty;
          description "Enable ospfIfStateChange notification";
        }
        leaf virtual-interface {
          xr:xr-xml-map "ospfmib_cfg:VirtualInterface";
          type empty;
          description "Enable ospfVirtIfStateChange notification";
        }
        leaf virtual-neighbor {
          xr:xr-xml-map "ospfmib_cfg:VirtualNeighbor";
          type empty;
          description "Enable ospfVirtNbrStateChange notification";
        }
        leaf neighbor {
          xr:xr-xml-map "ospfmib_cfg:Neighbor";
          type empty;
          description "Enable ospfNbrStateChange notification";
        }
      }

      container retransmit {
        xr:xr-xml-map "ospfmib_cfg:Retransmit";
        description "SNMP notifications for packet retransmissions";
        leaf virtual-packet {
          xr:xr-xml-map "ospfmib_cfg:VirtualPacket";
          type empty;
          description "Enable ospfVirtIfTxRetransmit notification";
        }
        leaf packet {
          xr:xr-xml-map "ospfmib_cfg:Packet";
          type empty;
          description "Enable ospfTxRetransmit notification";
        }
      }

      container error {
        xr:xr-xml-map "ospfmib_cfg:Error";
        description "SNMP notifications for OSPF errors";
        leaf config-error {
          xr:xr-xml-map "ospfmib_cfg:ConfigError";
          type empty;
          description "Enable ospfIfConfigError notification";
        }
        leaf authentication-failure {
          xr:xr-xml-map "ospfmib_cfg:AuthenticationFailure";
          type empty;
          description "Enable ospfIfAuthFailure notification";
        }
        leaf virtual-config-error {
          xr:xr-xml-map "ospfmib_cfg:VirtualConfigError";
          type empty;
          description "Enable ospfVirtIfConfigError notification";
        }
        leaf virtual-authentication-failure {
          xr:xr-xml-map "ospfmib_cfg:VirtualAuthenticationFailure";
          type empty;
          description "Enable ospfVirtIfAuthFailure notification";
        }
        leaf bad-packet {
          xr:xr-xml-map "ospfmib_cfg:BadPacket";
          type empty;
          description "Enable ospfIfRxBadPacket notification";
        }
        leaf virtual-bad-packet {
          xr:xr-xml-map "ospfmib_cfg:VirtualBadPacket";
          type empty;
          description "Enable ospfVirtIfRxBadPacket notification";
        }
      }
    }
    description
      "This augment extends the configuration data of
      'Cisco-IOS-XR-snmp-agent-cfg'";
  }
}
