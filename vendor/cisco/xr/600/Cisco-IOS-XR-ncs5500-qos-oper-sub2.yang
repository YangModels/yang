submodule Cisco-IOS-XR-ncs5500-qos-oper-sub2 {

  belongs-to Cisco-IOS-XR-ncs5500-qos-oper {
    prefix Cisco-IOS-XR-ncs5500-qos-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ncs5500-qos package operational data.

     Copyright (c) 2013-2015 by Cisco Systems, Inc.
     All rights reserved.";

  revision "2015-11-09" {
    description
      "IOS XR 6.0 revision.";
  }

  typedef Dnx-qosea-show-wred {
    type enumeration {
      enum wred-cos {
        description "WRED based on COS";
      }
      enum wred-dscp {
        description "WRED based on DSCP";
      }
      enum wred-precedence {
        description "WRED based on Precedence";
      }
      enum wred-discard-class {
        description "WRED based on discard class";
      }
      enum wred-mpls-exp {
        description "WRED based on MPLS EXP";
      }
      enum red-with-user-min-max {
        description "RED with user defined min and max";
      }
      enum red-with-default-min-max {
        description "RED with default min and max";
      }
      enum wred-invalid {
        description "Invalid";
      }
    }
    description "WRED type";
  }
  typedef Dnx-qosea-show-action {
    type enumeration {
      enum action-none {
        description "None";
      }
      enum action-transmit {
        description "Transmit";
      }
      enum action-drop {
        description "Drop";
      }
      enum action-mark {
        description "Mark";
      }
    }
    description "Policer action type";
  }
  typedef Dnx-qosea-show-policy-unit {
    type enumeration {
      enum invalid {
        value 0;
        description "Invalid uint type";
      }
      enum bytes {
        value 1;
        description "Units in bytes";
      }
      enum kilo-bytes {
        value 2;
        description "Units in kilobytes";
      }
      enum mega-bytes {
        value 3;
        description "Units in megabytes";
      }
      enum giga-bytes {
        value 4;
        description "Units in gigabytes";
      }
      enum bits-per-second {
        value 5;
        description "Units in bits per second";
      }
      enum kilo-bits-per-second {
        value 6;
        description "Units in kilo bits per second";
      }
      enum mega-bits-per-second {
        value 7;
        description "Units in mega bits per second";
      }
      enum giga-bits-per-second {
        value 8;
        description "Units in giga bits per second";
      }
      enum cells-per-second {
        value 9;
        description "Units in cells per second";
      }
      enum packets-per-second {
        value 10;
        description "Units in Packets Per Second";
      }
      enum microseconds {
        value 11;
        description "Units in microseconds";
      }
      enum milliseconds {
        value 12;
        description "Units in milliseconds";
      }
      enum packets {
        value 13;
        description "Units in packets";
      }
      enum cells {
        value 14;
        description "Units in cells";
      }
      enum percent {
        value 15;
        description "Units in percentage";
      }
      enum ratio {
        value 16;
        description "Units in ratio";
      }
    }
    description "Policy parameter unit type";
  }
  typedef Dnx-qosea-show-hp-level {
    type enumeration {
      enum high-priority-level1 {
        description "High priority queue level 1";
      }
      enum high-priority-level2 {
        description "High priority queue level 2";
      }
      enum high-priority-level3 {
        description "High priority queue level 3";
      }
      enum high-priority-level4 {
        description "High priority queue level 4";
      }
      enum high-priority-level5 {
        description "High priority queue level 5";
      }
      enum high-priority-level6 {
        description "High priority queue level 6";
      }
      enum high-priority-level7 {
        description "High priority queue level 7";
      }
      enum unknown {
        description "Unknown";
      }
    }
    description "Priority level";
  }
  typedef Dnx-qosea-show-queue {
    type enumeration {
      enum low-priority-default-queue {
        description "Low priority default queue";
      }
      enum low-priority-queue {
        description "Low priority queue";
      }
      enum high-priority-queue {
        description "High priority queue";
      }
      enum unknown-queue-type {
        description "Queue priority unknown";
      }
    }
    description "Priority Queue Type";
  }
  typedef Dnx-qosea-show-mark {
    type enumeration {
      enum mark-none {
        description "None";
      }
      enum dscp {
        description "DSCP";
      }
      enum precedence {
        description "Precedence";
      }
      enum mpls-topmost {
        description "MPLS topmost";
      }
      enum mpls-imposition {
        description "MPLS imposition";
      }
      enum qos-group {
        description "Qos group";
      }
      enum discard-class {
        description "Discard class";
      }
      enum cos {
        description "COS";
      }
      enum inner-cos {
        description "Inner COS";
      }
      enum dscp-tunnel {
        description "DSCP tunnel";
      }
      enum precedence-tunnel {
        description "Precedence tunnel";
      }
    }
    description "Mark type";
  }
  typedef Dnx-qosea-show-level {
    type enumeration {
      enum level1 {
        value 0;
        description "QoS level1 class";
      }
      enum level2 {
        value 1;
        description "QoS level2 class";
      }
      enum level3 {
        value 2;
        description "QoS level3 class";
      }
      enum level4 {
        value 3;
        description "QoS level4 class";
      }
      enum level5 {
        value 4;
        description "QoS level5 class";
      }
    }
    description "Level type";
  }
  typedef Dnx-qosea-show-intf-status {
    type enumeration {
      enum state-unknown {
        description "State is unknown";
      }
      enum state-down {
        description "State is Down";
      }
    }
    description "Intf Status";
  }
  typedef Dnx-qosea-show-policy-status {
    type enumeration {
      enum no-error {
        description "No errors";
      }
      enum policy-in-reset {
        description "QoS policy is reset";
      }
    }
    description "Status";
  }
  typedef Qos-policy-account-enum {
    type enumeration {
      enum qos-serv-policy-no-ac-count-pref {
        description "qos serv policy no ac count pref";
      }
      enum qos-serv-policy-ac-count-l2 {
        description "qos serv policy ac count l2";
      }
      enum qos-serv-policy-no-ac-count-l2 {
        description "qos serv policy no ac count l2";
      }
      enum qos-serv-policy-ac-count-user-def {
        description "qos serv policy ac count user def";
      }
      enum qos-serv-policy-ac-count-l1 {
        description "qos serv policy ac count l1";
      }
    }
    description "Qos policy account enum";
  }

  grouping QOS-RANGE {
    description "QOS RANGE";
    leaf range-start {
      xr:xr-xml-map "dnx_qosea_show:RangeStart";
      type uint8;
      description "Start value of a range";
    }
    leaf range-end {
      xr:xr-xml-map "dnx_qosea_show:RangeEnd";
      type uint8;
      description "End value of a range";
    }
  }

  grouping DNX-QOSEA-SHOW-RED-MATCH-VALUES {
    description "DNX QOSEA SHOW RED MATCH VALUES";

    list dnx-qosea-show-red-match-value {
      description "dnx qosea show red match value";
      uses QOS-RANGE;
    }
  }

  grouping PARAMETERS {
    description "WRED parameters";

    container wred-match-value {
      description "WRED match values";
      uses DNX-QOSEA-SHOW-RED-MATCH-VALUES;
    }

    container config-min-threshold {
      description "Configured minimum threshold";
      uses POLICY-PARAMETER;
    }

    container config-max-threshold {
      description "Configured maximum threshold";
      uses POLICY-PARAMETER;
    }
    leaf wred-match-type {
      xr:xr-xml-map "dnx_qosea_show:WREDMatchType";
      type Dnx-qosea-show-wred;
      description "WREDMatchType";
    }
    leaf hardware-min-threshold-bytes {
      xr:xr-xml-map "dnx_qosea_show:HardwareMinThresholdBytes";
      type uint32;
      description "Hardware minimum threshold";
    }
    leaf hardware-max-threshold-bytes {
      xr:xr-xml-map "dnx_qosea_show:HardwareMaxThresholdBytes";
      type uint32;
      description "Hardware maximum threshold";
    }
    leaf first-segment {
      xr:xr-xml-map "dnx_qosea_show:FirstSegment";
      type uint16;
      description "First segment";
    }
    leaf segment-size {
      xr:xr-xml-map "dnx_qosea_show:SegmentSize";
      type uint32;
      description "Segment size";
    }
  }

  grouping POLICER-ACTION {
    description "POLICER ACTION";
    leaf action-type {
      xr:xr-xml-map "dnx_qosea_show:ActionType";
      type Dnx-qosea-show-action;
      description "Policer action type";
    }

    list mark {
      description "Action mark";
      uses QOS-MARK;
    }
  }

  grouping POLICY-PARAMETER {
    description "Policy parameter";
    leaf policy-value {
      xr:xr-xml-map "dnx_qosea_show:PolicyValue";
      type uint32;
      description "Policy value";
    }
    leaf policy-unit {
      xr:xr-xml-map "dnx_qosea_show:PolicyUnit";
      type Dnx-qosea-show-policy-unit;
      description "Policy unit";
    }
  }

  grouping QOS-MARK {
    description "QoS mark";
    leaf mark-type {
      xr:xr-xml-map "dnx_qosea_show:MarkType";
      type Dnx-qosea-show-mark;
      description "Mark type";
    }
    leaf mark-value {
      xr:xr-xml-map "dnx_qosea_show:MarkValue";
      type uint16;
      description "Mark value";
    }
  }

  grouping DNX-QOSEA-SHOW-CLASS-ST {
    description "QoS policy";

    container config-max-rate {
      description "Configured maximum rate";
      uses POLICY-PARAMETER;
    }

    container config-min-rate {
      description "Configured minimum rate";
      uses POLICY-PARAMETER;
    }

    container config-queue-limit {
      description "Configured queue limit";
      uses POLICY-PARAMETER;
    }

    container config-policer-average-rate {
      description "Configured policer average rate";
      uses POLICY-PARAMETER;
    }

    container config-policer-peak-rate {
      description "Config policer peak rate";
      uses POLICY-PARAMETER;
    }

    container config-policer-conform-burst {
      description "Configured policer conform burst";
      uses POLICY-PARAMETER;
    }

    container config-policer-excess-burst {
      description "Configured policer excess burst";
      uses POLICY-PARAMETER;
    }

    container conform-action {
      description "Conform action";
      uses POLICER-ACTION;
    }

    container exceed-action {
      description "Exceed action";
      uses POLICER-ACTION;
    }

    container violate-action {
      description "Violate action";
      uses POLICER-ACTION;
    }
    leaf class-level {
      xr:xr-xml-map "dnx_qosea_show:ClassLevel";
      type Dnx-qosea-show-level;
      description "Class level";
    }
    leaf egress-queue-id {
      xr:xr-xml-map "dnx_qosea_show:EgressQueueID";
      type int32;
      description "Egress Queue ID";
    }
    leaf queue-type {
      xr:xr-xml-map "dnx_qosea_show:QueueType";
      type Dnx-qosea-show-queue;
      description "Queue type";
    }
    leaf priority-level {
      xr:xr-xml-map "dnx_qosea_show:PriorityLevel";
      type Dnx-qosea-show-hp-level;
      description "Priority level";
    }
    leaf hardware-max-rate-kbps {
      xr:xr-xml-map "dnx_qosea_show:HardwareMaxRateKbps";
      type uint32;
      units "kbit/s";
      description "Hardware maximum rate in kbps";
    }
    leaf hardware-min-rate-kbps {
      xr:xr-xml-map "dnx_qosea_show:HardwareMinRateKbps";
      type uint32;
      units "kbit/s";
      description "Hardware minimum rate in kbps";
    }
    leaf config-excess-bandwidth-percent {
      xr:xr-xml-map "dnx_qosea_show:ConfigExcessBandwidthPercent";
      type uint32;
      units "percentage";
      description "Configured excess bandwidth percentage";
    }
    leaf config-excess-bandwidth-unit {
      xr:xr-xml-map "dnx_qosea_show:ConfigExcessBandwidthUnit";
      type uint32;
      description "Configured excess bandwidth unit";
    }
    leaf hardware-excess-bandwidth-weight {
      xr:xr-xml-map "dnx_qosea_show:HardwareExcessBandwidthWeight";
      type uint32;
      description "Hardware excess bandwidth weight";
    }
    leaf network-min-bandwidth-kbps {
      xr:xr-xml-map "dnx_qosea_show:NetworkMinBandwidthKbps";
      type uint32;
      description "Network minimum Bandwith";
    }
    leaf hardware-queue-limit-bytes {
      xr:xr-xml-map "dnx_qosea_show:HardwareQueueLimitBytes";
      type uint64;
      units "byte";
      description "Hardware queue limit in bytes";
    }
    leaf hardware-queue-limit-microseconds {
      xr:xr-xml-map "dnx_qosea_show:HardwareQueueLimitMicroseconds";
      type uint64;
      units "microsecond";
      description "Hardware queue limit in microseconds";
    }
    leaf policer-bucket-id {
      xr:xr-xml-map "dnx_qosea_show:PolicerBucketID";
      type uint32;
      description "PolicerBucketID";
    }
    leaf policer-stats-handle {
      xr:xr-xml-map "dnx_qosea_show:PolicerStatsHandle";
      type uint64;
      description "PolicerStatsHandle";
    }
    leaf hardware-policer-average-rate-kbps {
      xr:xr-xml-map "dnx_qosea_show:HardwarePolicerAverageRateKbps";
      type uint32;
      units "kbit/s";
      description "Hardware policer average in kbps";
    }
    leaf hardware-policer-peak-rate-kbps {
      xr:xr-xml-map "dnx_qosea_show:HardwarePolicerPeakRateKbps";
      type uint32;
      description "Hardware policer peak rate";
    }
    leaf hardware-policer-conform-burst-bytes {
      xr:xr-xml-map "dnx_qosea_show:HardwarePolicerConformBurstByte"+
        "s";
      type uint32;
      description "Hardware policer conform burst";
    }
    leaf hardware-policer-excess-burst-bytes {
      xr:xr-xml-map "dnx_qosea_show:HardwarePolicerExcessBurstBytes";
      type uint32;
      description "Hardware policer excess burst";
    }

    list ip-mark {
      description "IP mark";
      uses QOS-MARK;
    }

    list common-mark {
      description "Common mark";
      uses QOS-MARK;
    }

    list mpls-mark {
      description "MPLS mark";
      uses QOS-MARK;
    }

    list wred {
      description "WRED parameters";
      uses PARAMETERS;
    }
  }

  grouping DNX-QOSEA-SHOW-IF-QOS-INFO-ST {
    description "Policy Details";
    leaf npu-id {
      xr:xr-xml-map "dnx_qosea_show:NPU_ID";
      type uint32;
      description "NPU ID";
    }
    leaf interface-handle {
      xr:xr-xml-map "dnx_qosea_show:InterfaceHandle";
      type uint32;
      description "InterfaceHandle";
    }
    leaf interface-bandwidth-kbps {
      xr:xr-xml-map "dnx_qosea_show:InterfaceBandwidthKbps";
      type uint32;
      units "kbit/s";
      description "Interface Bandwidth (in kbps)";
    }
    leaf policy-name {
      xr:xr-xml-map "dnx_qosea_show:PolicyName";
      type string {
        length "0..64";
      }
      description "Policy name";
    }
    leaf total-number-of-classes {
      xr:xr-xml-map "dnx_qosea_show:TotalNumberOfClasses";
      type uint16;
      description "Number of Classes";
    }
    leaf voq-base-address {
      xr:xr-xml-map "dnx_qosea_show:VOQ_BaseAddress";
      type uint32;
      description "VOQ base address";
    }
    leaf voq-stats-handle {
      xr:xr-xml-map "dnx_qosea_show:VOQStatsHandle";
      type uint64;
      description "VOQ stats handle";
    }
    leaf stats-accounting-type {
      xr:xr-xml-map "dnx_qosea_show:StatsAccountingType";
      type Qos-policy-account-enum;
      description "QoS Statistics Accounting Type";
    }
    leaf policy-status {
      xr:xr-xml-map "dnx_qosea_show:PolicyStatus";
      type Dnx-qosea-show-policy-status;
      description "Policy Status";
    }
    leaf interface-status {
      xr:xr-xml-map "dnx_qosea_show:InterfaceStatus";
      type Dnx-qosea-show-intf-status;
      description "Interface Status";
    }
  }
}
