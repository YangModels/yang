module Cisco-IOS-XR-icpe-infra-cfg {

  /*** NAMESPACE / PREFIX DEFINITION ***/

  namespace "http://cisco.com/ns/yang/Cisco-IOS-XR-icpe-infra-cfg";


  prefix "icpe-infra-cfg";

  /*** LINKAGE (IMPORTS / INCLUDES) ***/

  import ietf-inet-types { prefix "inet"; }

  import ietf-yang-types { prefix "yang"; }

  import Cisco-IOS-XR-types { prefix "xr"; }

  import Cisco-IOS-XR-ifmgr-cfg { prefix "a1"; }

  import Cisco-IOS-XR-rgmgr-cfg { prefix "a2"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR icpe-infra package configuration.

     This module contains definitions
     for the following management objects:
       nv-satellites: Satellite Configuration table
       nv-satellite-global: nv satellite global

     This YANG module augments the
       Cisco-IOS-XR-ifmgr-cfg,
       Cisco-IOS-XR-rgmgr-cfg,
     modules with configuration data.

     Copyright (c) 2013-2015 by Cisco Systems, Inc.
     All rights reserved.";

  revision "2015-11-09" {
    description
      "IOS XR 6.0 revision.";
  }

  typedef Icpe-sat-id {
    type uint32 {
      range "100..65534";
    }
    description "Icpe sat id";
  }
  typedef Icpe-slot {
    type uint32 {
      range "0..8";
    }
    description "Icpe slot";
  }
  typedef Icpe-min-links {
    type uint32 {
      range "1..64";
    }
    description "Icpe min links";
  }
  typedef Icpe-subslot {
    type uint32 {
      range "0..8";
    }
    description "Icpe subslot";
  }

  grouping ENABLE {
    description
      "Common node of nv-satellite-fabric-network,
      satellites";
    leaf enable {
      xr:xr-xml-map "icpe_cfg_intf_yang_gen:Enable";
      type empty;
      description "Enable";
    }
  }

  grouping REMOTE-PORTS-TABLE {
    description
      "Common node of nv-satellite-fabric-link,
      satellites";

    container remote-ports {
      xr:xr-xml-map "icpe_cfg_intf_yang_gen:RemotePortsTable";
      description "Remote Ports table";

      list remote-port {
        xr:xr-xml-map "icpe_cfg_intf_yang_gen:RemotePorts";
        key "port-type slot sub-slot";
        description "Remote Ports";
        leaf port-type {
          xr:xr-xml-map "icpe_cfg_intf_yang_gen:PortType";
          type xr:Cisco-ios-xr-string;
          description "Port type";
        }
        leaf slot {
          xr:xr-xml-map "icpe_cfg_intf_yang_gen:Slot";
          type Icpe-slot;
          description "Slot";
        }
        leaf sub-slot {
          xr:xr-xml-map "icpe_cfg_intf_yang_gen:SubSlot";
          type Icpe-subslot;
          description "Sub slot";
        }
        leaf port-range {
          xr:xr-xml-map "icpe_cfg_intf_yang_gen:PortRange";
          type string;
          mandatory true;
          description "Port range";
        }
      }
    }
  }

  grouping REDUNDANCY {
    description
      "Common node of nv-satellite-fabric-link,
      nv-satellite-fabric-network";

    container redundancy {
      xr:xr-xml-map "icpe_cfg_intf_yang_gen:Redundancy";
      description "Redundancy submode";
      leaf iccp-group {
        xr:xr-xml-map "icpe_cfg_intf_yang_gen:ICCPGroup";
        type uint32 {
          range "0..4294967295";
        }
        description
          "Links the satellite fabric to the given ICCP
          group";
      }
      leaf minimum-preferred-links {
        xr:xr-xml-map "icpe_cfg_intf_yang_gen:MinimumPreferredLinks";
        type Icpe-min-links;
        description "Mininum number of active links preferred";
      }
    }
  }

  container nv-satellites {
    xr:xr-xml-map "icpe_cfg_gl_yang_gen:nVSatelliteTable";
    description "Satellite Configuration table";

    list nv-satellite {
      xr:xr-xml-map "icpe_cfg_gl_yang_gen:nVSatellite";
      key "satellite-id";
      description "Satellite Configuration";

      container candidate-fabric-ports {
        xr:xr-xml-map "icpe_cfg_gl_yang_gen:CandidateFabricPortsTab"+
          "le";
        description
          "Enable interfaces on the satellite to be used
          as fabric ports table";

        list candidate-fabric-port {
          xr:xr-xml-map "icpe_cfg_gl_yang_gen:CandidateFabricPorts";
          key "port-type slot sub-slot";
          description
            "Enable interfaces on the satellite to be used
            as fabric ports";
          leaf port-type {
            xr:xr-xml-map "icpe_cfg_gl_yang_gen:PortType";
            type xr:Cisco-ios-xr-string;
            description "Port type";
          }
          leaf slot {
            xr:xr-xml-map "icpe_cfg_gl_yang_gen:Slot";
            type Icpe-slot;
            description "Slot";
          }
          leaf sub-slot {
            xr:xr-xml-map "icpe_cfg_gl_yang_gen:SubSlot";
            type Icpe-subslot;
            description "Sub slot";
          }
          leaf port-range {
            xr:xr-xml-map "icpe_cfg_gl_yang_gen:PortRange";
            type string;
            mandatory true;
            description "Port range";
          }
        }
      }

      container connection-info {
        xr:xr-xml-map "icpe_cfg_gl_yang_gen:ConnectionInfo";
        description "Satellite User";
        leaf username {
          xr:xr-xml-map "icpe_cfg_gl_yang_gen:Username";
          type string;
          description "Satellite Username";
        }
        leaf password {
          xr:xr-xml-map "icpe_cfg_gl_yang_gen:Password";
          type xr:Md5-password;
          description "Encrypted password for the user";
        }
      }

      container redundancy {
        xr:xr-xml-map "icpe_cfg_gl_yang_gen:Redundancy";
        description "Redundancy submode";
        leaf host-priority {
          xr:xr-xml-map "icpe_cfg_gl_yang_gen:HostPriority";
          type uint32 {
            range "0..255";
          }
          description
            "Priority for this host for the given satellite";
        }
      }
      leaf vrf {
        xr:xr-xml-map "icpe_cfg_gl_yang_gen:VRF";
        type string;
        description "VRF for Satellite IP Address";
      }
      leaf upgrade-on-connect {
        xr:xr-xml-map "icpe_cfg_gl_yang_gen:UpgradeOnConnect";
        type uint32 {
          range "0..255";
        }
        description "Satellite Upgrade on Connection";
      }
      leaf device-name {
        xr:xr-xml-map "icpe_cfg_gl_yang_gen:Device-Name";
        type string;
        description "Satellite Name";
      }
      leaf description {
        xr:xr-xml-map "icpe_cfg_gl_yang_gen:Description";
        type string;
        description "Satellite Description";
      }
      leaf type {
        xr:xr-xml-map "icpe_cfg_gl_yang_gen:Type";
        type string;
        description "Satellite Type";
      }
      leaf enable {
        xr:xr-xml-map "icpe_cfg_gl_yang_gen:Enable";
        type empty;
        description "Enable";
      }
      leaf disc-timeout {
        xr:xr-xml-map "icpe_cfg_gl_yang_gen:DiscTimeout";
        type uint32 {
          range "0..4294967295";
        }
        description "Discovery timeout for the satellite";
      }
      leaf serial-number {
        xr:xr-xml-map "icpe_cfg_gl_yang_gen:SerialNumber";
        type string;
        description "Satellite Serial Number";
      }
      leaf secret {
        xr:xr-xml-map "icpe_cfg_gl_yang_gen:Secret";
        type xr:Md5-password;
        description "Encrypted password for the Satellite";
      }
      leaf ip-address {
        xr:xr-xml-map "icpe_cfg_gl_yang_gen:IPAddress";
        type inet:ip-address-no-zone;
        description "Satellite IP Address";
      }
      leaf satellite-id {
        xr:xr-xml-map "icpe_cfg_gl_yang_gen:SatelliteID";
        type Icpe-sat-id;
        description "Satellite ID";
      }
    }
  }

  container nv-satellite-global {
    xr:xr-xml-map "icpe_cfg_gl_yang_gen:nVSatelliteGlobal";
    description "nv satellite global";

    container chassis-mac {
      xr:xr-xml-map "icpe_cfg_gl_yang_gen:ChassisMac";
      description "Chassis MAC address";
      leaf mac1 {
        xr:xr-xml-map "icpe_cfg_gl_yang_gen:Mac1";
        type uint32 {
          range "0..2147483647";
        }
        units "byte";
        description "First two bytes of MAC address";
      }
      leaf mac2 {
        xr:xr-xml-map "icpe_cfg_gl_yang_gen:Mac2";
        type uint32 {
          range "0..2147483647";
        }
        units "byte";
        description "Second two bytes of MAC address";
      }
      leaf mac3 {
        xr:xr-xml-map "icpe_cfg_gl_yang_gen:Mac3";
        type uint32 {
          range "0..2147483647";
        }
        units "byte";
        description "Third two bytes of MAC address";
      }
    }
  }

  augment "/a1:interface-configurations/a1:interface-configuration" {

    container nv-satellite-access {
      xr:xr-xml-map "icpe_cfg_intf_yang_gen:nVSatelliteAccess";
      description "nV Satellite Access Link Configuration";
    }
    description
      "This augment extends the configuration data of
      'Cisco-IOS-XR-ifmgr-cfg'";
  }

  augment "/a1:interface-configurations/a1:interface-configuration" {

    container nv-satellite-fabric-link {
      xr:xr-xml-map "icpe_cfg_intf_yang_gen:nVSatelliteFabricLink";
      description "nV Satellite Fabric Link Configuration";
      leaf satellite {
        xr:xr-xml-map "icpe_cfg_intf_yang_gen:Satellite";
        type Icpe-sat-id;
        description "Hub & Spoke connection to a single Satellite";
      }
      uses REDUNDANCY;
      uses REMOTE-PORTS-TABLE;
    }
    description
      "This augment extends the configuration data of
      'Cisco-IOS-XR-ifmgr-cfg'";
  }

  augment "/a1:interface-configurations/a1:interface-configuration" {

    container nv-satellite-fabric-network {
      xr:xr-xml-map "icpe_cfg_intf_yang_gen:nVSatelliteFabricNetwor"+
        "k";
      description
        "Complex Network connection to one or more
        Satellites";

      container satellites {
        xr:xr-xml-map "icpe_cfg_intf_yang_gen:SatellitesTable";
        description "Connected Satellite table";

        list satellite {
          xr:xr-xml-map "icpe_cfg_intf_yang_gen:Satellites";
          key "satellite-id";
          description "Connected Satellite";
          leaf satellite-id {
            xr:xr-xml-map "icpe_cfg_intf_yang_gen:SatelliteID";
            type Icpe-sat-id;
            description "Satellite ID";
          }
          uses REMOTE-PORTS-TABLE;
          uses ENABLE;
        }
      }
      uses REDUNDANCY;
      uses ENABLE;
    }
    description
      "This augment extends the configuration data of
      'Cisco-IOS-XR-ifmgr-cfg'";
  }

  augment "/a2:redundancy-group-manager/a2:iccp/a2:iccp-groups"+
    "/a2:iccp-group" {

    container nv-satellite {
      xr:xr-xml-map "icpe_gco_iccp_cfg:nVSatellite";
      description "nV Satellite configuration";
      leaf system-mac {
        xr:xr-xml-map "icpe_gco_iccp_cfg:SystemMAC";
        type yang:mac-address;
        description "Optional identifier for this system";
      }
    }
    description
      "This augment extends the configuration data of
      'Cisco-IOS-XR-rgmgr-cfg'";
  }
}
