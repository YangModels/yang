module Cisco-IOS-XR-fretta-bcm-dpa-oper {

  /*** NAMESPACE / PREFIX DEFINITION ***/

  namespace "http://cisco.com/ns/yang"+
    "/Cisco-IOS-XR-fretta-bcm-dpa-oper";


  prefix "fretta-bcm-dpa-oper";

  /*** LINKAGE (IMPORTS / INCLUDES) ***/

  import Cisco-IOS-XR-types { prefix "xr"; }

  include Cisco-IOS-XR-fretta-bcm-dpa-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR fretta-bcm-dpa package operational data.

     This module contains definitions
     for the following management objects:
       dpa: DPA operational data

     Copyright (c) 2013-2015 by Cisco Systems, Inc.
     All rights reserved.";

  revision "2015-11-09" {
    description
      "IOS XR 6.0 revision.";
  }

  typedef Max-trap-s {
    type uint32 {
      range "0..4294967295";
    }
    description "Max trap s";
  }
  typedef Max-lc-intf-hand-les {
    type uint32 {
      range "0..4294967295";
    }
    description "Max lc intf hand les";
  }

  container dpa {
    xr:xr-xml-map "dpa_npu_stats_oper:DPA";
    config false;
    description "DPA operational data";

    container stats {
      xr:xr-xml-map "dpa_npu_stats_oper:STATS";
      description "DPA voq data";

      container nodes {
        xr:xr-xml-map "dpa_npu_stats_oper:NodeTable";
        description "DPA data for available nodes";

        list node {
          xr:xr-xml-map "dpa_npu_stats_oper:Node";
          key "node-name";
          description "DPA operational data for a particular node";

          container all-traps-stats-data-blocks {
            xr:xr-xml-map "dpa_npu_stats_oper:AllTraps";
            description "DPA trap stats ";

            list all-traps-stats-data-block {
              xr:xr-xml-map "dpa_npu_stats_oper:AllTrapsStatsDataBl"+
                "ock";
              key "data-block-number";
              description
                "Indicates the data block number for trap
                stats data block and cannot be used to
                extract a single data block";
              leaf data-block-number {
                xr:xr-xml-map "dpa_npu_stats_oper:DataBlockNumber";
                type int32;
                description "Data Block Number";
              }
              uses DPA-TRAP-STATS;
            }
          }

          container single-trap-stats-data-blocks {
            xr:xr-xml-map "dpa_npu_stats_oper:SingleTrap";
            description "DPA stats for a single trap";

            list single-trap-stats-data-block {
              xr:xr-xml-map "dpa_npu_stats_oper:SingleTrapStatsData"+
                "Block";
              key "trapid";
              description "Trap number";
              leaf trapid {
                xr:xr-xml-map "dpa_npu_stats_oper:Trapid";
                type Max-trap-s;
                description "Trap number";
              }

              list trap-data-block-number {
                xr:xr-xml-map "dpa_npu_stats_oper:TrapDataBlockNumb"+
                  "er";
                key "data-block-number";
                description
                  "Indicates the data block number for a
                  particular trap and cannot be used to
                  extract a particular block";
                leaf data-block-number {
                  xr:xr-xml-map "dpa_npu_stats_oper:DataBlockNumber";
                  type int32;
                  description "Data Block Number";
                }
                uses DPA-TRAP-STATS;
              }
            }
          }

          container all-voq-stats-data-blocks {
            xr:xr-xml-map "dpa_npu_stats_oper:AllInterfaces";
            description "DPA voq ingress stats ";

            list all-voq-stats-data-block {
              xr:xr-xml-map "dpa_npu_stats_oper:AllVoqStatsDataBloc"+
                "k";
              key "data-block-number";
              description
                "Indicate the data block number of the voq
                stats data block and cannot be used to
                extract a single data block";
              leaf data-block-number {
                xr:xr-xml-map "dpa_npu_stats_oper:DataBlockNumber";
                type int32;
                description "Data Block Number";
              }
              uses DPA-VOQ-INTF-PORT;
            }
          }

          container voq-base-numbers {
            xr:xr-xml-map "dpa_npu_stats_oper:VoqBaseStats";
            description "DPA voq base stats ";

            list voq-base-number {
              xr:xr-xml-map "dpa_npu_stats_oper:VoqBaseNumber";
              key "base-number";
              description "Voq Base Number for a particular voq";
              leaf base-number {
                xr:xr-xml-map "dpa_npu_stats_oper:BaseNumber";
                type Max-lc-intf-hand-les;
                description "Interface handle";
              }

              list voq-base-data-block-number {
                xr:xr-xml-map "dpa_npu_stats_oper:VoqBaseDataBlockN"+
                  "umber";
                key "data-block-number";
                description
                  "Indicates the data block number for a
                  particular voq base and cannot be used to
                  extract a particular block number";
                leaf data-block-number {
                  xr:xr-xml-map "dpa_npu_stats_oper:DataBlockNumber";
                  type int32;
                  description "Data Block Number";
                }
                uses DPA-VOQ-INTF-PORT;
              }
            }
          }

          container single-voq-stats-data-blocks {
            xr:xr-xml-map "dpa_npu_stats_oper:SingleInterface";
            description
              "DPA voq ingress stats for a single interface";

            list single-voq-stats-data-block {
              xr:xr-xml-map "dpa_npu_stats_oper:SingleVoqStatsDataB"+
                "lock";
              key "interface-handle";
              description "Interface handle for a particular voq";
              leaf interface-handle {
                xr:xr-xml-map "dpa_npu_stats_oper:InterfaceHandle";
                type Max-lc-intf-hand-les;
                description "Interface handle";
              }

              list voq-stats-data-block-number {
                xr:xr-xml-map "dpa_npu_stats_oper:VoqStatsDataBlock"+
                  "Number";
                key "data-block-number";
                description
                  "Indicates the data block number for a
                  particular voq and cannot be used to
                  extract a single element";
                leaf data-block-number {
                  xr:xr-xml-map "dpa_npu_stats_oper:DataBlockNumber";
                  type int32;
                  description "Data Block Number";
                }
                uses DPA-VOQ-INTF-PORT;
              }
            }
          }
          leaf node-name {
            xr:xr-xml-map "dpa_npu_stats_oper:NodeName";
            type xr:Node-id;
            description "Node ID";
          }
        }
      }
    }
  }
}
