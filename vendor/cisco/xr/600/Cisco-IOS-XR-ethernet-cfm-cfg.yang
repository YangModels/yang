module Cisco-IOS-XR-ethernet-cfm-cfg {

  /*** NAMESPACE / PREFIX DEFINITION ***/

  namespace "http://cisco.com/ns/yang/Cisco-IOS-XR-ethernet-cfm-cfg";


  prefix "ethernet-cfm-cfg";

  /*** LINKAGE (IMPORTS / INCLUDES) ***/

  import ietf-yang-types { prefix "yang"; }

  import Cisco-IOS-XR-types { prefix "xr"; }

  import Cisco-IOS-XR-ethernet-cfm-datatypes { prefix "dt1"; }

  import Cisco-IOS-XR-infra-sla-datatypes { prefix "dt2"; }

  import Cisco-IOS-XR-ifmgr-cfg { prefix "a1"; }

  import Cisco-IOS-XR-l2-eth-infra-cfg { prefix "a2"; }

  import Cisco-IOS-XR-snmp-agent-cfg { prefix "a3"; }

  import Cisco-IOS-XR-infra-sla-cfg { prefix "a4"; }

  import Cisco-IOS-XR-icpe-infra-cfg { prefix "a5"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ethernet-cfm package configuration.

     This YANG module augments the
       Cisco-IOS-XR-ifmgr-cfg,
       Cisco-IOS-XR-l2-eth-infra-cfg,
       Cisco-IOS-XR-snmp-agent-cfg,
       Cisco-IOS-XR-infra-sla-cfg,
       Cisco-IOS-XR-icpe-infra-cfg
     modules with configuration data.

     Copyright (c) 2013-2015 by Cisco Systems, Inc.
     All rights reserved.";

  revision "2015-11-09" {
    description
      "IOS XR 6.0 revision.";
  }

  typedef Cfm-mip-policy {
    type enumeration {
      enum all {
        value 2;
        description
          "Create MIPs on all ports in the Bridge Domain
          or Cross-connect";
      }
      enum lower-mep-only {
        value 3;
        description
          "Create MIPs on ports which have a MEP at a
          lower level";
      }
    }
    description "Cfm mip policy";
  }
  typedef Cfm-service {
    type enumeration {
      enum bridge-domain {
        value 1;
        description
          "Use a Bridge Domain - all MEPs will be Up MEPs
          and MIPs are permitted";
      }
      enum p2p-cross-connect {
        value 2;
        description
          "Use a P2P Cross Connect - all MEPs will be Up
          MEPs and MIPs are permitted";
      }
      enum mp2mp-cross-connect {
        value 3;
        description
          "Use a MP2MP Cross Connect - all MEPs will be Up
          MEPs and MIPs are permitted";
      }
      enum down-meps {
        value 4;
        description "Down MEPs - no MIPs permitted";
      }
    }
    description "Cfm service";
  }
  typedef Cfm-short-ma-name-format {
    type enumeration {
      enum vlan-id {
        value 1;
        description "VLAN ID";
      }
      enum string {
        value 2;
        description "String Short MA Name";
      }
      enum number {
        value 3;
        description "Numeric Short MA Name";
      }
      enum vpn-id {
        value 4;
        description "RFC 2685 VPN ID";
      }
      enum icc-based {
        value 32;
        description "ICC-based format";
      }
    }
    description "Cfm short ma name format";
  }
  typedef Cfm-lm-counters-cfg {
    type enumeration {
      enum aggregate {
        value 1;
        description "Aggregate Counters";
      }
      enum list {
        value 2;
        description "List of per-CoS counters";
      }
      enum range {
        value 3;
        description "Range of per-CoS counters";
      }
    }
    description "Cfm lm counters cfg";
  }
  typedef Cfm-mdid-format {
    type enumeration {
      enum null {
        value 1;
        description "Null MDID";
      }
      enum dns-like {
        value 2;
        description "DNS-like MDID";
      }
      enum mac-address {
        value 3;
        description
          "MDID Comprising MAC Address and 16-bit integer";
      }
      enum string {
        value 4;
        description "String MDID";
      }
    }
    description "Cfm mdid format";
  }

  augment "/a1:interface-configurations/a1:interface-configuration"+
    "/a5:nv-satellite-fabric-link" {

    container ethernet-features {
      xr:xr-xml-map "cfm_cfg_sat:EthernetFeatures";
      description "Ethernet Satellite configuration";

      container cfm {
        xr:xr-xml-map "cfm_cfg_sat:CFM";
        description "CFM Satellite configuration";
        leaf continuity-check-interval {
          xr:xr-xml-map "cfm_cfg_sat:ContinuityCheckInterval";
          type dt1:Cfm-ccm-interval;
          description "Continuity-Check Interval";
        }
        leaf level {
          xr:xr-xml-map "cfm_cfg_sat:Level";
          type dt1:Cfm-level;
          description "Maintenance Domain Level";
        }
        leaf enable {
          xr:xr-xml-map "cfm_cfg_sat:Enable";
          type empty;
          description "Enable CFM on Satellite";
        }
      }
    }
    description
      "This augment extends the configuration data of
      'Cisco-IOS-XR-icpe-infra-cfg'";
  }

  augment "/a4:sla/a4:protocols" {

    container ethernet {
      xr:xr-xml-map "cfm_sla_mgmt_sla_cfg:Ethernet";
      description "The Ethernet SLA protocol";

      container profiles {
        xr:xr-xml-map "cfm_sla_mgmt_sla_cfg:ProfileTable";
        description "Table of SLA profiles on the protocol";

        list profile {
          xr:xr-xml-map "cfm_sla_mgmt_sla_cfg:Profile";
          key "profile-name";
          description "Name of the profile";

          container statistics {
            xr:xr-xml-map "cfm_sla_mgmt_sla_cfg:StatisticTable";
            description
              "Statistics configuration for the SLA profile";

            list statistic {
              xr:xr-xml-map "cfm_sla_mgmt_sla_cfg:Statistic";
              key "statistic-name";
              description "Type of statistic";

              container buckets-size {
                xr:xr-xml-map "cfm_sla_mgmt_sla_cfg:BucketsSize";
                presence "Indicates a buckets-size node is"+
                  " configured.";
                description
                  "Size of the buckets into which statistics
                  are collected";
                leaf buckets-size {
                  xr:xr-xml-map "cfm_sla_mgmt_sla_cfg:BucketsSize";
                  type uint32 {
                    range "1..100";
                  }
                  mandatory true;
                  description "Size of each bucket";
                }
                leaf buckets-size-unit {
                  xr:xr-xml-map "cfm_sla_mgmt_sla_cfg:BucketsSizeUn"+
                    "it";
                  type dt2:Sla-buckets-size-units-enum;
                  mandatory true;
                  description
                    "Unit associated with the BucketsSize";
                }
              }

              container aggregation {
                xr:xr-xml-map "cfm_sla_mgmt_sla_cfg:Aggregation";
                presence "Indicates a aggregation node is"+
                  " configured.";
                description
                  "Aggregation to apply to results for the
                  statistic";
                leaf bins-count {
                  xr:xr-xml-map "cfm_sla_mgmt_sla_cfg:BinsCount";
                  type uint32 {
                    range "0..100";
                  }
                  mandatory true;
                  description
                    "Number of bins to aggregate results into
                    (0 for no aggregation)";
                }
                leaf bins-width {
                  xr:xr-xml-map "cfm_sla_mgmt_sla_cfg:BinsWidth";
                  type uint32 {
                    range "1..10000";
                  }
                  description "Width of each bin";
                }
                leaf bins-width-tenths {
                  xr:xr-xml-map "cfm_sla_mgmt_sla_cfg:BinsWidthTent"+
                    "hs";
                  type uint32 {
                    range "0..9";
                  }
                  description "Tenths portion of the bin width";
                }
              }
              leaf enable {
                xr:xr-xml-map "cfm_sla_mgmt_sla_cfg:Enable";
                type empty;
                description
                  "Enable statistic gathering of the metric";
              }
              leaf buckets-archive {
                xr:xr-xml-map "cfm_sla_mgmt_sla_cfg:BucketsArchive";
                type uint32 {
                  range "1..100";
                }
                description
                  "Number of buckets to archive in memory";
              }
              leaf statistic-name {
                xr:xr-xml-map "cfm_sla_mgmt_sla_cfg:StatisticName";
                type dt2:Sla-statistic-type-enum;
                description "The type of statistic to measure";
              }
            }
          }

          container schedule {
            xr:xr-xml-map "cfm_sla_mgmt_sla_cfg:Schedule";
            presence "Indicates a schedule node is configured.";
            description
              "Schedule to use for probes within an
              operation";
            leaf probe-interval {
              xr:xr-xml-map "cfm_sla_mgmt_sla_cfg:ProbeInterval";
              type uint32 {
                range "1..90";
              }
              description
                "Interval between probes.  This must be
                specified if, and only if, ProbeIntervalUnit
                is not 'Week' or 'Day'.";
            }
            leaf probe-interval-day {
              xr:xr-xml-map "cfm_sla_mgmt_sla_cfg:ProbeIntervalDay";
              type dt2:Sla-probe-interval-day-enum;
              description
                "Day of week on which to schedule probes. 
                This must be specified if, and only if,
                ProbeIntervalUnit is 'Week'.";
            }
            leaf probe-interval-unit {
              xr:xr-xml-map "cfm_sla_mgmt_sla_cfg:ProbeIntervalUnit";
              type dt2:Sla-probe-interval-units-enum;
              mandatory true;
              description
                "Time unit associated with the ProbeInterval.
                The value must not be 'Once'.  If 'Week' or
                'Day' is specified, probes are scheduled
                weekly or daily respectively.";
            }
            leaf start-time-hour {
              xr:xr-xml-map "cfm_sla_mgmt_sla_cfg:StartTimeHour";
              type uint32 {
                range "0..23";
              }
              description
                "Time after midnight (in UTC) to send the
                first packet each day.";
            }
            leaf start-time-minute {
              xr:xr-xml-map "cfm_sla_mgmt_sla_cfg:StartTimeMinute";
              type uint32 {
                range "0..59";
              }
              description
                "Time after midnight (in UTC) to send the
                first packet each day. This must be
                specified if, and only if, StartTimeHour is
                specified.";
            }
            leaf start-time-second {
              xr:xr-xml-map "cfm_sla_mgmt_sla_cfg:StartTimeSecond";
              type uint32 {
                range "0..59";
              }
              description
                "Time after midnight (in UTC) to send the
                first packet each day. This must only be
                specified if StartTimeHour is specified, and
                must not be specified if ProbeIntervalUnit
                is 'Week' or 'Day'.";
            }
            leaf probe-duration {
              xr:xr-xml-map "cfm_sla_mgmt_sla_cfg:ProbeDuration";
              type uint32 {
                range "1..3600";
              }
              description
                "Duration of each probe.  This must be
                specified if, and only if, ProbeDurationUnit
                is specified.";
            }
            leaf probe-duration-unit {
              xr:xr-xml-map "cfm_sla_mgmt_sla_cfg:ProbeDurationUnit";
              type dt2:Sla-probe-duration-units-enum;
              description
                "Time unit associated with the ProbeDuration.
                The value must not be 'Once'.";
            }
          }

          container probe {
            xr:xr-xml-map "cfm_sla_mgmt_sla_cfg:Probe";
            description "Probe configuration for the SLA profile";

            container send {
              xr:xr-xml-map "cfm_sla_mgmt_sla_cfg:Send";
              presence "Indicates a send node is configured.";
              description
                "Schedule to use for packets within a burst. 
                The default value is to send a single packet
                once.";
              leaf burst-interval {
                xr:xr-xml-map "cfm_sla_mgmt_sla_cfg:BurstInterval";
                type uint32 {
                  range "1..3600";
                }
                description
                  "Interval between bursts.  This must be
                  specified if, and only if, the SendType is
                  'Burst' and the 'BurstIntervalUnit' is not
                  'Once'.";
              }
              leaf burst-interval-unit {
                xr:xr-xml-map "cfm_sla_mgmt_sla_cfg:BurstIntervalUn"+
                  "it";
                type dt2:Sla-burst-interval-units-enum;
                description
                  "Time unit associated with the BurstInterval
                  .  This must be specified if, and only is,
                  SendType is 'Burst'.";
              }
              leaf packet-interval {
                xr:xr-xml-map "cfm_sla_mgmt_sla_cfg:PacketInterval";
                type uint32 {
                  range "1..10000";
                }
                mandatory true;
                description "Interval between packets.";
              }
              leaf packet-interval-unit {
                xr:xr-xml-map "cfm_sla_mgmt_sla_cfg:PacketIntervalU"+
                  "nit";
                type dt2:Sla-packet-interval-units-enum;
                mandatory true;
                description
                  "Time unit associated with the
                  PacketInterval, must not be 'Once'.";
              }
              leaf packet-count {
                xr:xr-xml-map "cfm_sla_mgmt_sla_cfg:PacketCount";
                type uint32 {
                  range "2..1200";
                }
                description
                  "The number of packets in each burst.  This
                  must be specified if, and only if, the
                  SendType is 'Burst'.";
              }
              leaf send-type {
                xr:xr-xml-map "cfm_sla_mgmt_sla_cfg:SendType";
                type dt2:Sla-send;
                mandatory true;
                description
                  "The packet distribution: single packets or
                  bursts of packets.  If 'Burst' is specified
                  , PacketCount and BurstInterval must be
                  specified.";
              }
            }

            container packet-size-and-padding {
              xr:xr-xml-map "cfm_sla_mgmt_sla_cfg:PacketSizeAndPadd"+
                "ing";
              presence "Indicates a packet-size-and-padding node is"+
                " configured.";
              description "Minimum size to pad outgoing packet to";
              leaf size {
                xr:xr-xml-map "cfm_sla_mgmt_sla_cfg:Size";
                type uint32 {
                  range "1..9000";
                }
                mandatory true;
                description
                  "Minimum size to pad outgoing packet to";
              }
              leaf padding-type {
                xr:xr-xml-map "cfm_sla_mgmt_sla_cfg:PaddingType";
                type dt2:Sla-padding-pattern;
                description
                  "Type of padding to be used for the packet";
              }
              leaf padding-value {
                xr:xr-xml-map "cfm_sla_mgmt_sla_cfg:PaddingValue";
                type xr:Hex-integer;
                description
                  "Pattern to be used for hex padding. This
                  can be specified if, and only if, the
                  PaddingType is 'Hex'.";
              }
            }
            leaf priority {
              xr:xr-xml-map "cfm_sla_mgmt_sla_cfg:Priority";
              type uint32 {
                range "0..7";
              }
              description
                "Priority class to assign to outgoing SLA
                packets";
            }
            leaf synthetic-loss-calculation-packets {
              xr:xr-xml-map "cfm_sla_mgmt_sla_cfg:SyntheticLossCalc"+
                "ulationPackets";
              type uint32 {
                range "10..12096000";
              }
              description
                "Number of packets to use in each FLR
                calculation";
            }
          }
          leaf packet-type {
            xr:xr-xml-map "cfm_sla_mgmt_sla_cfg:PacketType";
            type string;
            description
              "The possible packet types are cfm-loopback,
              cfm-delay-measurement,
              cfm-delay-measurement-version-0 and
              cfm-synthetic-loss-measurement";
          }
          leaf profile-name {
            xr:xr-xml-map "cfm_sla_mgmt_sla_cfg:ProfileName";
            type xr:Cisco-ios-xr-string;
            description "Profile name";
          }
        }
      }
    }
    description
      "This augment extends the configuration data of
      'Cisco-IOS-XR-infra-sla-cfg'";
  }

  augment "/a1:interface-configurations/a1:interface-configuration"+
    "/a2:ethernet-features" {

    container cfm {
      xr:xr-xml-map "cfm_cfg_loc:CFM";
      description "CFM interface configuration";

      container domains {
        xr:xr-xml-map "cfm_cfg_loc:DomainTable";
        description "Domain-specific interface configuration";

        list domain {
          xr:xr-xml-map "cfm_cfg_loc:Domain";
          key "domain";
          description
            "Configuration for a particular Maintenance
            Domain";

          container mep {
            xr:xr-xml-map "cfm_cfg_loc:MEP";
            description "MEP Configuration";

            container sla-profile-target-mep-ids {
              xr:xr-xml-map "cfm_cfg_loc:SLATable";
              description "SLA specific configuration";

              list sla-profile-target-mep-id {
                key "profile target-mep-id";
                description
                  "Configuration for a particular SLA
                  operation";
                leaf profile {
                  xr:xr-xml-map "cfm_cfg_loc:Profile";
                  type xr:Cisco-ios-xr-string;
                  description "SLA profile name";
                }
                leaf target-mep-id {
                  xr:xr-xml-map "cfm_cfg_loc:TargetMEP_ID";
                  type dt1:Cfm-mep-id;
                  description "Target MEP-ID";
                }
              }

              list sla-profile-target-mac-address {
                key "profile target-mac-address";
                description
                  "Configuration for a particular SLA
                  operation";
                leaf profile {
                  xr:xr-xml-map "cfm_cfg_loc:Profile";
                  type xr:Cisco-ios-xr-string;
                  description "SLA profile name";
                }
                leaf target-mac-address {
                  xr:xr-xml-map "cfm_cfg_loc:TargetMACAddress";
                  type yang:mac-address;
                  description "Target MAC address";
                }
              }
            }

            container mep-properties {
              xr:xr-xml-map "cfm_cfg_loc:MEPProperties";
              presence "Indicates a mep-properties node is"+
                " configured.";
              description "Properties for this MEP";
              leaf service {
                xr:xr-xml-map "cfm_cfg_loc:Service";
                type string;
                mandatory true;
                description "Service (Maintenance Association)";
              }
              leaf mep-id {
                xr:xr-xml-map "cfm_cfg_loc:MEP_ID";
                type dt1:Cfm-mep-id;
                mandatory true;
                description "MEP ID";
              }
            }

            container loss-measurement-counters {
              xr:xr-xml-map "cfm_cfg_loc:LossMeasurementCounters";
              presence "Indicates a loss-measurement-counters node"+
                " is configured.";
              description "Loss-measurement specific configuration";
              leaf cfg-type {
                xr:xr-xml-map "cfm_cfg_loc:CfgType";
                type Cfm-lm-counters-cfg;
                mandatory true;
                description "Aggregate, List, or Range";
              }
              leaf cos0 {
                xr:xr-xml-map "cfm_cfg_loc:CoS0";
                type dt1:Cfm-cos-bits;
                description
                  "CoS bits for per-CoS counters - start of
                  range or list item";
              }
              leaf cos1 {
                xr:xr-xml-map "cfm_cfg_loc:CoS1";
                type dt1:Cfm-cos-bits;
                description
                  "CoS bits for per-CoS counters - end of
                  range or list item";
              }
              leaf cos2 {
                xr:xr-xml-map "cfm_cfg_loc:CoS2";
                type dt1:Cfm-cos-bits;
                description
                  "CoS bits for per-CoS counters - list item";
              }
              leaf cos3 {
                xr:xr-xml-map "cfm_cfg_loc:CoS3";
                type dt1:Cfm-cos-bits;
                description
                  "CoS bits for per-CoS counters - list item";
              }
              leaf cos4 {
                xr:xr-xml-map "cfm_cfg_loc:CoS4";
                type dt1:Cfm-cos-bits;
                description
                  "CoS bits for per-CoS counters - list item";
              }
              leaf cos5 {
                xr:xr-xml-map "cfm_cfg_loc:CoS5";
                type dt1:Cfm-cos-bits;
                description
                  "CoS bits for per-CoS counters - list item";
              }
              leaf cos6 {
                xr:xr-xml-map "cfm_cfg_loc:CoS6";
                type dt1:Cfm-cos-bits;
                description
                  "CoS bits for per-CoS counters - list item";
              }
              leaf cos7 {
                xr:xr-xml-map "cfm_cfg_loc:CoS7";
                type dt1:Cfm-cos-bits;
                description
                  "CoS bits for per-CoS counters - list item";
              }
            }
            leaf cos {
              xr:xr-xml-map "cfm_cfg_loc:CoS";
              type dt1:Cfm-cos-bits;
              description "The Class of Service bits for this MEP";
            }
          }
          leaf domain {
            xr:xr-xml-map "cfm_cfg_loc:Domain";
            type string;
            description "Maintenance Domain";
          }
        }
      }

      container ais-up {
        xr:xr-xml-map "cfm_cfg_loc:AISUp";
        description "Interface specific AIS configuration";

        container transmission {
          xr:xr-xml-map "cfm_cfg_loc:Transmission";
          presence "enable transmission";
          description "AIS transmission configuration";
          leaf ais-interval {
            xr:xr-xml-map "cfm_cfg_loc:AISInterval";
            type dt1:Cfm-ais-interval;
            description "AIS Interval";
          }
          leaf cos {
            xr:xr-xml-map "cfm_cfg_loc:CoS";
            type dt1:Cfm-cos-bits;
            description "Class of Service bits";
          }
        }
      }
    }
    description
      "This augment extends the configuration data of
      'Cisco-IOS-XR-l2-eth-infra-cfg'";
  }

  augment "/a2:ethernet-features" {

    container cfm {
      xr:xr-xml-map "cfm_cfg_sh:CFM";
      description "CFM global configuration";

      container traceroute-cache {
        xr:xr-xml-map "cfm_cfg_sh:TracerouteCache";
        must "(hold-time and not(cache-size)) or (not(hold-time)"+
          " and cache-size) or (hold-time and cache-size)" {
          description "Describes valid combinations of leafs";
        }
        description "Traceroute Cache Configuration";
        leaf hold-time {
          xr:xr-xml-map "cfm_cfg_sh:HoldTime";
          type uint32 {
            range "1..525600";
          }
          default "100";
          description "Hold Time in minutes";
        }
        leaf cache-size {
          xr:xr-xml-map "cfm_cfg_sh:CacheSize";
          type uint32 {
            range "1..4294967295";
          }
          default "100";
          description "Cache Size limit (number of replies)";
        }
      }

      container domains {
        xr:xr-xml-map "cfm_cfg_sh:DomainTable";
        description "Domain-specific global configuration";

        list domain {
          xr:xr-xml-map "cfm_cfg_sh:Domain";
          key "domain";
          description
            "Configuration for a particular Maintenance
            Domain";

          container services {
            xr:xr-xml-map "cfm_cfg_sh:ServiceTable";
            description "Service-specific global configuration";

            list service {
              xr:xr-xml-map "cfm_cfg_sh:Service";
              key "service";
              description
                "Configuration for a particular Service
                (Maintenance Association)";

              container efd2 {
                xr:xr-xml-map "cfm_cfg_sh:EFD2";
                presence "Indicates a efd2 node is configured.";
                description
                  "Enable EFD to bring down ports when MEPs
                  detect errors";
                leaf enable {
                  xr:xr-xml-map "cfm_cfg_sh:Enable";
                  type empty;
                  mandatory true;
                  description "Enable EFD";
                }
                leaf protection-switching-enable {
                  xr:xr-xml-map "cfm_cfg_sh:ProtectionSwitchingEnab"+
                    "le";
                  type empty;
                  description
                    "Enable protection switching notifications";
                }
              }

              container continuity-check-interval {
                xr:xr-xml-map "cfm_cfg_sh:ContinuityCheckInterval";
                presence "Indicates a continuity-check-interval"+
                  " node is configured.";
                description
                  "Continuity Check Interval and Loss
                  Threshold.  Configuring the interval
                  enables Continuity Check.";
                leaf ccm-interval {
                  xr:xr-xml-map "cfm_cfg_sh:CCMInterval";
                  type dt1:Cfm-ccm-interval;
                  mandatory true;
                  description "CCM Interval";
                }
                leaf loss-threshold {
                  xr:xr-xml-map "cfm_cfg_sh:LossThreshold";
                  type uint32 {
                    range "2..255";
                  }
                  description "Loss Threshold (default 3)";
                }
              }

              container mip-auto-creation {
                xr:xr-xml-map "cfm_cfg_sh:MIPAutoCreation";
                presence "Indicates a mip-auto-creation node is"+
                  " configured.";
                description "MIP Auto-creation Policy";
                leaf mip-policy {
                  xr:xr-xml-map "cfm_cfg_sh:MIPPolicy";
                  type Cfm-mip-policy;
                  mandatory true;
                  description "MIP Auto-creation Policy";
                }
                leaf ccm-learning-enable {
                  xr:xr-xml-map "cfm_cfg_sh:CCMLearningEnable";
                  type empty;
                  description
                    "Enable CCM Learning at MIPs in this
                    service";
                }
              }

              container ais {
                xr:xr-xml-map "cfm_cfg_sh:AIS";
                description "Service specific AIS configuration";

                container transmission {
                  xr:xr-xml-map "cfm_cfg_sh:Transmission";
                  presence "enable transmission";
                  description "AIS transmission configuration";
                  leaf ais-interval {
                    xr:xr-xml-map "cfm_cfg_sh:AISInterval";
                    type dt1:Cfm-ais-interval;
                    description "AIS Interval";
                  }
                  leaf cos {
                    xr:xr-xml-map "cfm_cfg_sh:CoS";
                    type dt1:Cfm-cos-bits;
                    description "Class of Service bits";
                  }
                }
              }

              container cross-check {
                xr:xr-xml-map "cfm_cfg_sh:CrossCheck";
                description "Cross-check configuration";

                container cross-check-meps {
                  xr:xr-xml-map "cfm_cfg_sh:CrossCheckMEPTable";
                  description "Cross-check MEPs";

                  list cross-check-mep {
                    xr:xr-xml-map "cfm_cfg_sh:CrossCheckMEP";
                    key "mep-id";
                    description
                      "MEP ID and optional MAC Address for
                      Cross-check";
                    leaf mep-id {
                      xr:xr-xml-map "cfm_cfg_sh:MEP_ID";
                      type dt1:Cfm-mep-id;
                      description "MEP ID";
                    }
                    leaf enable-mac-address {
                      xr:xr-xml-map "cfm_cfg_sh:EnableMACAddress";
                      type empty;
                      description "MAC Address is specified";
                    }
                    leaf mac-address {
                      xr:xr-xml-map "cfm_cfg_sh:MACAddress";
                      type yang:mac-address;
                      description "MAC Address";
                    }
                  }
                }
                leaf auto {
                  xr:xr-xml-map "cfm_cfg_sh:Auto";
                  type empty;
                  description "Enable automatic MEP cross-check";
                }
              }

              container service-properties {
                xr:xr-xml-map "cfm_cfg_sh:ServiceProperties";
                presence "Indicates a service-properties node is"+
                  " configured.";
                description
                  "Fundamental properties of the service
                  (maintenance association)";
                leaf service-type {
                  xr:xr-xml-map "cfm_cfg_sh:ServiceType";
                  type Cfm-service;
                  mandatory true;
                  description "Type of Service";
                }
                leaf group-name {
                  xr:xr-xml-map "cfm_cfg_sh:GroupName";
                  type string;
                  description
                    "Bridge Group or Cross-connect Group, if
                    Service Type is BridgeDomain or
                    CrossConnect";
                }
                leaf switching-name {
                  xr:xr-xml-map "cfm_cfg_sh:SwitchingName";
                  type string;
                  description
                    "Bridge Domain or Cross-connect name, if
                    Service Type is BridgeDomain or
                    CrossConnect";
                }
                leaf ce-id {
                  xr:xr-xml-map "cfm_cfg_sh:CEId";
                  type uint32 {
                    range "1..16384";
                  }
                  description "Local Customer Edge Identifier";
                }
                leaf remote-ce-id {
                  xr:xr-xml-map "cfm_cfg_sh:RemoteCEId";
                  type uint32 {
                    range "1..16384";
                  }
                  description "Remote Customer Edge Identifier";
                }
                leaf short-ma-name-format {
                  xr:xr-xml-map "cfm_cfg_sh:ShortMANameFormat";
                  type Cfm-short-ma-name-format;
                  description "Short MA Name Format";
                }
                leaf short-ma-name-string {
                  xr:xr-xml-map "cfm_cfg_sh:ShortMANameString";
                  type xr:Cisco-ios-xr-string {
                    length "0..46";
                  }
                  description
                    "String Short MA Name, if format is String";
                }
                leaf short-ma-name-number {
                  xr:xr-xml-map "cfm_cfg_sh:ShortMANameNumber";
                  type uint32 {
                    range "0..65535";
                  }
                  description
                    "Numeric Short MA Name, if format is VlanID
                    or Number";
                }
                leaf short-ma-name-oui {
                  xr:xr-xml-map "cfm_cfg_sh:ShortMANameOUI";
                  type uint32 {
                    range "0..16777215";
                  }
                  description
                    "VPN OUI, if Short MA Name format is VPN_ID";
                }
                leaf short-ma-name-vpn-index {
                  xr:xr-xml-map "cfm_cfg_sh:ShortMANameVPNIndex";
                  type int32;
                  description
                    "VPN Index, if Short MA Name format is
                    VPN_ID";
                }
                leaf short-ma-name-icc {
                  xr:xr-xml-map "cfm_cfg_sh:ShortMANameICC";
                  type xr:Cisco-ios-xr-string {
                    length "0..7";
                  }
                  description
                    "ITU Carrier Code (ICC), if format is
                    ICCBased";
                }
                leaf short-ma-name-umc {
                  xr:xr-xml-map "cfm_cfg_sh:ShortMANameUMC";
                  type xr:Cisco-ios-xr-string {
                    length "0..13";
                  }
                  description
                    "Unique MEG ID Code (UMC), if format is
                    ICCBased";
                }
              }
              leaf maximum-meps {
                xr:xr-xml-map "cfm_cfg_sh:MaximumMEPs";
                type uint32 {
                  range "2..8190";
                }
                default "100";
                description
                  "Limit on the number of MEPs in the service";
              }
              leaf log-cross-check-errors {
                xr:xr-xml-map "cfm_cfg_sh:LogCrossCheckErrors";
                type empty;
                description
                  "Log Cross-check Errors detected for peer
                  MEPs";
              }
              leaf continuity-check-archive-hold-time {
                xr:xr-xml-map "cfm_cfg_sh:ContinuityCheckArchiveHol"+
                  "dTime";
                type uint32 {
                  range "1..65535";
                }
                default "100";
                description
                  "How long to store information for peer MEPs
                  that have timed out";
              }
              leaf tags {
                xr:xr-xml-map "cfm_cfg_sh:Tags";
                type uint32;
                description
                  "The number of tags to use when sending CFM
                  packets from up MEPs in this Service";
              }
              leaf log-continuity-check-state-changes {
                xr:xr-xml-map "cfm_cfg_sh:LogContinuityCheckStateCh"+
                  "anges";
                type empty;
                description "Log peer MEPs state changes";
              }
              leaf log-efd {
                xr:xr-xml-map "cfm_cfg_sh:LogEFD";
                type empty;
                description "Enable logging";
              }
              leaf continuity-check-auto-traceroute {
                xr:xr-xml-map "cfm_cfg_sh:ContinuityCheckAutoTracer"+
                  "oute";
                type empty;
                description
                  "Automatically trigger a traceroute when a
                  peer MEP times out";
              }
              leaf log-continuity-check-errors {
                xr:xr-xml-map "cfm_cfg_sh:LogContinuityCheckErrors";
                type empty;
                description "Log CCM Errors detected for peer MEPs";
              }
              leaf log-ais {
                xr:xr-xml-map "cfm_cfg_sh:LogAIS";
                type empty;
                description "Log receipt of AIS and LCK messages";
              }
              leaf service {
                xr:xr-xml-map "cfm_cfg_sh:Service";
                type string;
                description "Service (Maintenance Association)";
              }
            }
          }

          container domain-properties {
            xr:xr-xml-map "cfm_cfg_sh:DomainProperties";
            description "Fundamental properties of the domain";
            leaf level {
              xr:xr-xml-map "cfm_cfg_sh:Level";
              type dt1:Cfm-level;
              description "Maintenance Domain Level";
            }
            leaf mdid-format {
              xr:xr-xml-map "cfm_cfg_sh:MDIDFormat";
              type Cfm-mdid-format;
              description "Maintenance Domain ID Format";
            }
            leaf mdid-mac-address {
              xr:xr-xml-map "cfm_cfg_sh:MDID_MACAddress";
              when "../mdid-format = 'mac-address'" {
                description "../MDIDFormat = MACAddress";
              }
              type yang:mac-address;
              description
                "MAC Address, if MDID Format is MACAddress";
            }
            leaf mdid-number {
              xr:xr-xml-map "cfm_cfg_sh:MDIDNumber";
              when "../mdid-format = 'mac-address'" {
                description "../MDIDFormat = MACAddress";
              }
              type uint32 {
                range "0..65535";
              }
              description
                "Unsigned 16-bit Interger, if MDID Format is
                MACAddress";
            }
            leaf mdid-string {
              xr:xr-xml-map "cfm_cfg_sh:MDIDString";
              when "../mdid-format = 'dns-like' or ../mdid-format"+
                " = 'string'" {
                  description
                    "../MDIDFormat = DNSLike or ../MDIDFormat =
                    String";
              }
              type string {
                length "0..44";
              }
              description
                "String MDID, if MDID format is String or
                DNSLike";
            }
          }
          leaf domain {
            xr:xr-xml-map "cfm_cfg_sh:Domain";
            type string;
            description "Maintenance Domain";
          }
        }
      }
      leaf nv-satellite-sla-processing-disable {
        xr:xr-xml-map "cfm_cfg_sh:nVSatelliteSLAProcessingDisable";
        type empty;
        description
          "Disable processing of Ethernet SLA packets on
          nV Satellite devices";
      }
    }
    description
      "This augment extends the configuration data of
      'Cisco-IOS-XR-l2-eth-infra-cfg'";
  }

  augment "/a3:snmp/a3:notification" {

    container cfm {
      xr:xr-xml-map "dot1agmib_cfg:CFM";
      description
        "802.1ag Connectivity Fault Management MIB
        notification configuration";
      leaf enable {
        xr:xr-xml-map "dot1agmib_cfg:Enable";
        type empty;
        description
          "Enable 802.1ag Connectivity Fault Management
          MIB notifications";
      }
    }
    description
      "This augment extends the configuration data of
      'Cisco-IOS-XR-snmp-agent-cfg'";
  }
}
