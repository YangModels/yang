module Cisco-IOS-XR-ncs5500-pi-oper {

  /*** NAMESPACE / PREFIX DEFINITION ***/

  namespace "http://cisco.com/ns/yang/Cisco-IOS-XR-ncs5500-pi-oper";


  prefix "ncs5500-pi-oper";

  /*** LINKAGE (IMPORTS / INCLUDES) ***/

  import Cisco-IOS-XR-types { prefix "xr"; }

  import Cisco-IOS-XR-qos-ma-oper { prefix "a1"; }

  include Cisco-IOS-XR-ncs5500-pi-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ncs5500-pi package operational data.

     This YANG module augments the
       Cisco-IOS-XR-qos-ma-oper
     module with state data.

     Copyright (c) 2013-2015 by Cisco Systems, Inc.
     All rights reserved.";

  revision "2015-11-09" {
    description
      "IOS XR 6.0 revision.";
  }


  grouping STATISTICS {
    description "Common node of input, output";

    container statistics {
      xr:xr-xml-map "qos_ea_fretta_pi_oper:Statistics";
      description
        "Policy-map statistics operational data for an
        interface";
      uses POLICY-STATS;
    }
  }

  grouping INTERFACE {
    description
      "Common node of interface-table,
      nv-interface-table";

    list interface {
      xr:xr-xml-map "qos_ea_fretta_pi_oper:Interface";
      key "interface-name";
      description
        "QoS policy-map operational data for a particular
        interface";

      container nodes {
        xr:xr-xml-map "qos_ea_fretta_pi_oper:NodeTable";
        description "QoS policy-map node table";

        list node {
          xr:xr-xml-map "qos_ea_fretta_pi_oper:Node";
          key "node-name";
          description "QoS operational data for a particular node";
          leaf node-name {
            xr:xr-xml-map "qos_ea_fretta_pi_oper:NodeName";
            type xr:Node-id;
            description "The node";
          }
          uses INPUT;
          uses OUTPUT;
        }
      }
      leaf interface-name {
        xr:xr-xml-map "qos_ea_fretta_pi_oper:InterfaceName";
        type xr:Interface-name;
        description "Name of the interface";
      }
      uses INPUT;
      uses MEMBER-INTERFACE-TABLE;
      uses SATELLITE-ID-TABLE;
      uses OUTPUT;
    }
  }

  grouping INPUT {
    description
      "Common node of interface, node,
      nv-satellite-interface, satellite-id";

    container input {
      xr:xr-xml-map "qos_ea_fretta_pi_oper:Input";
      description
        "A piece of QoS policy-map operational data for
        an interface";
      uses STATISTICS;
    }
  }

  grouping VO-Q-STATS {
    description
      "Common node of locationvo-q, output-vo-q,
      vo-qoutput";

    container vo-q-stats {
      xr:xr-xml-map "qos_ea_fretta_pi_oper:VoQStats";
      description
        "VoQ statistics operational data for an interface";
      uses POLICY-STATS;
    }
  }

  grouping MEMBER-INTERFACE-TABLE {
    description "Common node of interface, nv-satellite-interface";

    container member-interfaces {
      xr:xr-xml-map "qos_ea_fretta_pi_oper:MemberInterfaceTable";
      description "QoS policy-map member interface table";

      list member-interface {
        xr:xr-xml-map "qos_ea_fretta_pi_oper:MemberInterface";
        key "interface-name";
        description "QoS policy-map member interface statistics";
        leaf interface-name {
          xr:xr-xml-map "qos_ea_fretta_pi_oper:InterfaceName";
          type xr:Interface-name;
          description "Name of member interface";
        }
        uses SATELLITE-ID-TABLE;
        uses OUTPUT;
      }
    }
  }

  grouping OUTPUT {
    description
      "Common node of member-interface, interface, node,
      nv-satellite-interface, satellite-id";

    container output {
      xr:xr-xml-map "qos_ea_fretta_pi_oper:Output";
      description
        "A piece of QoS policy-map operational data for
        an interface";
      uses STATISTICS;
    }
  }

  grouping SATELLITE-ID-TABLE {
    description "Common node of interface, member-interface";

    container satellite-ids {
      xr:xr-xml-map "qos_ea_fretta_pi_oper:SatelliteIDTable";
      description "Satellite ID information";

      list satellite-id {
        xr:xr-xml-map "qos_ea_fretta_pi_oper:SatelliteID";
        key "nv-satellite-id";
        description "Satellite ID information";
        leaf nv-satellite-id {
          xr:xr-xml-map "qos_ea_fretta_pi_oper:nVSatelliteID";
          type int32;
          description "Satellite ID";
        }
        uses INPUT;
        uses OUTPUT;
      }
    }
  }

  augment "/a1:qos/a1:qos-global/a1:vo-q/a1:vo-q-statistics"+
    "/a1:vo-q-table" {

    list vo-qinterface {
      xr:xr-xml-map "qos_ea_fretta_pi_oper:VoQinterface";
      key "interface-name";
      description
        "QoS policy-map operational data for a particular
        interface";

      container vo-q-member-interfaces {
        xr:xr-xml-map "qos_ea_fretta_pi_oper:VoQMemberInterfaceTabl"+
          "e";
        description "VoQ QoS policy-map member interface table";

        list vo-q-member-interface {
          xr:xr-xml-map "qos_ea_fretta_pi_oper:VoQMemberInterface";
          key "interface-name";
          description "QoS policy-map member interface statistics";

          container vo-qoutput {
            xr:xr-xml-map "qos_ea_fretta_pi_oper:VoQoutput";
            description "output VoQ interface";
            uses VO-Q-STATS;
          }
          leaf interface-name {
            xr:xr-xml-map "qos_ea_fretta_pi_oper:InterfaceName";
            type xr:Interface-name;
            description "Name of member interface";
          }
        }
      }

      container output-vo-q {
        xr:xr-xml-map "qos_ea_fretta_pi_oper:OutputVoQ";
        description "output VoQ interface";

        container locationvo-qs {
          xr:xr-xml-map "qos_ea_fretta_pi_oper:LocationTableVoQ";
          description "QoS policy-map location table";

          list locationvo-q {
            xr:xr-xml-map "qos_ea_fretta_pi_oper:LocationVoQ";
            key "node-name";
            description
              "QoS operational data for a particular
              location";
            leaf node-name {
              xr:xr-xml-map "qos_ea_fretta_pi_oper:NodeName";
              type xr:Node-id;
              description "The node";
            }
            uses VO-Q-STATS;
          }
        }
        uses VO-Q-STATS;
      }
      leaf interface-name {
        xr:xr-xml-map "qos_ea_fretta_pi_oper:InterfaceName";
        type xr:Interface-name;
        description "Name of the interface";
      }
    }
    description
      "This augment extends the operational data of
      'Cisco-IOS-XR-qos-ma-oper'";
  }

  augment "/a1:qos/a1:nv-satellite/a1:nv-satellite-statistics"+
    "/a1:nv-satellite-ids/a1:nv-satellite-id" {

    container nv-satellite-interfaces {
      xr:xr-xml-map "qos_ea_fretta_pi_oper:nVSatelliteInterfaceTabl"+
        "e";
      description
        "Operational data of satellite interface of a
        particular satellite";

      list nv-satellite-interface {
        xr:xr-xml-map "qos_ea_fretta_pi_oper:nVSatelliteInterface";
        key "interface-name";
        description
          "Operational data for a particular satellite
          interface";
        leaf interface-name {
          xr:xr-xml-map "qos_ea_fretta_pi_oper:InterfaceName";
          type xr:Interface-name;
          description "Name of the interface";
        }
        uses INPUT;
        uses MEMBER-INTERFACE-TABLE;
        uses OUTPUT;
      }
    }
    description
      "This augment extends the operational data of
      'Cisco-IOS-XR-qos-ma-oper'";
  }

  augment "/a1:qos/a1:nv-interface-table" {
    description
      "This augment extends the operational data of
      'Cisco-IOS-XR-qos-ma-oper'";
    uses INTERFACE;
  }

  augment "/a1:qos/a1:interface-table" {
    description
      "This augment extends the operational data of
      'Cisco-IOS-XR-qos-ma-oper'";
    uses INTERFACE;
  }

  augment "/a1:qos/a1:nodes/a1:node/a1:policy-map"+
    "/a1:interface-table" {
    description
      "This augment extends the operational data of
      'Cisco-IOS-XR-qos-ma-oper'";
    uses INTERFACE;
  }
}
