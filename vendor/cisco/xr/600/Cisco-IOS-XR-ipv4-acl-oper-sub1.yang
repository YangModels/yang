submodule Cisco-IOS-XR-ipv4-acl-oper-sub1 {

  belongs-to Cisco-IOS-XR-ipv4-acl-oper {
    prefix Cisco-IOS-XR-ipv4-acl-oper;
  }

  /*** LINKAGE (IMPORTS / INCLUDES) ***/

  import ietf-inet-types { prefix "inet"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ipv4-acl package operational data.

     Copyright (c) 2013-2015 by Cisco Systems, Inc.
     All rights reserved.";

  revision "2015-11-09" {
    description
      "IOS XR 6.0 revision.";
  }

  typedef Bag-acl-nh-status {
    type enumeration {
      enum not-present {
        description "State Not Present";
      }
      enum unknown {
        description "State Unknown";
      }
      enum down {
        description "State DOWN";
      }
      enum up {
        description "State UP";
      }
    }
    description "Bag acl nh status";
  }
  typedef Bag-acl-nh {
    type enumeration {
      enum nexthop-none {
        description "Next Hop None";
      }
      enum nexthop-default {
        description "Nexthop Default";
      }
      enum nexthop {
        description "Nexthop";
      }
    }
    description "Bag acl nh";
  }
  typedef Acl-ttl-operator {
    type Acl-port-operator;
    description "Acl ttl operator";
  }
  typedef Acl-plen-operator {
    type Acl-port-operator;
    description "Acl plen operator";
  }
  typedef Acl-tcpflags-operator {
    type enumeration {
      enum match-none {
        description "Match None";
      }
      enum match-all {
        description "Match All";
      }
      enum match-any-old {
        description "Match any old";
      }
      enum match-any {
        description "Match any";
      }
    }
    description "Acl tcpflags operator";
  }
  typedef Acl-log {
    type enumeration {
      enum log-none {
        value 0;
        description "Log None";
      }
      enum log {
        value 1;
        description "Log Regular";
      }
      enum log-input {
        value 2;
        description "Log Input";
      }
    }
    description "Acl log";
  }
  typedef Acl-port-operator {
    type enumeration {
      enum none {
        value 0;
        description "None";
      }
      enum eq {
        value 1;
        description "Equal";
      }
      enum gt {
        value 2;
        description "Greater than";
      }
      enum lt {
        value 3;
        description "Less than";
      }
      enum neq {
        value 4;
        description "Not Equal";
      }
      enum range {
        value 5;
        description "Range";
      }
      enum onebyte {
        value 8;
        description "One Byte";
      }
      enum twobytes {
        value 9;
        description "Two Bytes";
      }
    }
    description "Acl port operator";
  }
  typedef Acl-action {
    type enumeration {
      enum deny {
        value 0;
        description "Deny";
      }
      enum permit {
        value 1;
        description "Permit";
      }
      enum encrypt {
        value 2;
        description "Encrypt";
      }
      enum bypass {
        value 3;
        description "Bypass";
      }
      enum fallthrough {
        value 4;
        description "Fallthrough";
      }
      enum invalid {
        value 5;
        description "Invalid";
      }
    }
    description "Acl action";
  }
  typedef Acl-ace1 {
    type enumeration {
      enum normal {
        description "This is Normal ACE";
      }
      enum remark {
        description "This is Remark ACE";
      }
      enum abf {
        description "This is ABF ACE";
      }
    }
    description "ACE Types";
  }
  typedef Acl-ace {
    type Acl-ace1;
    description "ACE Types";
  }

  grouping IPV4-ACL-EDM-OOR-DETAIL {
    description "Oor deatil config BAG";
    leaf default-max-ac-ls {
      xr:xr-xml-map "ipv4_acl_edm:DefaultMaxACLs";
      type uint32;
      description "default max configurable acls";
    }
    leaf default-max-ac-es {
      xr:xr-xml-map "ipv4_acl_edm:DefaultMaxACEs";
      type uint32;
      description "default max configurable aces";
    }
    leaf current-configured-ac-ls {
      xr:xr-xml-map "ipv4_acl_edm:CurrentConfiguredACLs";
      type uint32;
      description "Current configured acls";
    }
    leaf current-configured-ac-es {
      xr:xr-xml-map "ipv4_acl_edm:CurrentConfiguredACEs";
      type uint32;
      description "Current configured aces";
    }
    leaf current-max-configurable-ac-ls {
      xr:xr-xml-map "ipv4_acl_edm:CurrentMaxConfigurableACLs";
      type uint32;
      description "Current max configurable acls";
    }
    leaf current-max-configurable-ac-es {
      xr:xr-xml-map "ipv4_acl_edm:CurrentMaxConfigurableACEs";
      type uint32;
      description "Current max configurable aces";
    }
    leaf max-configurable-ac-ls {
      xr:xr-xml-map "ipv4_acl_edm:MaxConfigurableACLs";
      type uint32;
      description "max configurable acls";
    }
    leaf max-configurable-ac-es {
      xr:xr-xml-map "ipv4_acl_edm:MaxConfigurableACEs";
      type uint32;
      description "max configurable aces";
    }
  }

  grouping IPV4-ACL-BAG-HW-NH-INFO {
    description "HW_NH_Info structure";
    leaf next-hop {
      xr:xr-xml-map "ipv4_acl_edm:NextHop";
      type uint32;
      description "The Next Hop";
    }
    leaf type {
      xr:xr-xml-map "ipv4_acl_edm:Type";
      type Bag-acl-nh;
      description "the next-hop type";
    }
    leaf vrf-name {
      xr:xr-xml-map "ipv4_acl_edm:VRFName";
      type string {
        length "0..32";
      }
      description "VRF name";
    }
  }

  grouping IPV4-ACL-BAG-NH-INFO {
    description "NH_Info structure";
    leaf next-hop {
      xr:xr-xml-map "ipv4_acl_edm:NextHop";
      type inet:ipv4-address;
      description "The next hop";
    }
    leaf track-name {
      xr:xr-xml-map "ipv4_acl_edm:TrackName";
      type string;
      description "Track name";
    }
    leaf status {
      xr:xr-xml-map "ipv4_acl_edm:Status";
      type Bag-acl-nh-status;
      description "The next hop status";
    }
    leaf is-acl-next-hop-exist {
      xr:xr-xml-map "ipv4_acl_edm:IsACLNextHopExist";
      type boolean;
      description "The nexthop exist";
    }
  }

  grouping IPV4-ACL-EDM-ACE {
    description "ACLE bag";

    container hw-next-hop-info {
      description "HW Next hop info";
      uses IPV4-ACL-BAG-HW-NH-INFO;
    }
    leaf item-type {
      xr:xr-xml-map "ipv4_acl_edm:ItemType";
      type Acl-ace;
      description "ACE type (acl, remark)";
    }
    leaf sequence {
      xr:xr-xml-map "ipv4_acl_edm:Sequence";
      type uint32;
      description "ACLE sequence number";
    }
    leaf grant {
      xr:xr-xml-map "ipv4_acl_edm:Grant";
      type Acl-action;
      description "Permit/deny";
    }
    leaf protocol {
      xr:xr-xml-map "ipv4_acl_edm:Protocol";
      type uint16;
      description "IPv4 protocol type";
    }
    leaf source-address {
      xr:xr-xml-map "ipv4_acl_edm:SourceAddress";
      type inet:ipv4-address;
      description "Source address";
    }
    leaf source-address-mask {
      xr:xr-xml-map "ipv4_acl_edm:SourceAddressMask";
      type inet:ipv4-address;
      description "Source mask";
    }
    leaf destination-address {
      xr:xr-xml-map "ipv4_acl_edm:DestinationAddress";
      type inet:ipv4-address;
      description "Destination address";
    }
    leaf destination-address-mask {
      xr:xr-xml-map "ipv4_acl_edm:DestinationAddressMask";
      type inet:ipv4-address;
      description "Destination mask";
    }
    leaf source-operator {
      xr:xr-xml-map "ipv4_acl_edm:SourceOperator";
      type Acl-port-operator;
      description "Source operator";
    }
    leaf source-port1 {
      xr:xr-xml-map "ipv4_acl_edm:SourcePort1";
      type uint16;
      description "Source port 1";
    }
    leaf source-port2 {
      xr:xr-xml-map "ipv4_acl_edm:SourcePort2";
      type uint16;
      description "Source port 2";
    }
    leaf sorce-operator {
      xr:xr-xml-map "ipv4_acl_edm:SorceOperator";
      type Acl-port-operator;
      description "Deprecated by Source operator";
    }
    leaf sorce-port1 {
      xr:xr-xml-map "ipv4_acl_edm:SorcePort1";
      type uint16;
      description "Deprecated by SourcePort1";
    }
    leaf sorce-port2 {
      xr:xr-xml-map "ipv4_acl_edm:SorcePort2";
      type uint16;
      description "Deprecated by SourcePort2";
    }
    leaf destination-operator {
      xr:xr-xml-map "ipv4_acl_edm:DestinationOperator";
      type Acl-port-operator;
      description "Destination operator";
    }
    leaf destination-port1 {
      xr:xr-xml-map "ipv4_acl_edm:DestinationPort1";
      type uint16;
      description "Destination port 1";
    }
    leaf destination-port2 {
      xr:xr-xml-map "ipv4_acl_edm:DestinationPort2";
      type uint16;
      description "Destination port 2";
    }
    leaf log-option {
      xr:xr-xml-map "ipv4_acl_edm:LogOption";
      type Acl-log;
      description "Log option";
    }
    leaf counter-name {
      xr:xr-xml-map "ipv4_acl_edm:CounterName";
      type string;
      description "Counter name";
    }
    leaf capture {
      xr:xr-xml-map "ipv4_acl_edm:Capture";
      type boolean;
      description "Capture option, TRUE if enabled";
    }
    leaf dscp-present {
      xr:xr-xml-map "ipv4_acl_edm:DSCPPresent";
      type boolean;
      description "DSCP present";
    }
    leaf dscp {
      xr:xr-xml-map "ipv4_acl_edm:DSCP";
      type uint8;
      description "DSCP or DSCP range start";
    }
    leaf dscp2 {
      xr:xr-xml-map "ipv4_acl_edm:DSCP2";
      type uint8;
      description "DSCP Range End";
    }
    leaf dscp-operator {
      xr:xr-xml-map "ipv4_acl_edm:DSCPOperator";
      type uint8;
      description "DSCP Operator";
    }
    leaf precedence-present {
      xr:xr-xml-map "ipv4_acl_edm:PrecedencePresent";
      type boolean;
      description "Precedence present";
    }
    leaf precedence {
      xr:xr-xml-map "ipv4_acl_edm:Precedence";
      type uint8;
      description "Precedence";
    }
    leaf tcp-flags-operator {
      xr:xr-xml-map "ipv4_acl_edm:TCPFlagsOperator";
      type Acl-tcpflags-operator;
      description "TCP flags operator";
    }
    leaf tcp-flags {
      xr:xr-xml-map "ipv4_acl_edm:TCPFlags";
      type uint8;
      description "TCP flags";
    }
    leaf tcp-flags-mask {
      xr:xr-xml-map "ipv4_acl_edm:TCPFlagsMask";
      type uint8;
      description "TCP flags mask";
    }
    leaf fragments {
      xr:xr-xml-map "ipv4_acl_edm:Fragments";
      type uint8;
      description "Fragments";
    }
    leaf port-length-operator {
      xr:xr-xml-map "ipv4_acl_edm:PortLengthOperator";
      type Acl-plen-operator;
      description "Port length operator";
    }
    leaf port-length1 {
      xr:xr-xml-map "ipv4_acl_edm:PortLength1";
      type uint16;
      description "Port length 1";
    }
    leaf port-length2 {
      xr:xr-xml-map "ipv4_acl_edm:PortLength2";
      type uint16;
      description "Port length 2";
    }
    leaf ttl-operator {
      xr:xr-xml-map "ipv4_acl_edm:TTLOperator";
      type Acl-ttl-operator;
      description "TTL operator";
    }
    leaf ttl1 {
      xr:xr-xml-map "ipv4_acl_edm:TTL1";
      type uint16;
      description "TTL 1";
    }
    leaf ttl2 {
      xr:xr-xml-map "ipv4_acl_edm:TTL2";
      type uint16;
      description "TTL 2";
    }
    leaf no-stats {
      xr:xr-xml-map "ipv4_acl_edm:NoStats";
      type boolean;
      description "No stats";
    }
    leaf hits {
      xr:xr-xml-map "ipv4_acl_edm:Hits";
      type uint64;
      description "Number of hits";
    }
    leaf is-icmp-off {
      xr:xr-xml-map "ipv4_acl_edm:IsICMPOff";
      type boolean;
      description "True if ICMP off";
    }
    leaf next-hop-type {
      xr:xr-xml-map "ipv4_acl_edm:NextHopType";
      type Bag-acl-nh;
      description "Next hop type";
    }
    leaf remark {
      xr:xr-xml-map "ipv4_acl_edm:Remark";
      type string;
      description "Remark String";
    }
    leaf dynamic {
      xr:xr-xml-map "ipv4_acl_edm:dynamic";
      type boolean;
      description "Is dynamic ACE";
    }
    leaf source-prefix-group {
      xr:xr-xml-map "ipv4_acl_edm:SourcePrefixGroup";
      type string;
      description "Source prefix object-group";
    }
    leaf destination-prefix-group {
      xr:xr-xml-map "ipv4_acl_edm:DestinationPrefixGroup";
      type string;
      description "Destination prefix object-group";
    }
    leaf source-port-group {
      xr:xr-xml-map "ipv4_acl_edm:SourcePortGroup";
      type string;
      description "Source port object-group";
    }
    leaf destination-port-group {
      xr:xr-xml-map "ipv4_acl_edm:DestinationPortGroup";
      type string;
      description "Destination port object-group";
    }
    leaf acl-name {
      xr:xr-xml-map "ipv4_acl_edm:ACLName";
      type string;
      description "ACL Name";
    }

    list next-hop-info {
      max-elements "3";
      description "Next hop info";
      uses IPV4-ACL-BAG-NH-INFO;
    }
  }

  grouping IPV4-PFX-EDM-ACE {
    description "Prefix list entry BAG";
    leaf item-type {
      xr:xr-xml-map "ipv4_acl_edm:ItemType";
      type Acl-ace;
      description "ACE type (prefix, remark)";
    }
    leaf sequence {
      xr:xr-xml-map "ipv4_acl_edm:Sequence";
      type uint32;
      description "ACLE sequence number";
    }
    leaf grant {
      xr:xr-xml-map "ipv4_acl_edm:Grant";
      type Acl-action;
      description "Grant value permit/deny ";
    }
    leaf prefix {
      xr:xr-xml-map "ipv4_acl_edm:Prefix";
      type inet:ipv4-address;
      description "Prefix";
    }
    leaf prefix-length {
      xr:xr-xml-map "ipv4_acl_edm:PrefixLength";
      type uint32;
      description "Prefix length ";
    }
    leaf operator {
      xr:xr-xml-map "ipv4_acl_edm:Operator";
      type Acl-port-operator;
      description "Port Operator";
    }
    leaf minimum-length {
      xr:xr-xml-map "ipv4_acl_edm:MinimumLength";
      type uint32;
      description "Min length";
    }
    leaf maximum-length {
      xr:xr-xml-map "ipv4_acl_edm:MaximumLength";
      type uint32;
      description "Maximum length";
    }
    leaf hits {
      xr:xr-xml-map "ipv4_acl_edm:Hits";
      type uint32;
      description "Number of hits";
    }
    leaf remark {
      xr:xr-xml-map "ipv4_acl_edm:Remark";
      type string;
      description "Remark String";
    }
    leaf acl-name {
      xr:xr-xml-map "ipv4_acl_edm:ACLName";
      type string;
      description "ACL Name";
    }
  }
}
