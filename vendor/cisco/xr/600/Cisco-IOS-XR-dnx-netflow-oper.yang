module Cisco-IOS-XR-dnx-netflow-oper {

  /*** NAMESPACE / PREFIX DEFINITION ***/

  namespace "http://cisco.com/ns/yang/Cisco-IOS-XR-dnx-netflow-oper";


  prefix "dnx-netflow-oper";

  /*** LINKAGE (IMPORTS / INCLUDES) ***/

  import Cisco-IOS-XR-types { prefix "xr"; }

  include Cisco-IOS-XR-dnx-netflow-oper-sub5 {
    revision-date 2015-11-09;
  }

  include Cisco-IOS-XR-dnx-netflow-oper-sub4 {
    revision-date 2015-11-09;
  }

  include Cisco-IOS-XR-dnx-netflow-oper-sub3 {
    revision-date 2015-11-09;
  }

  include Cisco-IOS-XR-dnx-netflow-oper-sub2 {
    revision-date 2015-11-09;
  }

  include Cisco-IOS-XR-dnx-netflow-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR dnx-netflow package operational data.

     This module contains definitions
     for the following management objects:
       net-flow: NetFlow operational data

     Copyright (c) 2013-2015 by Cisco Systems, Inc.
     All rights reserved.";

  revision "2015-11-09" {
    description
      "IOS XR 6.0 revision.";
  }


  container net-flow {
    xr:xr-xml-map "netflow_dnx_oper:NetFlow";
    config false;
    description "NetFlow operational data";

    container configuration {
      xr:xr-xml-map "netflow_dnx_oper:Configuration";
      description "NetFlow configuration information";

      container flow-monitor-maps {
        xr:xr-xml-map "netflow_dnx_oper:FlowMonitorMapTable";
        description "Flow monitor map configuration information";

        list flow-monitor-map {
          xr:xr-xml-map "netflow_dnx_oper:FlowMonitorMap";
          key "monitor-name";
          description "Flow monitor map information";
          leaf monitor-name {
            xr:xr-xml-map "netflow_dnx_oper:MonitorName";
            type xr:Cisco-ios-xr-string;
            description "Monitor name";
          }
          uses NFMGR-FMM-EDM-INFO;
        }
      }

      container flow-sampler-maps {
        xr:xr-xml-map "netflow_dnx_oper:FlowSamplerMapTable";
        description "Flow sampler map configuration information";

        list flow-sampler-map {
          xr:xr-xml-map "netflow_dnx_oper:FlowSamplerMap";
          key "sampler-name";
          description "Flow sampler map information";
          leaf sampler-name {
            xr:xr-xml-map "netflow_dnx_oper:SamplerName";
            type xr:Cisco-ios-xr-string;
            description "Sampler name";
          }
          uses NFMGR-FSM-EDM-INFO;
        }
      }

      container flow-exporter-maps {
        xr:xr-xml-map "netflow_dnx_oper:FlowExporterMapTable";
        description "Flow exporter map configuration information";

        list flow-exporter-map {
          xr:xr-xml-map "netflow_dnx_oper:FlowExporterMap";
          key "exporter-name";
          description "Flow exporter map information";
          leaf exporter-name {
            xr:xr-xml-map "netflow_dnx_oper:ExporterName";
            type xr:Cisco-ios-xr-string;
            description "Exporter name";
          }
          uses NFMGR-FEM-EDM-INFO;
        }
      }
    }

    container statistics {
      xr:xr-xml-map "netflow_dnx_oper:StatisticsTable";
      description "Node-specific NetFlow statistics information";

      list statistic {
        xr:xr-xml-map "netflow_dnx_oper:Statistics";
        key "node";
        description
          "NetFlow statistics information for a particular
          node";

        container producer {
          xr:xr-xml-map "netflow_dnx_oper:Producer";
          description "NetFlow producer statistics";

          container statistics {
            xr:xr-xml-map "netflow_dnx_oper:Statistics";
            description "Statistics information";
            uses NF-PRODUCER-STATS;
          }
        }

        container server {
          xr:xr-xml-map "netflow_dnx_oper:Server";
          description "NetFlow server statistics";

          container flow-exporters {
            xr:xr-xml-map "netflow_dnx_oper:FlowExporterTable";
            description "Flow exporter information";

            list flow-exporter {
              xr:xr-xml-map "netflow_dnx_oper:FlowExporter";
              key "exporter-name";
              description "Exporter information";

              container exporter {
                xr:xr-xml-map "netflow_dnx_oper:Exporter";
                description
                  "Statistics information for the exporter";
                uses NFSVR-SHOW-FLOW-EXPORTER-RESP-ARRAY;
              }
              leaf exporter-name {
                xr:xr-xml-map "netflow_dnx_oper:ExporterName";
                type xr:Cisco-ios-xr-string;
                description "Exporter name";
              }
            }
          }
        }
        leaf node {
          xr:xr-xml-map "netflow_dnx_oper:Node";
          type xr:Node-id;
          description "Node location";
        }
      }
    }
  }
}
