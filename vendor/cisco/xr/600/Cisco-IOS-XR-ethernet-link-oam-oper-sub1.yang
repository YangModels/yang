submodule Cisco-IOS-XR-ethernet-link-oam-oper-sub1 {

  belongs-to Cisco-IOS-XR-ethernet-link-oam-oper {
    prefix Cisco-IOS-XR-ethernet-link-oam-oper;
  }

  /*** LINKAGE (IMPORTS / INCLUDES) ***/

  import ietf-yang-types { prefix "yang"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ethernet-link-oam package operational data.

     Copyright (c) 2013-2015 by Cisco Systems, Inc.
     All rights reserved.";

  revision "2015-11-09" {
    description
      "IOS XR 6.0 revision.";
  }

  typedef Log-location {
    type enumeration {
      enum log-location-local {
        value 1;
        description "A local event";
      }
      enum log-location-remote {
        value 2;
        description "A remote event";
      }
    }
    description "The location of the event that caused a log entry";
  }
  typedef Log {
    type enumeration {
      enum log-type-symbol-event {
        value 1;
        description "Log entry for an errored symbol event";
      }
      enum log-type-period-event {
        value 2;
        description "Log entry for an errored frame period event";
      }
      enum log-type-frame-event {
        value 3;
        description "Log entry for an errored frame event";
      }
      enum log-type-secs-event {
        value 4;
        description
          "Log entry for an errored frame seconds summary
          event";
      }
      enum log-type-link-fault {
        value 256;
        description "Log entry for a link fault";
      }
      enum log-type-dying-gasp {
        value 257;
        description "Log entry for a dying gasp";
      }
      enum log-type-critical-event {
        value 258;
        description "Log entry for a critical event";
      }
    }
    description "The type of a log entry";
  }
  typedef Action {
    type enumeration {
      enum no-action {
        value 1;
        description "Disabled (do nothing)";
      }
      enum disable-interface {
        value 2;
        description "Disable the interface";
      }
      enum log {
        value 3;
        description "Log the event and do nothing else";
      }
      enum efd {
        value 4;
        description "EFD the interface";
      }
    }
    description "Actions supported by an OAM interface";
  }
  typedef Protocol-state {
    type enumeration {
      enum protocol-state-inactive {
        value 0;
        description "The protocol is in the INACTIVE state";
      }
      enum protocol-state-fault {
        value 1;
        description "The protocol is in the FAULT state";
      }
      enum protocol-state-active-send-local {
        value 2;
        description
          "The protocol is in the ACTIVE_SEND_LOCAL state";
      }
      enum protocol-state-passive-wait {
        value 3;
        description
          "The protocol is in the SEND_LOCAL_REMOTE state";
      }
      enum protocol-state-send-local-remote {
        value 4;
        description "The protocol is in the LOCAL_REMOTE state";
      }
      enum protocol-state-send-local-remote-ok {
        value 5;
        description "The protocol is in the LOCAL_REMOTE_OK state";
      }
      enum protocol-state-send-any {
        value 6;
        description "The protocol is in the SEND_ANY state";
      }
    }
    description "The state the protocol is in";
  }
  typedef Mode {
    type enumeration {
      enum passive {
        value 0;
        description "Passive mode";
      }
      enum active {
        value 1;
        description "Active mode";
      }
      enum dont-care {
        value 2;
        description "Don't care what the mode is";
      }
    }
    description "Mode of an OAM interface";
  }
  typedef Loopback-status {
    type enumeration {
      enum none {
        value 1;
        description "Loopback is not being performed";
      }
      enum initiating {
        value 2;
        description "Initiating master loopback";
      }
      enum master-loopback {
        value 3;
        description "In master loopback mode";
      }
      enum terminating {
        value 4;
        description "Terminating master loopback mode";
      }
      enum local-loopback {
        value 5;
        description "In slave loopback mode";
      }
      enum unknown {
        value 6;
        description "Parser and multiplexer combination unexpected";
      }
    }
    description "The loopback mode of an OAM interface";
  }
  typedef Operational-state {
    type enumeration {
      enum disabled {
        value 1;
        description "802.3 OAM is disabled";
      }
      enum link-fault {
        value 2;
        description "802.3 OAM has encountered a link fault";
      }
      enum passive-wait {
        value 3;
        description
          "Passive OAM entity waiting to see if peer is
          OAM capable";
      }
      enum active-send-local {
        value 4;
        description
          "Active OAM entity trying to determine if peer
          is OAM capable";
      }
      enum send-local-and-remote {
        value 5;
        description
          "OAM discovered peer but still to accept or
          reject peer config";
      }
      enum send-local-and-remote-ok {
        value 6;
        description "OAM peering is allowed by local device";
      }
      enum peering-locally-rejected {
        value 7;
        description "OAM peering rejected by local device";
      }
      enum peering-remotely-rejected {
        value 8;
        description "OAM peering rejected by remote device";
      }
      enum operational {
        value 9;
        description "802.3 OAM is operational";
      }
      enum operational-half-duplex {
        value 10;
        description "802.3 OAM is operating in half-duplex mode";
      }
    }
    description "Operational state of an interface";
  }

  grouping ELOD-STATS {
    description "Statistics for an 802.3 OAM interface";
    leaf information-tx {
      xr:xr-xml-map "elo_lib_status:InformationTX";
      type uint32;
      description "Number of information OAMPDUs transmitted";
    }
    leaf information-rx {
      xr:xr-xml-map "elo_lib_status:InformationRX";
      type uint32;
      description "Number of information OAMPDUs received";
    }
    leaf unique-event-notification-tx {
      xr:xr-xml-map "elo_lib_status:UniqueEventNotificationTX";
      type uint32;
      description
        "Number of unique event notification OAMPDUs
        transmitted";
    }
    leaf unique-event-notification-rx {
      xr:xr-xml-map "elo_lib_status:UniqueEventNotificationRX";
      type uint32;
      description
        "Number of unique event notification OAMPDUs
        received";
    }
    leaf duplicate-event-notification-tx {
      xr:xr-xml-map "elo_lib_status:DuplicateEventNotificationTX";
      type uint32;
      description
        "Number of duplicate event notification OAMPDUs
        transmitted";
    }
    leaf duplicate-event-notification-rx {
      xr:xr-xml-map "elo_lib_status:DuplicateEventNotificationRX";
      type uint32;
      description
        "Number of duplicate event notification OAMPDUs
        received";
    }
    leaf loopback-control-tx {
      xr:xr-xml-map "elo_lib_status:LoopbackControlTX";
      type uint32;
      description "Number of loopback control OAMPDUs transmitted";
    }
    leaf loopback-control-rx {
      xr:xr-xml-map "elo_lib_status:LoopbackControlRX";
      type uint32;
      description "Number of loopback control OAMPDUs received";
    }
    leaf variable-request-tx {
      xr:xr-xml-map "elo_lib_status:VariableRequestTX";
      type uint32;
      description "Number of variable request OAMPDUs transmitted";
    }
    leaf variable-request-rx {
      xr:xr-xml-map "elo_lib_status:VariableRequestRX";
      type uint32;
      description "Number of variable request OAMPDUs received";
    }
    leaf variable-response-tx {
      xr:xr-xml-map "elo_lib_status:VariableResponseTX";
      type uint32;
      description "Number of variable response OAMPDUs transmitted";
    }
    leaf variable-response-rx {
      xr:xr-xml-map "elo_lib_status:VariableResponseRX";
      type uint32;
      description "Number of variable response OAMPDUs received";
    }
    leaf org-specific-tx {
      xr:xr-xml-map "elo_lib_status:OrgSpecificTX";
      type uint32;
      description
        "Number of organization specific OAMPDUs
        transmitted";
    }
    leaf org-specific-rx {
      xr:xr-xml-map "elo_lib_status:OrgSpecificRX";
      type uint32;
      description
        "Number of organization specific OAMPDUs received";
    }
    leaf unsupported-codes-tx {
      xr:xr-xml-map "elo_lib_status:UnsupportedCodesTX";
      type uint32;
      description
        "Number of OAMPDUs with unsupported codes
        transmitted";
    }
    leaf unsupported-codes-rx {
      xr:xr-xml-map "elo_lib_status:UnsupportedCodesRX";
      type uint32;
      description
        "Number of OAMPDUs with unsupported codes
        received";
    }
    leaf frames-lost-due-to-oam {
      xr:xr-xml-map "elo_lib_status:FramesLostDueToOAM";
      type uint32;
      description "Number of frames lost due to OAM";
    }
    leaf fixed-frames-rx {
      xr:xr-xml-map "elo_lib_status:FixedFramesRX";
      type uint32;
      description "Number of RX frames 'fixed' by OAM";
    }
    leaf local-error-symbol-period-records {
      xr:xr-xml-map "elo_lib_status:LocalErrorSymbolPeriodRecords";
      type uint32;
      description "Number of local error symbol period records";
    }
    leaf local-error-frame-records {
      xr:xr-xml-map "elo_lib_status:LocalErrorFrameRecords";
      type uint32;
      description "Number of local error frame records";
    }
    leaf local-error-frame-period-records {
      xr:xr-xml-map "elo_lib_status:LocalErrorFramePeriodRecords";
      type uint32;
      description "Number of local error frame period records";
    }
    leaf local-error-frame-second-records {
      xr:xr-xml-map "elo_lib_status:LocalErrorFrameSecondRecords";
      type uint32;
      description "Number of local error frame second records";
    }
    leaf remote-error-symbol-period-records {
      xr:xr-xml-map "elo_lib_status:RemoteErrorSymbolPeriodRecords";
      type uint32;
      description "Number of remote error symbol period records";
    }
    leaf remote-error-frame-records {
      xr:xr-xml-map "elo_lib_status:RemoteErrorFrameRecords";
      type uint32;
      description "Number of remote error frame records";
    }
    leaf remote-error-frame-period-records {
      xr:xr-xml-map "elo_lib_status:RemoteErrorFramePeriodRecords";
      type uint32;
      description "Number of remote error frame period records";
    }
    leaf remote-error-frame-second-records {
      xr:xr-xml-map "elo_lib_status:RemoteErrorFrameSecondRecords";
      type uint32;
      description "Number of remote error frame second records";
    }
  }

  grouping ELOD-LOG-ENTRY {
    description "A single log entry";
    leaf index {
      xr:xr-xml-map "elo_lib_status:Index";
      type uint32;
      description "Index in the log entries table";
    }
    leaf handle {
      xr:xr-xml-map "elo_lib_status:Handle";
      type xr:Interface-name;
      description "Interface handle for this log entry";
    }
    leaf oui {
      xr:xr-xml-map "elo_lib_status:Oui";
      type yang:hex-string;
      description "OUI for the log entry";
    }
    leaf timestamp {
      xr:xr-xml-map "elo_lib_status:Timestamp";
      type uint64;
      description
        "Timestamp in hundredths of a second since unix
        epoch for when the event occurred";
    }
    leaf type {
      xr:xr-xml-map "elo_lib_status:Type";
      type Log;
      description "Type of event that this entry describes";
    }
    leaf location {
      xr:xr-xml-map "elo_lib_status:Location";
      type Log-location;
      description "Where the event occurred";
    }
    leaf event-total {
      xr:xr-xml-map "elo_lib_status:EventTotal";
      type uint32;
      description "Total number of times event has occurred";
    }
    leaf action-taken {
      xr:xr-xml-map "elo_lib_status:ActionTaken";
      type Action;
      description "Local action taken (If applicable)";
    }
    leaf window {
      xr:xr-xml-map "elo_lib_status:Window";
      type uint64;
      description "Size of the window (If applicable)";
    }
    leaf threshold {
      xr:xr-xml-map "elo_lib_status:Threshold";
      type uint64;
      description "Size of the threshold (If applicable)";
    }
    leaf local-high-threshold {
      xr:xr-xml-map "elo_lib_status:LocalHighThreshold";
      type uint64;
      description
        "Size of the local high threshold (If applicable)
        . For remote threshold events this is scaled for
        comparison with the Breaching Value. This is to
        account for different local and remote window
        sizes.";
    }
    leaf value {
      xr:xr-xml-map "elo_lib_status:Value";
      type uint64;
      description "Breaching value (If applicable)";
    }
    leaf running-total {
      xr:xr-xml-map "elo_lib_status:RunningTotal";
      type uint64;
      description
        "The running total number of errors seen since
        OAM was enabled on the interface(If applicable)";
    }
  }

  grouping ELOD-SUMMARY-INFO {
    description
      "Summary information for all 802.3 OAM sessions on
      a node";
    leaf interfaces {
      xr:xr-xml-map "elo_lib_status:Interfaces";
      type uint32;
      description
        "The number of interfaces with 802.3 OAM
        configured";
    }
    leaf port-down {
      xr:xr-xml-map "elo_lib_status:PortDown";
      type uint32;
      description "The number of interfaces in 'Port Down' state";
    }
    leaf passive-wait {
      xr:xr-xml-map "elo_lib_status:PassiveWait";
      type uint32;
      description
        "The number of interfaces in 'Passive Wait' state";
    }
    leaf active-send {
      xr:xr-xml-map "elo_lib_status:ActiveSend";
      type uint32;
      description "The number of interfaces in 'Active Send' state";
    }
    leaf evaluating {
      xr:xr-xml-map "elo_lib_status:Evaluating";
      type uint32;
      description "The number of interfaces in 'Evaluating' state";
    }
    leaf local-accept {
      xr:xr-xml-map "elo_lib_status:LocalAccept";
      type uint32;
      description
        "The number of interfaces in 'Local Accept' state";
    }
    leaf local-reject {
      xr:xr-xml-map "elo_lib_status:LocalReject";
      type uint32;
      description
        "The number of interfaces in 'Local Reject' state";
    }
    leaf remote-reject {
      xr:xr-xml-map "elo_lib_status:RemoteReject";
      type uint32;
      description
        "The number of interfaces in 'Remote Reject'
        state";
    }
    leaf operational {
      xr:xr-xml-map "elo_lib_status:Operational";
      type uint32;
      description "The number of interfaces in 'Operational' state";
    }
    leaf loopback-mode {
      xr:xr-xml-map "elo_lib_status:LoopbackMode";
      type uint32;
      description "The number of interfaces in loopback mode";
    }
    leaf miswired-connections {
      xr:xr-xml-map "elo_lib_status:MiswiredConnections";
      type uint32;
      description "The number of miswired connections";
    }
    leaf events {
      xr:xr-xml-map "elo_lib_status:Events";
      type uint64;
      description "The number of events recorded";
    }
    leaf local-events {
      xr:xr-xml-map "elo_lib_status:LocalEvents";
      type uint64;
      description "The number of local events recorded";
    }
    leaf local-symbol-period {
      xr:xr-xml-map "elo_lib_status:LocalSymbolPeriod";
      type uint64;
      description
        "The number of local symbol period events
        recorded";
    }
    leaf local-frame {
      xr:xr-xml-map "elo_lib_status:LocalFrame";
      type uint64;
      description "The mumber of local frame error events recorded";
    }
    leaf local-frame-period {
      xr:xr-xml-map "elo_lib_status:LocalFramePeriod";
      type uint64;
      description
        "The number of local frame period events recorded";
    }
    leaf local-frame-seconds {
      xr:xr-xml-map "elo_lib_status:LocalFrameSeconds";
      type uint64;
      description "The number of local frame second events recoded";
    }
    leaf remote-events {
      xr:xr-xml-map "elo_lib_status:RemoteEvents";
      type uint64;
      description "The number of remote events recorded";
    }
    leaf remote-symbol-period {
      xr:xr-xml-map "elo_lib_status:RemoteSymbolPeriod";
      type uint64;
      description
        "The number of remote symbol period events
        recorded";
    }
    leaf remote-frame {
      xr:xr-xml-map "elo_lib_status:RemoteFrame";
      type uint64;
      description
        "The mumber of remote frame error events recorded";
    }
    leaf remote-frame-period {
      xr:xr-xml-map "elo_lib_status:RemoteFramePeriod";
      type uint64;
      description
        "The number of remote frame period events
        recorded";
    }
    leaf remote-frame-seconds {
      xr:xr-xml-map "elo_lib_status:RemoteFrameSeconds";
      type uint64;
      description
        "The number of remote frame second events recoded";
    }
  }

  grouping ELOD-RUNNING-CONFIG {
    description
      "The configuration currently running on an
      interface";
    leaf fast-hello-interval-enabled {
      xr:xr-xml-map "elo_lib_status:FastHelloIntervalEnabled";
      type boolean;
      description "Is 100ms hello interval time enabled?";
    }
    leaf link-monitor-enabled {
      xr:xr-xml-map "elo_lib_status:LinkMonitorEnabled";
      type boolean;
      description "Is link monitoring enabled?";
    }
    leaf remote-loopback-enabled {
      xr:xr-xml-map "elo_lib_status:RemoteLoopbackEnabled";
      type boolean;
      description "Is remote loopback enabled?";
    }
    leaf mib-retrieval-enabled {
      xr:xr-xml-map "elo_lib_status:MIBRetrievalEnabled";
      type boolean;
      description "Is MIB retrieval enabled?";
    }
    leaf udlf-enabled {
      xr:xr-xml-map "elo_lib_status:UDLFEnabled";
      type boolean;
      description
        "Is uni-directional link-fault detection enabled?";
    }
    leaf mode {
      xr:xr-xml-map "elo_lib_status:Mode";
      type Mode;
      description "Configured mode";
    }
    leaf connection-timeout {
      xr:xr-xml-map "elo_lib_status:ConnectionTimeout";
      type uint8;
      description "Connection timeout";
    }
    leaf symbol-period-window {
      xr:xr-xml-map "elo_lib_status:SymbolPeriodWindow";
      type uint32;
      description "Symbol period event window size";
    }
    leaf symbol-period-threshold-low {
      xr:xr-xml-map "elo_lib_status:SymbolPeriodThresholdLow";
      type uint64;
      description "Low symbol period event threshold";
    }
    leaf symbol-period-threshold-high {
      xr:xr-xml-map "elo_lib_status:SymbolPeriodThresholdHigh";
      type uint64;
      description "High symbol period event threshold";
    }
    leaf frame-window {
      xr:xr-xml-map "elo_lib_status:FrameWindow";
      type uint32;
      description "Frame event window size";
    }
    leaf frame-threshold-low {
      xr:xr-xml-map "elo_lib_status:FrameThresholdLow";
      type uint32;
      description "Frame event low threshold";
    }
    leaf frame-threshold-high {
      xr:xr-xml-map "elo_lib_status:FrameThresholdHigh";
      type uint32;
      description "Frame event high threshold";
    }
    leaf frame-period-window {
      xr:xr-xml-map "elo_lib_status:FramePeriodWindow";
      type uint32;
      description "Frame period event window size";
    }
    leaf frame-period-threshold-low {
      xr:xr-xml-map "elo_lib_status:FramePeriodThresholdLow";
      type uint32;
      description "Frame period event low threshold";
    }
    leaf frame-period-threshold-high {
      xr:xr-xml-map "elo_lib_status:FramePeriodThresholdHigh";
      type uint32;
      description "Frame period event high threshold";
    }
    leaf frame-seconds-window {
      xr:xr-xml-map "elo_lib_status:FrameSecondsWindow";
      type uint32;
      units "second";
      description "Frame seconds event high threshold";
    }
    leaf frame-seconds-threshold-low {
      xr:xr-xml-map "elo_lib_status:FrameSecondsThresholdLow";
      type uint32;
      units "second";
      description "Frame seconds event high threshold";
    }
    leaf frame-seconds-threshold-high {
      xr:xr-xml-map "elo_lib_status:FrameSecondsThresholdHigh";
      type uint32;
      units "second";
      description "Frame seconds event high threshold";
    }
    leaf high-threshold-action {
      xr:xr-xml-map "elo_lib_status:HighThresholdAction";
      type Action;
      description
        "Action to perform when a high threshold is
        breached";
    }
    leaf link-fault-action {
      xr:xr-xml-map "elo_lib_status:LinkFaultAction";
      type Action;
      description "Action to perform when a link fault occurs";
    }
    leaf dying-gasp-action {
      xr:xr-xml-map "elo_lib_status:DyingGaspAction";
      type Action;
      description "Action to perform when a dying gasp occurs";
    }
    leaf critical-event-action {
      xr:xr-xml-map "elo_lib_status:CriticalEventAction";
      type Action;
      description "Action to perform when a critical event occurs";
    }
    leaf discovery-timeout-action {
      xr:xr-xml-map "elo_lib_status:DiscoveryTimeoutAction";
      type Action;
      description
        "Action to perform when a discovery timeout
        occurs";
    }
    leaf capabilities-conflict-action {
      xr:xr-xml-map "elo_lib_status:CapabilitiesConflictAction";
      type Action;
      description
        "Action to perform when a capabilities conflict
        occurs";
    }
    leaf wiring-conflict-action {
      xr:xr-xml-map "elo_lib_status:WiringConflictAction";
      type Action;
      description "Action to perform when a wiring conflict occurs";
    }
    leaf session-up-action {
      xr:xr-xml-map "elo_lib_status:SessionUpAction";
      type Action;
      description "Action to perform when a session comes up";
    }
    leaf session-down-action {
      xr:xr-xml-map "elo_lib_status:SessionDownAction";
      type Action;
      description "Action to perform when a session comes down";
    }
    leaf remote-loopback-action {
      xr:xr-xml-map "elo_lib_status:RemoteLoopbackAction";
      type Action;
      description
        "Action to perform when a session enters or exits
        remote loopback";
    }
    leaf require-remote-mode {
      xr:xr-xml-map "elo_lib_status:RequireRemoteMode";
      type Mode;
      description "The mode that is required of the remote peer";
    }
    leaf require-remote-mib-retrieval {
      xr:xr-xml-map "elo_lib_status:RequireRemoteMIBRetrieval";
      type boolean;
      description
        "Require the remote peer to support MIB retrieval";
    }
    leaf require-loopback {
      xr:xr-xml-map "elo_lib_status:RequireLoopback";
      type boolean;
      description
        "Require the remote peer to support loopback mode";
    }
    leaf require-link-monitoring {
      xr:xr-xml-map "elo_lib_status:RequireLinkMonitoring";
      type boolean;
      description
        "Require the remote peer to support link
        monitoring";
    }
    leaf fast-hello-interval-enabled-overridden {
      xr:xr-xml-map "elo_lib_status:FastHelloIntervalEnabledOverrid"+
        "den";
      type boolean;
      description
        "Is this configuration information an interface
        override?";
    }
    leaf link-monitoring-enabled-overridden {
      xr:xr-xml-map "elo_lib_status:LinkMonitoringEnabledOverridden";
      type boolean;
      description
        "Is this configuration information an interface
        override?";
    }
    leaf remote-loopback-enabled-overridden {
      xr:xr-xml-map "elo_lib_status:RemoteLoopbackEnabledOverridden";
      type boolean;
      description
        "Is this configuration information an interface
        override?";
    }
    leaf mib-retrieval-enabled-overridden {
      xr:xr-xml-map "elo_lib_status:MIBRetrievalEnabledOverridden";
      type boolean;
      description
        "Is this configuration information an interface
        override?";
    }
    leaf udlf-enabled-overridden {
      xr:xr-xml-map "elo_lib_status:UDLFEnabledOverridden";
      type boolean;
      description
        "Is this configuration information an interface
        override?";
    }
    leaf mode-overridden {
      xr:xr-xml-map "elo_lib_status:ModeOverridden";
      type boolean;
      description
        "Is this configuration information an interface
        override?";
    }
    leaf connection-timeout-overridden {
      xr:xr-xml-map "elo_lib_status:ConnectionTimeoutOverridden";
      type boolean;
      description
        "Is this configuration information an interface
        override?";
    }
    leaf symbol-period-window-overridden {
      xr:xr-xml-map "elo_lib_status:SymbolPeriodWindowOverridden";
      type boolean;
      description
        "Is this configuration information an interface
        override?";
    }
    leaf symbol-period-threshold-low-overridden {
      xr:xr-xml-map "elo_lib_status:SymbolPeriodThresholdLowOverrid"+
        "den";
      type boolean;
      description
        "Is this configuration information an interface
        override?";
    }
    leaf symbol-period-threshold-high-overridden {
      xr:xr-xml-map "elo_lib_status:SymbolPeriodThresholdHighOverri"+
        "dden";
      type boolean;
      description
        "Is this configuration information an interface
        override?";
    }
    leaf frame-window-overridden {
      xr:xr-xml-map "elo_lib_status:FrameWindowOverridden";
      type boolean;
      description
        "Is this configuration information an interface
        override?";
    }
    leaf frame-threshold-low-overridden {
      xr:xr-xml-map "elo_lib_status:FrameThresholdLowOverridden";
      type boolean;
      description
        "Is this configuration information an interface
        override?";
    }
    leaf frame-threshold-high-overridden {
      xr:xr-xml-map "elo_lib_status:FrameThresholdHighOverridden";
      type boolean;
      description
        "Is this configuration information an interface
        override?";
    }
    leaf frame-period-window-overridden {
      xr:xr-xml-map "elo_lib_status:FramePeriodWindowOverridden";
      type boolean;
      description
        "Is this configuration information an interface
        override?";
    }
    leaf frame-period-threshold-low-overridden {
      xr:xr-xml-map "elo_lib_status:FramePeriodThresholdLowOverridd"+
        "en";
      type boolean;
      description
        "Is this configuration information an interface
        override?";
    }
    leaf frame-period-threshold-high-overridden {
      xr:xr-xml-map "elo_lib_status:FramePeriodThresholdHighOverrid"+
        "den";
      type boolean;
      description
        "Is this configuration information an interface
        override?";
    }
    leaf frame-seconds-window-overridden {
      xr:xr-xml-map "elo_lib_status:FrameSecondsWindowOverridden";
      type boolean;
      description
        "Is this configuration information an interface
        override?";
    }
    leaf frame-seconds-threshold-low-overridden {
      xr:xr-xml-map "elo_lib_status:FrameSecondsThresholdLowOverrid"+
        "den";
      type boolean;
      description
        "Is this configuration information an interface
        override?";
    }
    leaf frame-seconds-threshold-high-overridden {
      xr:xr-xml-map "elo_lib_status:FrameSecondsThresholdHighOverri"+
        "dden";
      type boolean;
      description
        "Is this configuration information an interface
        override?";
    }
    leaf high-threshold-action-overridden {
      xr:xr-xml-map "elo_lib_status:HighThresholdActionOverridden";
      type boolean;
      description
        "Is this configuration information an interface
        override?";
    }
    leaf link-fault-action-overridden {
      xr:xr-xml-map "elo_lib_status:LinkFaultActionOverridden";
      type boolean;
      description
        "Is this configuration information an interface
        override?";
    }
    leaf dying-gasp-action-overridden {
      xr:xr-xml-map "elo_lib_status:DyingGaspActionOverridden";
      type boolean;
      description
        "Is this configuration information an interface
        override?";
    }
    leaf critical-event-action-overridden {
      xr:xr-xml-map "elo_lib_status:CriticalEventActionOverridden";
      type boolean;
      description
        "Is this configuration information an interface
        override?";
    }
    leaf discovery-timeout-action-overridden {
      xr:xr-xml-map "elo_lib_status:DiscoveryTimeoutActionOverridde"+
        "n";
      type boolean;
      description
        "Is this configuration information an interface
        override?";
    }
    leaf capabilities-conflict-action-overridden {
      xr:xr-xml-map "elo_lib_status:CapabilitiesConflictActionOverr"+
        "idden";
      type boolean;
      description
        "Is this configuration information an interface
        override?";
    }
    leaf wiring-conflict-action-overridden {
      xr:xr-xml-map "elo_lib_status:WiringConflictActionOverridden";
      type boolean;
      description
        "Is this configuration information an interface
        override?";
    }
    leaf session-down-action-overridden {
      xr:xr-xml-map "elo_lib_status:SessionDownActionOverridden";
      type boolean;
      description
        "Is this configuration information an interface
        override?";
    }
    leaf session-up-action-overridden {
      xr:xr-xml-map "elo_lib_status:SessionUpActionOverridden";
      type boolean;
      description
        "Is this configuration information an interface
        override?";
    }
    leaf remote-loopback-action-overridden {
      xr:xr-xml-map "elo_lib_status:RemoteLoopbackActionOverridden";
      type boolean;
      description
        "Is this configuration information an interface
        override?";
    }
    leaf require-mode-overridden {
      xr:xr-xml-map "elo_lib_status:RequireModeOverridden";
      type boolean;
      description
        "Is this configuration information an interface
        override?";
    }
    leaf require-mib-retrieval-overridden {
      xr:xr-xml-map "elo_lib_status:RequireMIBRetrievalOverridden";
      type boolean;
      description
        "Is this configuration information an interface
        override?";
    }
    leaf require-loopback-overridden {
      xr:xr-xml-map "elo_lib_status:RequireLoopbackOverridden";
      type boolean;
      description
        "Is this configuration information an interface
        override?";
    }
    leaf require-link-monitoring-overridden {
      xr:xr-xml-map "elo_lib_status:RequireLinkMonitoringOverridden";
      type boolean;
      description
        "Is this configuration information an interface
        override?";
    }
  }

  grouping EFD-TRIGGERS {
    description
      "Triggers currently causing the interface to be
      brought down using EFD";
    leaf link-fault-received {
      xr:xr-xml-map "elo_lib_status:LinkFaultReceived";
      type boolean;
      description "Link-fault messages being received";
    }
    leaf discovery-timed-out {
      xr:xr-xml-map "elo_lib_status:DiscoveryTimedOut";
      type boolean;
      description "The discovery process has timed out";
    }
    leaf capabilities-conflict {
      xr:xr-xml-map "elo_lib_status:CapabilitiesConflict";
      type boolean;
      description "A capabilities conflict has been detected";
    }
    leaf wiring-conflict {
      xr:xr-xml-map "elo_lib_status:WiringConflict";
      type boolean;
      description "A wiring conflict has been detected";
    }
    leaf session-down {
      xr:xr-xml-map "elo_lib_status:SessionDown";
      type boolean;
      description "The 802.3 OAM session is down";
    }
  }

  grouping ELOD-ERRORS {
    description
      "Most recent error information for an 802.3 OAM
      interface";
    leaf pfi-reason {
      xr:xr-xml-map "elo_lib_status:PFIReason";
      type string;
      description
        "Reason for the Interface Management error (if
        applicable)";
    }
    leaf pfi-error-code {
      xr:xr-xml-map "elo_lib_status:PfiErrorCode";
      type uint32;
      description "The Interface Management error/success code";
    }
    leaf platform-reason {
      xr:xr-xml-map "elo_lib_status:PlatformReason";
      type string;
      description "Reason for the platform error (if applicable)";
    }
    leaf platform-error-code {
      xr:xr-xml-map "elo_lib_status:PlatformErrorCode";
      type uint32;
      description "The platform error/success code";
    }
    leaf spio-reason {
      xr:xr-xml-map "elo_lib_status:SPIOReason";
      type string;
      description "Reason for the Packet I/O error (if applicable)";
    }
    leaf spio-error-code {
      xr:xr-xml-map "elo_lib_status:SPIOErrorCode";
      type uint32;
      description "The Packet I/O error/success code";
    }
    leaf epi-reason {
      xr:xr-xml-map "elo_lib_status:EPIReason";
      type string;
      description "Reason for the Packet error (if applicable)";
    }
    leaf epi-error-code {
      xr:xr-xml-map "elo_lib_status:EPIErrorCode";
      type uint32;
      description "The Packet error/success code";
    }
    leaf caps-add-reason {
      xr:xr-xml-map "elo_lib_status:CapsAddReason";
      type string;
      description "Reason for the caps add error (if applicable)";
    }
    leaf caps-add-error-code {
      xr:xr-xml-map "elo_lib_status:CapsAddErrorCode";
      type uint32;
      description "The caps add error/success code";
    }
  }

  grouping ELOD-INTERFACE-STATE {
    description "The state of an 802.3 OAM interface";

    container errors {
      description "The errors that have occurred on this interface";
      uses ELOD-ERRORS;
    }

    container efd-triggers {
      description "Any present EFD triggers";
      uses EFD-TRIGGERS;
    }
    leaf protocol-code {
      xr:xr-xml-map "elo_lib_status:ProtocolCode";
      type Protocol-state;
      description "The state the protocol is in";
    }
    leaf rx-fault {
      xr:xr-xml-map "elo_lib_status:RXFault";
      type boolean;
      description "Has a uni-directional link-fault been detected?";
    }
    leaf local-mwd-key {
      xr:xr-xml-map "elo_lib_status:LocalMWDKey";
      type uint32;
      description "The local MWD key";
    }
    leaf remote-mwd-key-present {
      xr:xr-xml-map "elo_lib_status:RemoteMWDKeyPresent";
      type boolean;
      description "Does the remote side have an MWD key?";
    }
    leaf remote-mwd-key {
      xr:xr-xml-map "elo_lib_status:RemoteMWDKey";
      type uint32;
      description "The remote MWD key";
    }
  }

  grouping ELOD-DISCOVERY-INFO {
    description "The results of a 'get discovery info' query";
    leaf name {
      xr:xr-xml-map "elo_lib_status:Name";
      type string;
      description "Interface Name";
    }
    leaf operational-status {
      xr:xr-xml-map "elo_lib_status:OperationalStatus";
      type Operational-state;
      description "Operational status";
    }
    leaf loopback-mode {
      xr:xr-xml-map "elo_lib_status:LoopbackMode";
      type Loopback-status;
      description "The loopback mode the interface is in";
    }
    leaf local-mode {
      xr:xr-xml-map "elo_lib_status:LocalMode";
      type Mode;
      description "Local Mode (passive/active)";
    }
    leaf miswired {
      xr:xr-xml-map "elo_lib_status:Miswired";
      type boolean;
      description "Has the interface mis-wired?";
    }
    leaf local-mwd-key {
      xr:xr-xml-map "elo_lib_status:LocalMWDKey";
      type uint32;
      description "Local Mis-wiring Detection key";
    }
    leaf local-function-unidirectional {
      xr:xr-xml-map "elo_lib_status:LocalFunctionUnidirectional";
      type boolean;
      description "Local Unidirectional support";
    }
    leaf local-function-loopback {
      xr:xr-xml-map "elo_lib_status:LocalFunctionLoopback";
      type boolean;
      description "Local loopback support";
    }
    leaf local-function-event {
      xr:xr-xml-map "elo_lib_status:LocalFunctionEvent";
      type boolean;
      description "Local event support";
    }
    leaf local-functionvariable {
      xr:xr-xml-map "elo_lib_status:LocalFunctionVariable";
      type boolean;
      description "Local variable retreival support";
    }
    leaf local-revision {
      xr:xr-xml-map "elo_lib_status:LocalRevision";
      type uint32;
      description "Local revision";
    }
    leaf local-mtu {
      xr:xr-xml-map "elo_lib_status:LocalMTU";
      type uint32;
      description "Local MTU";
    }
    leaf local-operational {
      xr:xr-xml-map "elo_lib_status:LocalOperational";
      type boolean;
      description "Is the local OAM session operational?";
    }
    leaf local-evaluating {
      xr:xr-xml-map "elo_lib_status:LocalEvaluating";
      type boolean;
      description "Is the local OAM session evaluating?";
    }
    leaf remote-mode {
      xr:xr-xml-map "elo_lib_status:RemoteMode";
      type Mode;
      description "Remote Mode (passive/active)";
    }
    leaf remote-unidirectional {
      xr:xr-xml-map "elo_lib_status:RemoteUnidirectional";
      type boolean;
      description "Remote unidirectional support";
    }
    leaf remote-loopback {
      xr:xr-xml-map "elo_lib_status:RemoteLoopback";
      type boolean;
      description "Remote loopback support";
    }
    leaf remote-event {
      xr:xr-xml-map "elo_lib_status:RemoteEvent";
      type boolean;
      description "Remote event support";
    }
    leaf remote-variable {
      xr:xr-xml-map "elo_lib_status:RemoteVariable";
      type boolean;
      description "Remote variable retreival support";
    }
    leaf remote-mtu {
      xr:xr-xml-map "elo_lib_status:RemoteMTU";
      type uint32;
      description "Remote MTU";
    }
    leaf remote-mac-address {
      xr:xr-xml-map "elo_lib_status:RemoteMACAddress";
      type yang:mac-address;
      description "Remote MAC address";
    }
    leaf remote-vendor-oui {
      xr:xr-xml-map "elo_lib_status:RemoteVendorOUI";
      type yang:hex-string;
      description "Remote vendor OUI";
    }
    leaf remote-revision {
      xr:xr-xml-map "elo_lib_status:RemoteRevision";
      type uint16;
      description "Remote revision";
    }
    leaf remote-vendor-info {
      xr:xr-xml-map "elo_lib_status:RemoteVendorInfo";
      type uint32;
      description "Remote vendor info";
    }
    leaf remote-mwd-key {
      xr:xr-xml-map "elo_lib_status:RemoteMWDKey";
      type uint32;
      description "Remote Mis-wiring Detection key";
    }
    leaf operational-status-valid {
      xr:xr-xml-map "elo_lib_status:OperationalStatusValid";
      type boolean;
      description "Has this value been received successfully?";
    }
    leaf loopback-mode-valid {
      xr:xr-xml-map "elo_lib_status:LoopbackModeValid";
      type boolean;
      description "Has this value been received successfully?";
    }
    leaf local-mode-valid {
      xr:xr-xml-map "elo_lib_status:LocalModeValid";
      type boolean;
      description "Has this value been received successfully?";
    }
    leaf miswired-valid {
      xr:xr-xml-map "elo_lib_status:MiswiredValid";
      type boolean;
      description "Has this value been received successfully?";
    }
    leaf local-mwd-key-valid {
      xr:xr-xml-map "elo_lib_status:LocalMWDKeyValid";
      type boolean;
      description "Has this value been received successfully?";
    }
    leaf local-function-unidirectional-valid {
      xr:xr-xml-map "elo_lib_status:LocalFunctionUnidirectionalVali"+
        "d";
      type boolean;
      description "Has this value been received successfully?";
    }
    leaf local-function-loopback-valid {
      xr:xr-xml-map "elo_lib_status:LocalFunctionLoopbackValid";
      type boolean;
      description "Has this value been received successfully?";
    }
    leaf local-function-event-valid {
      xr:xr-xml-map "elo_lib_status:LocalFunctionEventValid";
      type boolean;
      description "Has this value been received successfully?";
    }
    leaf local-functionvariable-valid {
      xr:xr-xml-map "elo_lib_status:LocalFunctionVariableValid";
      type boolean;
      description "Has this value been received successfully?";
    }
    leaf local-revisionvalid {
      xr:xr-xml-map "elo_lib_status:LocalRevisionValid";
      type boolean;
      description "Has this value been received successfully?";
    }
    leaf local-mtu-valid {
      xr:xr-xml-map "elo_lib_status:LocalMTUValid";
      type boolean;
      description "Has this value been received successfully?";
    }
    leaf remote-mode-valid {
      xr:xr-xml-map "elo_lib_status:RemoteModeValid";
      type boolean;
      description "Has this value been received successfully?";
    }
    leaf remote-unidirectional-valid {
      xr:xr-xml-map "elo_lib_status:RemoteUnidirectionalValid";
      type boolean;
      description "Has this value been received successfully?";
    }
    leaf remote-loopback-valid {
      xr:xr-xml-map "elo_lib_status:RemoteLoopbackValid";
      type boolean;
      description "Has this value been received successfully?";
    }
    leaf remote-event-valid {
      xr:xr-xml-map "elo_lib_status:RemoteEventValid";
      type boolean;
      description "Has this value been received successfully?";
    }
    leaf remote-variable-valid {
      xr:xr-xml-map "elo_lib_status:RemoteVariableValid";
      type boolean;
      description "Has this value been received successfully?";
    }
    leaf remote-mtu-valid {
      xr:xr-xml-map "elo_lib_status:RemoteMTUValid";
      type boolean;
      description "Has this value been received successfully?";
    }
    leaf remote-mac-address-valid {
      xr:xr-xml-map "elo_lib_status:RemoteMACAddressValid";
      type boolean;
      description "Has this value been received successfully?";
    }
    leaf remote-vendor-oui-valid {
      xr:xr-xml-map "elo_lib_status:RemoteVendorOUIValid";
      type boolean;
      description "Has this value been received successfully?";
    }
    leaf remote-revisionvalid {
      xr:xr-xml-map "elo_lib_status:RemoteRevisionValid";
      type boolean;
      description "Has this value been received successfully?";
    }
    leaf remote-vendor-info-valid {
      xr:xr-xml-map "elo_lib_status:RemoteVendorInfoValid";
      type boolean;
      description "Has this value been received successfully?";
    }
    leaf remote-mwd-key-valid {
      xr:xr-xml-map "elo_lib_status:RemoteMWDKeyValid";
      type boolean;
      description "Has this value been received successfully?";
    }
  }
}
