module Cisco-IOS-XR-um-hw-module-l3-cfg {
  namespace "http://cisco.com/ns/yang/Cisco-IOS-XR-um-hw-module-l3-cfg";
  prefix um-hw-module-l3-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR hw-module-l3 package configuration.
     
     This YANG module augments the
     modules with configuration data.
     
     Copyright (c) 2022 by Cisco Systems, Inc.
     All rights reserved.";

  revision 2022-09-16 {
    description
      "Added leaf for per-prefix-egress-stats
       2022-09-08
         Added leaf for sharedlspa, caching and modified pathname for ler and lsr";
    semver:module-version "1.1.0";
  }
  revision 2020-05-08 {
    description
      "Initial release";
    semver:module-version "1.0.0";
  }

  container hw-module {
    description
      "Configure h/w module";
    container l3 {
      description
        "Configure l3 ";
      container feature {
        description
          "Configure l3 features";
        leaf caching {
          type enumeration {
            enum "disable" {
              value 7;
              description
                "Disable fast convergence caching feature.";
            }
          }
          description
            "Configure fast convergence caching feature";
        }
        leaf ler {
          type enumeration {
            enum "disable" {
              value 3;
              description
                "Disable LER feature";
            }
          }
          description
            "Configure LER feature";
        }
        leaf lsr {
          type enumeration {
            enum "disable" {
              value 5;
              description
                "Disable LSR feature";
            }
          }
          description
            "Configure LSR feature";
        }
        leaf mpls-over-udp-decap {
          type enumeration {
            enum "enable" {
              value 1;
              description
                "Enable MPLS-over-UDP decap feature";
            }
          }
          description
            "Configure MPLS-over-UDP decap feature";
        }
        container pbr {
          description
            "Configure PBR feature";
          leaf sixpe {
            type enumeration {
              enum "enable" {
                value 1;
                description
                  "Enable BGP FS 6PE feature";
              }
            }
            description
              "Configure BGP FS 6pe";
          }
          leaf hash {
            type enumeration {
              enum "enable" {
                value 1;
                description
                  "Enable PBR hash feature";
              }
            }
            description
              "Configure PBR hash";
          }
          leaf stats {
            type enumeration {
              enum "disable" {
                value 1;
                description
                  "Disable PBR statistics";
              }
            }
            description
              "Configure PBR statistics";
          }
        }
        leaf per-prefix-egress-stats {
          type enumeration {
            enum "enable" {
              value 12;
              description
                "Enable per-prefix-egress-stats accounting for unicast labels";
            }
          }
          description
            "Configure per-prefix-egress stats feature";
        }
        leaf sharedlspa {
          type enumeration {
            enum "enable" {
              value 10;
              description
                "Enable sharedlspa sharing";
            }
          }
          description
            "Configure shared_lspa feature";
        }
      }
    }
  }
}
