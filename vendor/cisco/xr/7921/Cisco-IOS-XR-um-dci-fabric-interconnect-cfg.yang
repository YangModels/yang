module Cisco-IOS-XR-um-dci-fabric-interconnect-cfg {
  namespace "http://cisco.com/ns/yang/Cisco-IOS-XR-um-dci-fabric-interconnect-cfg";
  prefix um-dci-fabric-interconnect-cfg;

  import Cisco-IOS-XR-types {
    prefix xr;
  }
  import ietf-inet-types {
    prefix inet;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR dci-fabric-interconnect package configuration.
     
     This YANG module augments the
     modules with configuration data.
     
     Copyright (c) 2020-2022 by Cisco Systems, Inc.
     All rights reserved.";

  revision 2020-12-14 {
    description
      "Initial release";
    semver:module-version "1.0.0";
  }

  container dci-fabric-interconnect {
    presence "Indicates a dci-fabric-interconnect node is configured.";
    description
      "Configure FTI parameters/sub-parameters";
    leaf identity {
      type union {
        type string {
          length "1..800" {
            description
              "Enter Identity: Loopback Interface name";
          }
        }
        type inet:ipv4-address-no-zone;
      }
      description
        "Enter Identity: Loopback Interface name";
    }
    container auto-configuration-pool {
      presence "Indicates a auto-configuration-pool node is configured.";
      description
        "Configure Auto Config Pool parameters";
      leaf bgp-as {
        type uint32 {
          range "0..4294967295" {
            description
              "AS number";
          }
        }
        description
          "Specify BGP AS number";
      }
      container local-vtep {
        description
          "Specify VXLAN attributes";
        leaf nve {
          type uint32 {
            range "0..4294967295" {
              description
                "index";
            }
          }
          description
            "NVE interface id";
        }
      }
      leaf bridge-group {
        type xr:Cisco-ios-xr-string {
          length "1..800" {
            description
              "name";
          }
        }
        description
          "Bridge-group name";
      }
      container vrfs {
        description
          "Configure local VRF parameters";
        list vrf {
          key "vrf-name";
          description
            "Configure local VRF parameters";
          leaf vrf-name {
            type xr:Cisco-ios-xr-string {
              length "1..800" {
                description
                  "vrf name";
              }
            }
            description
              "Configure local VRF parameters";
          }
          leaf ipv4-address {
            type inet:ipv4-address-no-zone;
            mandatory true;
            description
              "BVI override IP address";
          }
        }
      }
      container vni-pool {
        presence "Indicates a vni-pool node is configured.";
        description
          "VNI range value";
        leaf min-value {
          type uint32 {
            range "1..4000" {
              description
                "VNI Range:min value";
            }
          }
          mandatory true;
          description
            "VNI range value";
        }
        leaf max-value {
          type uint32 {
            range "1..4000" {
              description
                "VNI Range:max value";
            }
          }
          mandatory true;
          description
            "VNI Range:max value";
        }
      }
      container bvi-pool {
        presence "Indicates a bvi-pool node is configured.";
        description
          "BVI range value";
        leaf min-value {
          type uint32 {
            range "1..4000" {
              description
                "BVI Range:min value";
            }
          }
          mandatory true;
          description
            "BVI range value";
        }
        leaf max-value {
          type uint32 {
            range "1..4000" {
              description
                "BVI Range:max value";
            }
          }
          mandatory true;
          description
            "BVI Range:max value";
        }
      }
      container bd-pool {
        presence "Indicates a bd-pool node is configured.";
        description
          "Bridge Domain range value";
        leaf min-value {
          type uint32 {
            range "1..4000" {
              description
                "BD Range:min value";
            }
          }
          mandatory true;
          description
            "Bridge Domain range value";
        }
        leaf max-value {
          type uint32 {
            range "1..4000" {
              description
                "BD Range:max value";
            }
          }
          mandatory true;
          description
            "BD Range:max value";
        }
      }
    }
    container fabrics {
      description
        "Configure fabric parameters";
      list fabric {
        key "fabric-id";
        description
          "Configure fabric parameters";
        leaf fabric-id {
          type uint32 {
            range "1000..9999" {
              description
                "fabric identifier";
            }
          }
          description
            "Configure fabric parameters";
        }
        container opflex-peers {
          description
            "Enter Opflex peer info";
          list opflex-peer {
            key "address";
            description
              "Enter Opflex peer info";
            leaf address {
              type inet:ipv4-address-no-zone;
              description
                "Enter Opflex peer info";
            }
          }
        }
        container ssl {
          description
            "SSL configuration";
          container disabled {
            must "not(../path)";
            presence "Indicates a disabled node is configured.";
            description
              "SSL disabled";
          }
          leaf path {
            type xr:Cisco-ios-xr-string {
              length "1..800" {
                description
                  "Path to certificate";
              }
            }
            must "not(../disabled)";
            description
              "Path to certificate";
          }
        }
      }
    }
  }
}
