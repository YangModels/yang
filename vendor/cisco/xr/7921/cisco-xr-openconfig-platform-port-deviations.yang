//*************  DO-NOT EDIT  **************
//*********** Auto-generated file ********** 

 module cisco-xr-openconfig-platform-port-deviations {


  namespace "http://cisco.com/ns/yang/cisco-xr-openconfig-platform-port-deviations";
  prefix  "oc-portdevs";

  import openconfig-platform-port { prefix oc-port; }
  import openconfig-interfaces { prefix oc-if; }
  import openconfig-platform { prefix oc-platform; }

  organization "Cisco Systems, Inc.";

  contact
    "Cisco Systems, Inc.
     Customer Service

     Postal: 170 West Tasman Drive
     San Jose, CA 95134

     Tel: +1 800 553-NETS

     E-mail: cs-yang@cisco.com";

  description
    "This module contains a set of deviations for 
 
     openconfig-platform-port.yang@2018-01-20 

     on Cisco IOS-XR devices.

     Copyright (c) 2017-2019 by Cisco Systems, Inc.
     All rights reserved.";

  revision "2022-10-10" {
    description
      "Remove deviations to support model applicable to IOS-XR 7.9.1";
  }

  revision "2018-12-10" {
    description
      "Initial revision applicable to IOS-XR 6.6.1";
  }

  deviation /oc-if:interfaces/oc-if:interface/oc-if:state/oc-port:hardware-port {
    deviate not-supported;
  }


}
//total deviations:1
