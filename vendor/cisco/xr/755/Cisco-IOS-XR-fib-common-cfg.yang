module Cisco-IOS-XR-fib-common-cfg {
  namespace "http://cisco.com/ns/yang/Cisco-IOS-XR-fib-common-cfg";
  prefix fib-common-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR fib-common package configuration.
     
     This module contains definitions
     for the following management objects:
       fib: CEF configuration
     
     Copyright (c) 2013-2021 by Cisco Systems, Inc.
     All rights reserved.";

  revision 2021-12-18 {
    description
      "Added cef hierarchical-load-balancing configuration";
    semver:module-version "1.2.0";
  }
  revision 2021-07-09 {
    description
      "Added PI FIB Telemetry Hopeless Retry and OOR";
    semver:module-version "1.1.0";
  }
  revision 2020-07-23 {
    description
      "obsolete frr-follow-bgp-pic
       2020-07-21
           Added Support for Proactive ARP and ND";
    semver:module-version "1.1.0";
  }
  revision 2019-04-05 {
    description
      "Establish semantic version baseline.";
    semver:module-version "1.0.0";
  }
  revision 2017-05-01 {
    description
      "Fixing backward compatibility error in module.";
  }
  revision 2017-01-20 {
    description
      "IOS XR 6.2.1 revision";
  }
  revision 2015-11-09 {
    description
      "IOS XR 6.0 revision.";
  }

  typedef Fib-hlb-mode {
    type enumeration {
      enum "ecmp" {
        value 1;
        description
          "HLB Mode ECMP";
      }
      enum "ucmp" {
        value 2;
        description
          "HLB Mode UCMP";
      }
    }
    description
      "Fib hlb mode";
  }

  typedef Fib-pbts-forward-class {
    type union {
      type enumeration {
        enum "any" {
          value 8;
          description
            "Any class";
        }
      }
      type uint32 {
        range "0..8";
      }
    }
    description
      "Fib pbts forward class";
  }

  typedef Fib-pbts-fallback {
    type enumeration {
      enum "list" {
        value 1;
        description
          "Fallback to class number list";
      }
      enum "any" {
        value 2;
        description
          "Fallback to any class";
      }
      enum "drop" {
        value 3;
        description
          "Fallback to drop";
      }
    }
    description
      "Fib pbts fallback";
  }

  container fib {
    description
      "CEF configuration";
    container pbts-forward-class-fallbacks {
      description
        "PBTS class configuration";
      list pbts-forward-class-fallback {
        key "forward-class-number";
        description
          "Set PBTS class for fallback";
        leaf forward-class-number {
          type Fib-pbts-forward-class;
          description
            "PBTS forward class number";
        }
        leaf fallback-type {
          type Fib-pbts-fallback;
          mandatory true;
          description
            "Set PBTS fallback type";
        }
        leaf-list fallback-class-number-array {
          type uint32 {
            range "0..7";
          }
          max-elements "7";
          description
            "Set PBTS fallback class number array";
        }
      }
    }
    container platform {
      description
        "FIB platform parameters";
      container label-switched-multicast {
        description
          "Options for label-switched-multicast parameters";
        leaf frr-holdtime {
          type uint32 {
            range "3..180";
          }
          units "second";
          description
            "Set time to keep FRR slots programmed post FRR";
        }
      }
    }
    container hierarchical-loadbalancing {
      description
        "Hierarchical Load Balancing";
      leaf hlb-mode {
        type Fib-hlb-mode;
        description
          "HLB Mode";
      }
      leaf hlb-num-paths {
        type uint32 {
          range "1..128";
        }
        description
          "HLB NumPaths";
      }
    }
    leaf auto-hash-recover {
      type boolean;
      description
        "Set option for automatcially recovering
         consistent-hashing state on interface up";
    }
    leaf prefer-aib-routes {
      type boolean;
      description
        "Set options for adjacency routes overriding RIB
         routes";
    }
    leaf proactive-arp-nd {
      type empty;
      description
        "Enable Proactive ARP and ND";
    }
    leaf encap-sharing-disable {
      type boolean;
      description
        "Set true to disable encapsulation sharing";
    }
    leaf frr-follow-bgp-pic {
      type boolean;
      status deprecated;
      description
        "Set option for fast-reroute to follow BGP PIC
         update, not to wait for timeout";
    }
  }
}
