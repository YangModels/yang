module Cisco-IOS-XR-um-segment-routing-traffic-eng-cfg {
  namespace "http://cisco.com/ns/yang/Cisco-IOS-XR-um-segment-routing-traffic-eng-cfg";
  prefix um-segment-routing-traffic-eng-cfg;

  import Cisco-IOS-XR-types {
    prefix xr;
  }
  import ietf-inet-types {
    prefix inet;
  }
  import Cisco-IOS-XR-um-segment-routing-cfg {
    prefix a1;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR segment-routing-traffic-eng package configuration.
     
     This YANG module augments the
     modules with configuration data.
     
     Copyright (c) 2022 by Cisco Systems, Inc.
     All rights reserved.";

  revision 2022-01-03 {
    description
      "Added support for Circuit Style SRTE";
    semver:module-version "1.0.1M";
  }
  revision 2021-06-29 {
    description
      "Initial release";
    semver:module-version "1.0.0";
  }

  augment "/a1:segment-routing" {
    container traffic-eng {
      presence "Indicates a traffic-eng node is configured.";
      description
        "Segment Routing Traffic Engineering";
      container srv6 {
        presence "Indicates a srv6 node is configured.";
        description
          "Segment Routing IPv6";
        container locator {
          description
            "Configure locator";
          leaf locator-name {
            type xr:Cisco-ios-xr-string {
              length "1..64" {
                description
                  "Specify locator name with max 64 characters";
              }
            }
            must "../binding-sid/dynamic/behavior/ub6-insert-reduced";
            description
              "Specify locator name with max 64 characters";
          }
          container binding-sid {
            description
              "Binding-SID allocation options";
            container dynamic {
              description
                "Dynamic based option";
              container behavior {
                description
                  "Binding-SID behavior options";
                container ub6-insert-reduced {
                  must "../../../../locator-name";
                  presence "Indicates a ub6-insert-reduced node is configured.";
                  description
                    "Binding-SID insert reduced behavior";
                }
              }
            }
          }
        }
        leaf maximum-sid-depth {
          type uint32 {
            range "1..255" {
              description
                "Maximum SID Depth";
            }
          }
          description
            "Maximum number of SIDs for SRv6 that the PCC can impose on a packet";
        }
      }
      container candidate-paths {
        presence "Indicates a candidate-paths node is configured.";
        description
          "Configurations for candidate paths.";
        container all {
          presence "Indicates a all node is configured.";
          description
            "Configurations for all candidate paths.";
          container source-address {
            description
              "Source address for candidate-path";
            leaf ipv4 {
              type inet:ipv4-address-no-zone;
              must "not(../ipv6)";
              description
                "IPv4 address";
            }
            leaf ipv6 {
              type inet:ipv6-address-no-zone;
              must "not(../ipv4)";
              description
                "IPv6 address";
            }
          }
        }
        container local {
          presence "Indicates a local node is configured.";
          description
            "Configurations for locally instantiated candidate paths.";
          container source-address {
            description
              "Source address for candidate-path";
            leaf ipv4 {
              type inet:ipv4-address-no-zone;
              must "not(../ipv6)";
              description
                "IPv4 address";
            }
            leaf ipv6 {
              type inet:ipv6-address-no-zone;
              must "not(../ipv4)";
              description
                "IPv6 address";
            }
          }
        }
        container on-demand {
          presence "Indicates a on-demand node is configured.";
          description
            "Configurations for BGP-ODN candidate paths.";
          container source-address {
            description
              "Source address for candidate-path";
            leaf ipv4 {
              type inet:ipv4-address-no-zone;
              must "not(../ipv6)";
              description
                "IPv4 address";
            }
            leaf ipv6 {
              type inet:ipv6-address-no-zone;
              must "not(../ipv4)";
              description
                "IPv6 address";
            }
          }
        }
        container bgp-srte {
          presence "Indicates a bgp-srte node is configured.";
          description
            "Configurations for BGP-SRTE instantiated candidate paths.";
          container source-address {
            description
              "Source address for candidate-path";
            leaf ipv4 {
              type inet:ipv4-address-no-zone;
              must "not(../ipv6)";
              description
                "IPv4 address";
            }
            leaf ipv6 {
              type inet:ipv6-address-no-zone;
              must "not(../ipv4)";
              description
                "IPv6 address";
            }
          }
        }
        container pcep {
          presence "Indicates a pcep node is configured.";
          description
            "Configurations for PCE instantiated candidate paths.";
          container source-address {
            description
              "Source address for candidate-path";
            leaf ipv4 {
              type inet:ipv4-address-no-zone;
              must "not(../ipv6)";
              description
                "IPv4 address";
            }
            leaf ipv6 {
              type inet:ipv6-address-no-zone;
              must "not(../ipv4)";
              description
                "IPv6 address";
            }
          }
        }
      }
      container steering {
        presence "Indicates a steering node is configured.";
        description
          "Global Steering options";
        container labeled-services {
          presence "Indicates a labeled-services node is configured.";
          description
            "steering options for labeled services";
          container disable {
            description
              "Disable steering for labeled-services for policies";
            container all {
              presence "Indicates a all node is configured.";
              description
                "All policies";
            }
            container local {
              presence "Indicates a local node is configured.";
              description
                "All local policies";
            }
            container on-demand {
              presence "Indicates a on-demand node is configured.";
              description
                "All on-demand color policies";
            }
            container bgp-srte {
              presence "Indicates a bgp-srte node is configured.";
              description
                "All BGP-SRTE policies";
            }
            container pcep {
              presence "Indicates a pcep node is configured.";
              description
                "All PCE policies";
            }
          }
        }
      }
      container logging {
        description
          "Logging configuration";
        container policy {
          description
            "Configure policy logging parameters";
          container status {
            presence "Indicates a status node is configured.";
            description
              "Enable policy status logging";
          }
        }
        container pcep {
          description
            "Enable pcep peer-status logging";
          container peer-status {
            presence "Indicates a peer-status node is configured.";
            description
              "Enable pcep peer-status logging";
          }
        }
      }
      container trace {
        description
          "Configure SR-TE trace options";
        container buffer {
          description
            "SR-TE Trace buffers";
          container all {
            description
              "All buffers control";
            leaf trace-count {
              type uint32 {
                range "0..1000000" {
                  description
                    "count";
                }
              }
              description
                "Trace count";
            }
          }
          container common {
            description
              "Common buffer control";
            container gen-error {
              description
                "Generic error buffer";
              leaf trace-count {
                type uint32 {
                  range "0..1000000" {
                    description
                      "count";
                  }
                }
                description
                  "Trace count";
              }
            }
            container lslib {
              description
                "lslib trace buffer";
              leaf trace-count {
                type uint32 {
                  range "0..1000000" {
                    description
                      "count";
                  }
                }
                description
                  "Trace count";
              }
            }
            container cspf {
              description
                "cspf trace buffer";
              leaf trace-count {
                type uint32 {
                  range "0..1000000" {
                    description
                      "count";
                  }
                }
                description
                  "Trace count";
              }
            }
            container topo {
              description
                "topo trace buffer";
              leaf trace-count {
                type uint32 {
                  range "0..1000000" {
                    description
                      "count";
                  }
                }
                description
                  "Trace count";
              }
            }
            container mempool {
              description
                "mempool trace buffer";
              leaf trace-count {
                type uint32 {
                  range "0..1000000" {
                    description
                      "count";
                  }
                }
                description
                  "Trace count";
              }
            }
            container pcep {
              description
                "pcep trace buffer";
              leaf trace-count {
                type uint32 {
                  range "0..1000000" {
                    description
                      "count";
                  }
                }
                description
                  "Trace count";
              }
            }
            container timing {
              description
                "timing trace buffer";
              leaf trace-count {
                type uint32 {
                  range "0..1000000" {
                    description
                      "count";
                  }
                }
                description
                  "Trace count";
              }
            }
            container cmn-codeflow {
              description
                "code-flow trace buffer";
              leaf trace-count {
                type uint32 {
                  range "0..1000000" {
                    description
                      "count";
                  }
                }
                description
                  "Trace count";
              }
            }
          }
          container error {
            description
              "Error buffer control";
            leaf trace-count {
              type uint32 {
                range "0..1000000" {
                  description
                    "count";
                }
              }
              description
                "Trace count";
            }
          }
          container fib {
            description
              "FIB buffer control";
            leaf trace-count {
              type uint32 {
                range "0..1000000" {
                  description
                    "count";
                }
              }
              description
                "Trace count";
            }
          }
          container im {
            description
              "IM buffer control";
            leaf trace-count {
              type uint32 {
                range "0..1000000" {
                  description
                    "count";
                }
              }
              description
                "Trace count";
            }
          }
          container igp {
            description
              "IGP buffer control";
            leaf trace-count {
              type uint32 {
                range "0..1000000" {
                  description
                    "count";
                }
              }
              description
                "Trace count";
            }
          }
          container lm {
            description
              "LM buffer control";
            leaf trace-count {
              type uint32 {
                range "0..1000000" {
                  description
                    "count";
                }
              }
              description
                "Trace count";
            }
          }
          container lsd {
            description
              "LSD buffer control";
            leaf trace-count {
              type uint32 {
                range "0..1000000" {
                  description
                    "count";
                }
              }
              description
                "Trace count";
            }
          }
          container mgmt {
            description
              "Management buffer control";
            leaf trace-count {
              type uint32 {
                range "0..1000000" {
                  description
                    "count";
                }
              }
              description
                "Trace count";
            }
          }
          container policy {
            description
              "Policy buffer control";
            leaf trace-count {
              type uint32 {
                range "0..1000000" {
                  description
                    "count";
                }
              }
              description
                "Trace count";
            }
          }
          container service-api {
            description
              "Service API buffer control";
            leaf trace-count {
              type uint32 {
                range "0..1000000" {
                  description
                    "count";
                }
              }
              description
                "Trace count";
            }
          }
          container agent {
            description
              "Agent buffer control";
            leaf trace-count {
              type uint32 {
                range "0..1000000" {
                  description
                    "count";
                }
              }
              description
                "Trace count";
            }
          }
          container bsid {
            description
              "BSID buffer control";
            leaf trace-count {
              type uint32 {
                range "0..1000000" {
                  description
                    "count";
                }
              }
              description
                "Trace count";
            }
          }
          container policy-lsp {
            description
              "Policy LSP buffer control";
            leaf trace-count {
              type uint32 {
                range "0..1000000" {
                  description
                    "count";
                }
              }
              description
                "Trace count";
            }
          }
          container policy-cpath {
            description
              "Policy candidate path buffer control";
            leaf trace-count {
              type uint32 {
                range "0..1000000" {
                  description
                    "count";
                }
              }
              description
                "Trace count";
            }
          }
          container generic-error {
            description
              "Generic errors buffer control";
            leaf trace-count {
              type uint32 {
                range "0..1000000" {
                  description
                    "count";
                }
              }
              description
                "Trace count";
            }
          }
          container chkpt {
            description
              "Checkpoint buffer control";
            leaf trace-count {
              type uint32 {
                range "0..1000000" {
                  description
                    "count";
                }
              }
              description
                "Trace count";
            }
          }
          container policy-state {
            description
              "Policy state buffer control";
            leaf trace-count {
              type uint32 {
                range "0..1000000" {
                  description
                    "count";
                }
              }
              description
                "Trace count";
            }
          }
          container init {
            description
              "Initialization buffer control";
            leaf trace-count {
              type uint32 {
                range "0..1000000" {
                  description
                    "count";
                }
              }
              description
                "Trace count";
            }
          }
          container lmrib {
            description
              "LMRIB buffer control";
            leaf trace-count {
              type uint32 {
                range "0..1000000" {
                  description
                    "count";
                }
              }
              description
                "Trace count";
            }
          }
          container pfp {
            description
              "PFP buffer control";
            leaf trace-count {
              type uint32 {
                range "0..1000000" {
                  description
                    "count";
                }
              }
              description
                "Trace count";
            }
          }
          container rib {
            description
              "IPv6 RIB buffer control";
            leaf trace-count {
              type uint32 {
                range "0..1000000" {
                  description
                    "count";
                }
              }
              description
                "Trace count";
            }
          }
        }
      }
      container policies {
        description
          "Name of SR-TE Policy";
        list policy {
          key "policy-name";
          description
            "Name of SR-TE Policy";
          leaf policy-name {
            type xr:Cisco-ios-xr-string {
              length "1..59" {
                description
                  "Identifying name for policy with max 59 characters";
              }
            }
            description
              "Name of SR-TE Policy";
          }
          container srv6 {
            presence "Indicates a srv6 node is configured.";
            description
              "Segment Routing IPv6";
            container locator {
              description
                "Configure locator";
              leaf locator-name {
                type xr:Cisco-ios-xr-string {
                  length "1..64" {
                    description
                      "Specify locator name with max 64 characters";
                  }
                }
                must "../binding-sid/dynamic/behavior/ub6-insert-reduced";
                description
                  "Specify locator name with max 64 characters";
              }
              container binding-sid {
                description
                  "Binding-SID allocation options";
                container dynamic {
                  description
                    "Dynamic based option";
                  container behavior {
                    description
                      "Binding-SID behavior options";
                    container ub6-insert-reduced {
                      must "../../../../locator-name";
                      presence "Indicates a ub6-insert-reduced node is configured.";
                      description
                        "Binding-SID insert reduced behavior";
                    }
                  }
                }
              }
            }
          }
          container autoroute {
            presence "Indicates a autoroute node is configured.";
            description
              "Autoroute configuration";
            container include {
              description
                "Prefixes for which IGP routes will be installed";
              container all {
                presence "Indicates a all node is configured.";
                description
                  "Include all eligible prefixes";
              }
              container ipv4s {
                description
                  "IPv4 address family";
                list ipv4 {
                  key "address length";
                  description
                    "IPv4 address family";
                  leaf address {
                    type inet:ipv4-address-no-zone;
                    description
                      "IPv4 address family";
                  }
                  leaf length {
                    type uint32 {
                      range "0..32";
                    }
                    description
                      "IPv4 address family";
                  }
                }
              }
              container ipv6 {
                description
                  "IPv6 address family";
                container all {
                  presence "Indicates a all node is configured.";
                  description
                    "Include all eligible IPv6 prefixes";
                }
              }
            }
            leaf forward-class {
              type uint32 {
                range "0..7" {
                  description
                    "Forward class value";
                }
              }
              description
                "Specify forward class for policy based routing";
            }
            container metric {
              description
                "Autoroute metric";
              leaf constant {
                type uint32 {
                  range "1..2147483647" {
                    description
                      "Constant metric";
                  }
                }
                must "not(../relative)";
                description
                  "Set metric mode constant";
              }
              leaf relative {
                type int32 {
                  range "-10..10" {
                    description
                      "Relative metric";
                  }
                }
                must "not(../constant)";
                description
                  "Set metric mode relative";
              }
            }
            container force-sr-include {
              presence "Indicates a force-sr-include node is configured.";
              description
                "Force autoroute Policy to be safe for carrying SR Labelled traffic";
            }
          }
          container candidate-paths {
            presence "Indicates a candidate-paths node is configured.";
            description
              "Candidate-paths configuration";
            container preferences {
              description
                "Policy path-option preference entry";
              list preference {
                key "preference-id";
                description
                  "Policy path-option preference entry";
                leaf preference-id {
                  type uint32 {
                    range "1..65535" {
                      description
                        "Path-option preference";
                    }
                  }
                  description
                    "Policy path-option preference entry";
                }
                container per-flow {
                  presence "Indicates a per-flow node is configured.";
                  description
                    "Per-flow configuration";
                  container forward-classes {
                    description
                      "Specify forward class for per-flow based routing";
                    list forward-class {
                      key "forward-class-value";
                      description
                        "Forward class value";
                      leaf forward-class-value {
                        type uint32 {
                          range "0..7" {
                            description
                              "Forward class value";
                          }
                        }
                        description
                          "Forward class value";
                      }
                      leaf color {
                        type uint32 {
                          range "1..4294967295" {
                            description
                              "Color value";
                          }
                        }
                        mandatory true;
                        description
                          "Specify corresponding policy color for the forwarding class";
                      }
                    }
                    leaf default {
                      type uint32 {
                        range "0..7" {
                          description
                            "Forward-class value";
                        }
                      }
                      description
                        "Configure default forward-class";
                    }
                  }
                }
                container dynamic {
                  presence "Indicates a dynamic node is configured.";
                  description
                    "Dynamically allocated path";
                  leaf weight {
                    type uint32 {
                      range "1..4294967295" {
                        description
                          "Weight";
                      }
                    }
                    description
                      "Path option weight";
                  }
                  container reverse-path {
                    description
                      "reverse-path";
                    leaf segment-list {
                      type string {
                        length "1..128" {
                          description
                            "Identifying name for segment-list";
                        }
                      }
                      description
                        "segment-list";
                    }
                  }
                  container pcep {
                    presence "Indicates a pcep node is configured.";
                    description
                      "Path Computation Element Protocol related configuration";
                  }
                  container metric {
                    presence "Indicates a metric node is configured.";
                    description
                      "Path metric configuration";
                    container type {
                      description
                        "Metric type configuration";
                      container te {
                        must
                          "not(../igp or ../hopcount
                           or ../latency)";
                        presence "Indicates a te node is configured.";
                        description
                          "TE metric type";
                      }
                      container igp {
                        must
                          "not(../te or ../hopcount
                           or ../latency)";
                        presence "Indicates a igp node is configured.";
                        description
                          "IGP metric type";
                      }
                      container hopcount {
                        must
                          "not(../te or ../igp
                           or ../latency)";
                        presence "Indicates a hopcount node is configured.";
                        description
                          "Hopcount metric type";
                      }
                      container latency {
                        must
                          "not(../te or ../igp
                           or ../hopcount)";
                        presence "Indicates a latency node is configured.";
                        description
                          "Latency metric type";
                      }
                    }
                    leaf sid-limit {
                      type uint32 {
                        range "1..255" {
                          description
                            "SID limit value";
                        }
                      }
                      description
                        "SID limit";
                    }
                    container margin {
                      description
                        "Metric margin";
                      leaf absolute {
                        type uint32 {
                          range "0..2147483647" {
                            description
                              "Absolute metric margin value";
                          }
                        }
                        must "not(../relative)";
                        description
                          "Absolute metric margin";
                      }
                      leaf relative {
                        type uint32 {
                          range "0..2147483647" {
                            description
                              "Relative metric margin value";
                          }
                        }
                        must "not(../absolute)";
                        description
                          "Relative metric margin";
                      }
                    }
                  }
                  container anycast-sid-inclusion {
                    presence "Indicates a anycast-sid-inclusion node is configured.";
                    description
                      "Path Anycast SID Inclusion configuration";
                  }
                }
                container explicit {
                  description
                    "Preconfigured path";
                  container segment-lists {
                    description
                      "Identifying name for segment-list";
                    list segment-list {
                      key "segment-list-name";
                      description
                        "Identifying name for segment-list";
                      leaf segment-list-name {
                        type string {
                          length "1..128" {
                            description
                              "Identifying name for segment-list";
                          }
                        }
                        description
                          "Identifying name for segment-list";
                      }
                      leaf weight {
                        type uint32 {
                          range "1..4294967295" {
                            description
                              "Weight";
                          }
                        }
                        description
                          "Path option weight";
                      }
                      container reverse-path {
                        description
                          "reverse-path";
                        leaf segment-list {
                          type string {
                            length "1..128" {
                              description
                                "Identifying name for segment-list";
                            }
                          }
                          description
                            "segment-list";
                        }
                      }
                      container pcep {
                        presence "Indicates a pcep node is configured.";
                        description
                          "Path Computation Element Protocol related configuration";
                      }
                      container metric {
                        presence "Indicates a metric node is configured.";
                        description
                          "Path metric configuration";
                        container type {
                          description
                            "Metric type configuration";
                          container te {
                            must
                              "not(../igp or ../hopcount
                               or ../latency)";
                            presence "Indicates a te node is configured.";
                            description
                              "TE metric type";
                          }
                          container igp {
                            must
                              "not(../te or ../hopcount
                               or ../latency)";
                            presence "Indicates a igp node is configured.";
                            description
                              "IGP metric type";
                          }
                          container hopcount {
                            must
                              "not(../te or ../igp
                               or ../latency)";
                            presence "Indicates a hopcount node is configured.";
                            description
                              "Hopcount metric type";
                          }
                          container latency {
                            must
                              "not(../te or ../igp
                               or ../hopcount)";
                            presence "Indicates a latency node is configured.";
                            description
                              "Latency metric type";
                          }
                        }
                        leaf sid-limit {
                          type uint32 {
                            range "1..255" {
                              description
                                "SID limit value";
                            }
                          }
                          description
                            "SID limit";
                        }
                        container margin {
                          description
                            "Metric margin";
                          leaf absolute {
                            type uint32 {
                              range "0..2147483647" {
                                description
                                  "Absolute metric margin value";
                              }
                            }
                            must "not(../relative)";
                            description
                              "Absolute metric margin";
                          }
                          leaf relative {
                            type uint32 {
                              range "0..2147483647" {
                                description
                                  "Relative metric margin value";
                              }
                            }
                            must "not(../absolute)";
                            description
                              "Relative metric margin";
                          }
                        }
                      }
                      container anycast-sid-inclusion {
                        presence "Indicates a anycast-sid-inclusion node is configured.";
                        description
                          "Path Anycast SID Inclusion configuration";
                      }
                    }
                  }
                }
                container constraints {
                  description
                    "Candidate path constraints";
                  container bounds {
                    description
                      "Assign anycast metric bounds to path";
                    container cumulative {
                      description
                        "Cumulative metric bound";
                      container type {
                        description
                          "The metric type for the bound";
                        leaf te {
                          type uint32 {
                            range "1..4294967295" {
                              description
                                "Bound metric value";
                            }
                          }
                          description
                            "Bound metric type TE";
                        }
                        leaf igp {
                          type uint32 {
                            range "1..4294967295" {
                              description
                                "Bound metric value";
                            }
                          }
                          description
                            "Bound metric type IGP";
                        }
                        leaf latency {
                          type uint32 {
                            range "1..4294967295" {
                              description
                                "Bound metric value in microseconds";
                            }
                          }
                          description
                            "Bound metric type latency";
                        }
                        leaf hopcount {
                          type uint32 {
                            range "1..4294967295" {
                              description
                                "Bound metric value";
                            }
                          }
                          description
                            "Bound metric type hopcount";
                        }
                      }
                    }
                  }
                  container affinity {
                    description
                      "Assign affinities to path";
                    container include-any {
                      description
                        "Affinity attributes - at least one must be included";
                      container name {
                        description
                          "Affinity name";
                        container affinity-colors {
                          description
                            "Affinity color name";
                          list affinity-color {
                            key "affinity-color-name";
                            description
                              "Affinity color name";
                            leaf affinity-color-name {
                              type string {
                                length "1..32" {
                                  description
                                    "Affinity color name";
                                }
                              }
                              description
                                "Affinity color name";
                            }
                          }
                        }
                      }
                    }
                    container include-all {
                      description
                        "Affinity attributes - all must be included";
                      container name {
                        description
                          "Affinity name";
                        container affinity-colors {
                          description
                            "Affinity color name";
                          list affinity-color {
                            key "affinity-color-name";
                            description
                              "Affinity color name";
                            leaf affinity-color-name {
                              type string {
                                length "1..32" {
                                  description
                                    "Affinity color name";
                                }
                              }
                              description
                                "Affinity color name";
                            }
                          }
                        }
                      }
                    }
                    container exclude-any {
                      description
                        "Affinity attributes to exclude - presence of at least one excludes link";
                      container name {
                        description
                          "Affinity name";
                        container affinity-colors {
                          description
                            "Affinity color name";
                          list affinity-color {
                            key "affinity-color-name";
                            description
                              "Affinity color name";
                            leaf affinity-color-name {
                              type string {
                                length "1..32" {
                                  description
                                    "Affinity color name";
                                }
                              }
                              description
                                "Affinity color name";
                            }
                          }
                        }
                      }
                    }
                  }
                  container segments {
                    description
                      "Path segments constraints";
                    leaf sid-algorithm {
                      type uint32 {
                        range "0..255" {
                          description
                            "'0' for regular SIDs, '1' for strict-spf SIDs, '128' - '255' for algorithm SIDs";
                        }
                      }
                      description
                        "Prefix-SID algorithm";
                    }
                    container protection {
                      description
                        "Protection type";
                      container protected-preferred {
                        must
                          "not(../protected-only or ../unprotected-only
                           or ../unprotected-preferred)";
                        presence "Indicates a protected-preferred node is configured.";
                        description
                          "Protected adj-SID preferred (default)";
                      }
                      container protected-only {
                        must
                          "not(../protected-preferred or ../unprotected-only
                           or ../unprotected-preferred)";
                        presence "Indicates a protected-only node is configured.";
                        description
                          "Protected adj-SID only";
                      }
                      container unprotected-only {
                        must
                          "not(../protected-preferred or ../protected-only
                           or ../unprotected-preferred)";
                        presence "Indicates a unprotected-only node is configured.";
                        description
                          "Unprotected adj-SID only";
                      }
                      container unprotected-preferred {
                        must
                          "not(../protected-preferred or ../protected-only
                           or ../unprotected-only)";
                        presence "Indicates a unprotected-preferred node is configured.";
                        description
                          "Unprotected adj-SID preferred";
                      }
                    }
                  }
                  container disjoint-path {
                    description
                      "Request disjoint path computation";
                    leaf group-id {
                      type uint32 {
                        range "1..65535" {
                          description
                            "Group ID";
                        }
                      }
                      description
                        "Group ID";
                    }
                    container type {
                      description
                        "Disjointness type";
                      container link {
                        must
                          "not(../node or ../srlg
                           or ../srlg-node)";
                        presence "Indicates a link node is configured.";
                        description
                          "Link Disjointness";
                        leaf sub-id {
                          type uint32 {
                            range "1..65535" {
                              description
                                "Subgroup ID number";
                            }
                          }
                          description
                            "Subgroup ID";
                        }
                      }
                      container node {
                        must
                          "not(../link or ../srlg
                           or ../srlg-node)";
                        presence "Indicates a node node is configured.";
                        description
                          "Node Disjointness";
                        leaf sub-id {
                          type uint32 {
                            range "1..65535" {
                              description
                                "Subgroup ID number";
                            }
                          }
                          description
                            "Subgroup ID";
                        }
                      }
                      container srlg {
                        must
                          "not(../link or ../node
                           or ../srlg-node)";
                        presence "Indicates a srlg node is configured.";
                        description
                          "SRLG Disjointness";
                        leaf sub-id {
                          type uint32 {
                            range "1..65535" {
                              description
                                "Subgroup ID number";
                            }
                          }
                          description
                            "Subgroup ID";
                        }
                      }
                      container srlg-node {
                        must
                          "not(../link or ../node
                           or ../srlg)";
                        presence "Indicates a srlg-node node is configured.";
                        description
                          "SRLG Node Disjointness";
                        leaf sub-id {
                          type uint32 {
                            range "1..65535" {
                              description
                                "Subgroup ID number";
                            }
                          }
                          description
                            "Subgroup ID";
                        }
                      }
                    }
                  }
                }
                container lock {
                  presence "Indicates a lock node is configured.";
                  description
                    "Candidate path protection locks on protect lsp";
                  leaf duration {
                    type uint32 {
                      range "0..3000" {
                        description
                          "Duration in seconds 0-3000. Use 0 to disable. Default is 300.";
                      }
                    }
                    description
                      "Keep protect cpath locked as active lsp after higher preference cpath lsp is made standby";
                  }
                }
                container effective-metric {
                  presence "Indicates a effective-metric node is configured.";
                  description
                    "Effective metric configuration submode";
                  leaf value {
                    type uint32 {
                      range "0..4294967295" {
                        description
                          "Integer value of metric";
                      }
                    }
                    description
                      "Metric value, advertised to other protocols";
                  }
                  container type {
                    description
                      "Metric type, advertised to other protocols";
                    container igp {
                      must
                        "not(../te or ../latency
                         or ../hopcount)";
                      presence "Indicates a igp node is configured.";
                      description
                        "IGP metric type";
                    }
                    container te {
                      must
                        "not(../igp or ../latency
                         or ../hopcount)";
                      presence "Indicates a te node is configured.";
                      description
                        "TE metric type";
                    }
                    container latency {
                      must
                        "not(../igp or ../te
                         or ../hopcount)";
                      presence "Indicates a latency node is configured.";
                      description
                        "LATENCY metric type";
                    }
                    container hopcount {
                      must
                        "not(../igp or ../te
                         or ../latency)";
                      presence "Indicates a hopcount node is configured.";
                      description
                        "HOPCOUNT metric type";
                    }
                  }
                }
                leaf pce-group {
                  type xr:Cisco-ios-xr-string {
                    length "1..16" {
                      description
                        "Name of the PCE group - maximum 16 characters";
                    }
                  }
                  description
                    "PCE group configuration";
                }
              }
            }
          }
          leaf color {
            type uint32 {
              range "1..4294967295" {
                description
                  "Color value";
              }
            }
            description
              "Specify color for policy";
          }
          container end-point {
            description
              "Policy endpoint";
            leaf ipv4 {
              type inet:ipv4-address-no-zone;
              must "not(../ipv6)";
              description
                "IPv4 address";
            }
            leaf ipv6 {
              type inet:ipv6-address-no-zone;
              must "not(../ipv4)";
              description
                "IPv6 address";
            }
          }
          container source-address {
            description
              "Source address of policy";
            leaf ipv4 {
              type inet:ipv4-address-no-zone;
              must "not(../ipv6)";
              description
                "IPv4 address";
            }
            leaf ipv6 {
              type inet:ipv6-address-no-zone;
              must "not(../ipv4)";
              description
                "IPv6 address";
            }
          }
          leaf max-install-standby-cpaths {
            type uint32 {
              range "0..3" {
                description
                  "Number of standby candidate path LSPs to allow";
              }
            }
            description
              "Allow additional candidate paths to warm up non forwarding LSPs";
          }
          container binding-sid {
            description
              "Binding Segment Identifier";
            leaf mpls {
              type uint32 {
                range "16..1048575" {
                  description
                    "MPLS label";
                }
              }
              description
                "MPLS label";
            }
          }
          leaf bandwidth {
            type uint32 {
              range "1..4294967295" {
                description
                  "Bandwidth value in kbps";
              }
            }
            description
              "Requested Bandwidth";
          }
          container shutdown {
            presence "Indicates a shutdown node is configured.";
            description
              "Policy admin-shutdown";
          }
          container ipv6 {
            description
              "IPv6 configuration";
            container disable {
              presence "Indicates a disable node is configured.";
              description
                "Disable IPv6 caps (applicable to only policies with NULL end-point)";
            }
          }
          container steering {
            description
              "Steering options configuration";
            container labeled-services {
              description
                "Options for steering of labeled services";
              container disable {
                presence "Indicates a disable node is configured.";
                description
                  "Disable steering for labeled services";
              }
            }
            container path-invalidation {
              description
                "Path invalidation action, default is to fall back to unconstrained IGP path";
              container drop {
                presence "Indicates a drop node is configured.";
                description
                  "If path became invalid, keep policy up, but drop all traffic sent on the policy";
              }
            }
            container bgp {
              description
                "BGP client";
              container disable {
                presence "Indicates a disable node is configured.";
                description
                  "Disable all services";
              }
            }
          }
          container performance-measurement {
            presence "Indicates a performance-measurement node is configured.";
            description
              "Performance Measurement configuration submode";
            container delay-measurement {
              presence "Indicates a delay-measurement node is configured.";
              description
                "Delay-measurement configuration submode";
              container delay-profile {
                description
                  "SR Policy delay profile name";
                leaf name {
                  type xr:Cisco-ios-xr-string {
                    length "1..256" {
                      description
                        "Profile name";
                    }
                  }
                  description
                    "Profile name";
                }
              }
              container logging {
                presence "Indicates a logging node is configured.";
                description
                  "Syslog configuration options";
                container delay-exceeded {
                  presence "Indicates a delay-exceeded node is configured.";
                  description
                    "Emit syslog when the delay exceeds the threshold";
                }
              }
            }
            container reverse-path {
              description
                "Specify parameters about the reverse path back to the head-end";
              leaf label {
                type uint32 {
                  range "16..1048575" {
                    description
                      "Reverse path label";
                  }
                }
                description
                  "PM packets return to head-end using a label";
              }
            }
            container liveness-detection {
              presence "Indicates a liveness-detection node is configured.";
              description
                "Liveness detection configuration submode";
              container invalidation-action {
                description
                  "Action to be taken when PM liveness session is invalidated";
                container none {
                  must "not(../down)";
                  presence "Indicates a none node is configured.";
                  description
                    "PM liveness session state does not affect LSP state, use for diagnostic purposes";
                }
                container down {
                  must "not(../none)";
                  presence "Indicates a down node is configured.";
                  description
                    "LSP can only be operationally up if the PM liveness session is up";
                }
              }
              container liveness-profile {
                description
                  "SR Policy liveness profile name";
                leaf name {
                  type xr:Cisco-ios-xr-string {
                    length "1..256" {
                      description
                        "Profile name";
                    }
                  }
                  description
                    "Profile name";
                }
                container backup {
                  description
                    "SR Policy liveness backup profile name";
                  leaf name {
                    type xr:Cisco-ios-xr-string {
                      length "1..256" {
                        description
                          "Profile name";
                      }
                    }
                    description
                      "Profile name";
                  }
                }
              }
              container logging {
                presence "Indicates a logging node is configured.";
                description
                  "Syslog configuration options";
                container session-state-change {
                  presence "Indicates a session-state-change node is configured.";
                  description
                    "Emit syslog when the state of the session changes";
                }
              }
            }
          }
          container path-protection {
            presence "Indicates a path-protection node is configured.";
            description
              "Candidate path protection";
          }
          container bfd {
            presence "Indicates a bfd node is configured.";
            description
              "Bidirectional Forwarding Detection (BFD)";
            container disable {
              presence "Indicates a disable node is configured.";
              description
                "Do not create BFD sessions";
            }
            container invalidation-action {
              description
                "Action to be taken when BFD session is invalidated";
              container none {
                must "not(../down)";
                presence "Indicates a none node is configured.";
                description
                  "BFD session state does not affect LSP state, use for diagnostic purposes";
              }
              container down {
                must "not(../none)";
                presence "Indicates a down node is configured.";
                description
                  "LSP can only be operationally up if the BFD session is up";
              }
            }
            leaf minimum-interval {
              type uint32 {
                range "50..30000" {
                  description
                    "Hello interval in milliseconds (default 150)";
                }
              }
              description
                "Hello interval (default 150)";
            }
            leaf multiplier {
              type uint32 {
                range "1..10" {
                  description
                    "Number of missed BFD packets to declare session down (default 3)";
                }
              }
              description
                "Number of missed BFD packets to declare session down";
            }
            container reverse-path {
              presence "Indicates a reverse-path node is configured.";
              description
                "Specify parameters about the reverse path back to the head-end";
              leaf binding-label {
                type uint32 {
                  range "16..1048575" {
                    description
                      "Binding label of a policy/tunnel from destination to head-end";
                  }
                }
                description
                  "BFD packets return to head-end by using a binding label";
              }
            }
            container logging {
              presence "Indicates a logging node is configured.";
              description
                "Syslog configuration options";
              container session-state-change {
                presence "Indicates a session-state-change node is configured.";
                description
                  "Emit syslog when the state of the session changes";
              }
            }
          }
          container effective-metric {
            presence "Indicates a effective-metric node is configured.";
            description
              "Effective metric configuration submode";
            leaf value {
              type uint32 {
                range "0..4294967295" {
                  description
                    "Integer value of metric";
                }
              }
              description
                "Metric value, advertised to other protocols";
            }
            container type {
              description
                "Metric type, advertised to other protocols";
              container igp {
                must
                  "not(../te or ../latency
                   or ../hopcount)";
                presence "Indicates a igp node is configured.";
                description
                  "IGP metric type";
              }
              container te {
                must
                  "not(../igp or ../latency
                   or ../hopcount)";
                presence "Indicates a te node is configured.";
                description
                  "TE metric type";
              }
              container latency {
                must
                  "not(../igp or ../te
                   or ../hopcount)";
                presence "Indicates a latency node is configured.";
                description
                  "LATENCY metric type";
              }
              container hopcount {
                must
                  "not(../igp or ../te
                   or ../latency)";
                presence "Indicates a hopcount node is configured.";
                description
                  "HOPCOUNT metric type";
              }
            }
          }
          leaf pce-group {
            type xr:Cisco-ios-xr-string {
              length "1..16" {
                description
                  "Name of the PCE group - maximum 16 characters";
              }
            }
            description
              "PCE group configuration";
          }
        }
      }
      container interfaces {
        description
          "Enable SR-TE on an interface";
        list interface {
          key "interface-name";
          description
            "Enable SR-TE on an interface";
          leaf interface-name {
            type xr:Interface-name;
            description
              "Enable SR-TE on an interface";
          }
          container affinity {
            description
              "Interface affinity configuration";
            list names {
              key "name";
              description
                "Affinity name";
              leaf name {
                type string {
                  length "1..32" {
                    description
                      "Affinity color name";
                  }
                }
                description
                  "Affinity color name";
              }
            }
          }
          leaf metric {
            type uint32 {
              range "0..2147483647" {
                description
                  "TE metric value";
              }
            }
            description
              "Interface TE metric configuration";
          }
        }
      }
      container affinity-map {
        description
          "Affinity map configuration";
        list names {
          key "name";
          description
            "Affinity name";
          leaf name {
            type string {
              length "1..32" {
                description
                  "Affinity color name";
              }
            }
            description
              "Affinity name";
          }
          leaf bit-position {
            type uint32 {
              range "0..255" {
                description
                  "Affinity attribute bit position";
              }
            }
            mandatory true;
            description
              "Bit Position for the mapped affinity";
          }
        }
      }
      container segment-lists {
        description
          "Identifying name for segment-list";
        list segment-list {
          key "segment-list-name";
          description
            "Identifying name for segment-list";
          leaf segment-list-name {
            type string {
              length "1..128" {
                description
                  "Identifying name for segment-list";
              }
            }
            description
              "Identifying name for segment-list";
          }
          container indexes {
            description
              "Next entry index";
            list index {
              must "mpls/label or mpls/adjacency";
              key "index-number";
              description
                "Next entry index";
              leaf index-number {
                type uint32 {
                  range "1..65535" {
                    description
                      "Index number";
                  }
                }
                description
                  "Next entry index";
              }
              container mpls {
                description
                  "MPLS configuration";
                leaf label {
                  type uint32 {
                    range "0..1048575" {
                      description
                        "MPLS label value";
                    }
                  }
                  description
                    "MPLS label configuration";
                }
                leaf adjacency {
                  type inet:ip-address-no-zone;
                  description
                    "Specify hop address";
                }
              }
            }
          }
        }
      }
      container timers {
        description
          "SR-TE timers configuration";
        leaf install-delay {
          type uint32 {
            range "0..300" {
              description
                "Install timer value in seconds (0 for immediate installation)";
            }
          }
          description
            "Delay before switching to a reoptimized path (default: 10 seconds)";
        }
        leaf cleanup-delay {
          type uint32 {
            range "0..300" {
              description
                "Cleanup timer value in seconds (0 for immediate cleanup)";
            }
          }
          description
            "Delay before cleaning up previous path (default: 10 seconds)";
        }
        leaf periodic-reoptimization {
          type uint32 {
            range "0..86400" {
              description
                "Reoptimization timer value in seconds (0 to disable periodic reoptimization)";
            }
          }
          description
            "How often to perform periodic reoptimization of policies (default: 600 seconds)";
        }
        container candidate-path {
          description
            "Candidate path related timers";
          leaf cleanup-delay {
            type uint32 {
              range "0..86400" {
                description
                  "Cleanup timer value in seconds (0 for immediate cleanup)";
              }
            }
            description
              "Delay before cleaning up candidate paths (default: 120 seconds)";
          }
        }
        leaf init-verify-restart {
          type uint32 {
            range "10..10000" {
              description
                "Time value in seconds. Default is 40";
            }
          }
          description
            "Timer to wait for topology convergence after topology starts populating for restart case";
        }
        leaf init-verify-switchover {
          type uint32 {
            range "10..10000" {
              description
                "Time value in seconds. Default is 60";
            }
          }
          description
            "Timer to wait for topology convergence after topology starts populating for switchover case";
        }
        leaf init-verify-startup {
          type uint32 {
            range "10..10000" {
              description
                "Time value in seconds. Default is 120";
            }
          }
          description
            "Timer to wait for topology convergence after topology starts populating for startup case";
        }
      }
      container pcc {
        presence "Indicates a pcc node is configured.";
        description
          "Path Computation Client configurations";
        container source-address {
          description
            "Source address of PCEP sessions";
          leaf ipv4 {
            type inet:ipv4-address-no-zone;
            description
              "IPv4 address";
          }
          leaf ipv6 {
            type inet:ipv6-address-no-zone;
            description
              "IPv6 address";
          }
        }
        container pce {
          description
            "Path Computation Element (PCE) server";
          container address {
            description
              "Address of PCE server";
            container ipv4s {
              description
                "IPv4 address of PCE server";
              list ipv4 {
                key "address";
                description
                  "IPv4 address of PCE server";
                leaf address {
                  type inet:ipv4-address-no-zone;
                  description
                    "IPv4 address of PCE server";
                }
                leaf precedence {
                  type uint32 {
                    range "0..255" {
                      description
                        "Precedence value (0 is most preferred, 255 is least preferred)";
                    }
                  }
                  description
                    "Precedence of PCE peer, default is 255";
                }
                container password {
                  description
                    "Configure password for MD5 authentication";
                  leaf encrypted {
                    type string {
                      length "1..800" {
                        description
                          "The ENCRYPTED password string";
                      }
                    }
                    description
                      "Specifies an ENCRYPTED password will follow";
                  }
                }
                leaf keychain {
                  type xr:Cisco-ios-xr-string {
                    length "1..32" {
                      description
                        "Name of the key chain - maximum 32 characters";
                    }
                  }
                  description
                    "Configure keychain based authentication for PCC";
                }
                leaf tcp-ao {
                  type xr:Cisco-ios-xr-string {
                    length "1..32" {
                      description
                        "Name of the TCP AO keychain - maximum 32 characters";
                    }
                  }
                  description
                    "Configure AO keychain based authentication";
                }
                container include-tcp-options {
                  presence "Indicates a include-tcp-options node is configured.";
                  description
                    "Include other TCP options in the header";
                }
                leaf pce-group {
                  type xr:Cisco-ios-xr-string {
                    length "1..16" {
                      description
                        "Name of the PCE group - maximum 16 characters";
                    }
                  }
                  description
                    "Make this PCE part of a PCE group";
                }
              }
            }
            container ipv6s {
              description
                "IPv6 address of PCE server";
              list ipv6 {
                key "address";
                description
                  "IPv6 address of PCE server";
                leaf address {
                  type inet:ipv6-address-no-zone;
                  description
                    "IPv6 address of PCE server";
                }
                leaf precedence {
                  type uint32 {
                    range "0..255" {
                      description
                        "Precedence value (0 is most preferred, 255 is least preferred)";
                    }
                  }
                  description
                    "Precedence of PCE peer, default is 255";
                }
                container password {
                  description
                    "Configure password for MD5 authentication";
                  leaf encrypted {
                    type string {
                      length "1..800" {
                        description
                          "The ENCRYPTED password string";
                      }
                    }
                    description
                      "Specifies an ENCRYPTED password will follow";
                  }
                }
                leaf tcp-ao {
                  type xr:Cisco-ios-xr-string {
                    length "1..32" {
                      description
                        "Name of the TCP AO keychain - maximum 32 characters";
                    }
                  }
                  description
                    "Configure AO keychain based authentication";
                }
                container include-tcp-options {
                  presence "Indicates a include-tcp-options node is configured.";
                  description
                    "Include other TCP options in the header";
                }
                leaf pce-group {
                  type xr:Cisco-ios-xr-string {
                    length "1..16" {
                      description
                        "Name of the PCE group - maximum 16 characters";
                    }
                  }
                  description
                    "Make this PCE part of a PCE group";
                }
              }
            }
          }
        }
        container report-all {
          presence "Indicates a report-all node is configured.";
          description
            "Report all local SR policies to connected PCEP peers";
        }
        container timers {
          description
            "Configure various timer values";
          leaf delegation-timeout {
            type uint32 {
              range "0..1576800000" {
                description
                  "Timer value in seconds, 0 to disable the delegation timeout (default 300)";
              }
            }
            description
              "Maximum time delegated SR-TE policies can remain up without an active connection to a PCE";
          }
          leaf keepalive {
            type uint32 {
              range "0..255" {
                description
                  "Timer value in seconds, 0 means we do not send keepalives, (default 30)";
              }
            }
            description
              "Maximum time between two consecutive PCEP messages sent by this node";
          }
          leaf deadtimer {
            type uint32 {
              range "1..255" {
                description
                  "Timer value in seconds (default 120)";
              }
            }
            description
              "Amount of time after which the peer can declare this session down, if no PCEP message has been received";
          }
          container initiated {
            description
              "Configure timers related to PCE Initiated policies";
            leaf state {
              type uint32 {
                range "0..86400" {
                  description
                    "Timer value in seconds (default 600)";
                }
              }
              description
                "Amount of time that PCE initiated policy can exist as an orphan before it is cleaned up";
            }
            leaf orphan {
              type uint32 {
                range "0..180" {
                  description
                    "Timer value in seconds (default 180)";
                }
              }
              description
                "Amount of time that PCE initiated policy remains delegated to a peer that has gone down";
            }
          }
        }
        container profiles {
          description
            "Configuration template that can be specified via PCEP";
          list profile {
            key "profile-id";
            description
              "Configuration template that can be specified via PCEP";
            leaf profile-id {
              type uint32 {
                range "1..65534" {
                  description
                    "numeric identifier for the profile";
                }
              }
              description
                "Configuration template that can be specified via PCEP";
            }
            container steering {
              presence "Indicates a steering node is configured.";
              description
                "Steering options for PCC profile";
              container path-invalidation {
                description
                  "Path invalidation action, default is to fall back to unconstrained IGP path";
                container drop {
                  presence "Indicates a drop node is configured.";
                  description
                    "If path became invalid, keep policy up, but drop all traffic sent on the policy";
                }
              }
            }
            container autoroute {
              description
                "Autoroute configuration";
              container include {
                description
                  "Prefixes for which IGP routes will be installed";
                container ipv4 {
                  description
                    "IPv4 address family";
                  container all {
                    presence "Indicates a all node is configured.";
                    description
                      "Include all eligible prefixes";
                  }
                }
                container ipv6 {
                  description
                    "IPv6 address family";
                  container all {
                    presence "Indicates a all node is configured.";
                    description
                      "Include all eligible IPv6 prefixes";
                  }
                }
              }
              leaf forward-class {
                type uint32 {
                  range "0..7" {
                    description
                      "Forward class value, default value is 8";
                  }
                }
                description
                  "Specify forward class for policy based routing";
              }
              container force-sr-include {
                presence "Indicates a force-sr-include node is configured.";
                description
                  "Force policy to carry SR MPLS traffic as well";
              }
              container metric {
                description
                  "Autoroute metric";
                leaf constant {
                  type uint32 {
                    range "1..2147483647" {
                      description
                        "Absolute metric";
                    }
                  }
                  must "not(../relative)";
                  description
                    "Set metric mode constant";
                }
                leaf relative {
                  type int32 {
                    range "-10..10" {
                      description
                        "Relative metric";
                    }
                  }
                  must "not(../constant)";
                  description
                    "Set metric mode relative";
                }
              }
            }
          }
        }
        container redundancy {
          description
            "PCC redundancy configuration";
          container pcc-centric {
            presence "Indicates a pcc-centric node is configured.";
            description
              "Enable PCC centric model, where PCC only allows the lowest precedence PCE to initiate policies";
          }
        }
        container srpag {
          presence "Indicates a srpag node is configured.";
          description
            "Enable signaling of SR Policy Association Group";
        }
      }
      container on-demand {
        description
          "On-Demand configuration";
        container colors {
          description
            "On-Demand color configuration";
          list color {
            key "color-value";
            description
              "On-Demand color configuration";
            leaf color-value {
              type uint32 {
                range "1..4294967295" {
                  description
                    "color value";
                }
              }
              description
                "On-Demand color configuration";
            }
            container srv6 {
              presence "Indicates a srv6 node is configured.";
              description
                "Segment Routing IPv6";
              container locator {
                description
                  "Configure locator";
                leaf locator-name {
                  type xr:Cisco-ios-xr-string {
                    length "1..64" {
                      description
                        "Specify locator name with max 64 characters";
                    }
                  }
                  must "../binding-sid/dynamic/behavior/ub6-insert-reduced";
                  description
                    "Specify locator name with max 64 characters";
                }
                container binding-sid {
                  description
                    "Binding-SID allocation options";
                  container dynamic {
                    description
                      "Dynamic based option";
                    container behavior {
                      description
                        "Binding-SID behavior options";
                      container ub6-insert-reduced {
                        must "../../../../locator-name";
                        presence "Indicates a ub6-insert-reduced node is configured.";
                        description
                          "Binding-SID insert reduced behavior";
                      }
                    }
                  }
                }
              }
            }
            container per-flow {
              presence "Indicates a per-flow node is configured.";
              description
                "Per-flow configuration";
              container forward-classes {
                description
                  "Specify forward class for per-flow based routing";
                list forward-class {
                  key "forward-class-value";
                  description
                    "Forward class value";
                  leaf forward-class-value {
                    type uint32 {
                      range "0..7" {
                        description
                          "Forward class value";
                      }
                    }
                    description
                      "Forward class value";
                  }
                  leaf color {
                    type uint32 {
                      range "1..4294967295" {
                        description
                          "Color value";
                      }
                    }
                    mandatory true;
                    description
                      "Specify corresponding policy color for the forwarding class";
                  }
                }
                leaf default {
                  type uint32 {
                    range "0..7" {
                      description
                        "Forward-class value";
                    }
                  }
                  description
                    "Configure default forward-class";
                }
              }
            }
            container dynamic {
              presence "Indicates a dynamic node is configured.";
              description
                "Dynamically computed path";
              container pcep {
                presence "Indicates a pcep node is configured.";
                description
                  "Path Computation Element Protocol related configuration";
              }
              container anycast-sid-inclusion {
                presence "Indicates a anycast-sid-inclusion node is configured.";
                description
                  "Anycast SID Inclusion";
              }
              container metric {
                presence "Indicates a metric node is configured.";
                description
                  "Specify the path computation metric options";
                container type {
                  description
                    "Specify the path computation metric type to be used";
                  container igp {
                    must
                      "not(../te or ../hopcount
                       or ../latency)";
                    presence "Indicates a igp node is configured.";
                    description
                      "Use the IGP metric for path computation";
                  }
                  container te {
                    must
                      "not(../igp or ../hopcount
                       or ../latency)";
                    presence "Indicates a te node is configured.";
                    description
                      "Use the TE metric for path computation";
                  }
                  container hopcount {
                    must
                      "not(../igp or ../te
                       or ../latency)";
                    presence "Indicates a hopcount node is configured.";
                    description
                      "Use the least number of hops for path computation";
                  }
                  container latency {
                    must
                      "not(../igp or ../te
                       or ../hopcount)";
                    presence "Indicates a latency node is configured.";
                    description
                      "Use the measured latency metric for path computation";
                  }
                }
                container margin {
                  description
                    "Metric margin";
                  leaf absolute {
                    type uint32 {
                      range "0..2147483647" {
                        description
                          "Absolute metric margin value";
                      }
                    }
                    must "not(../relative)";
                    description
                      "Absolute metric margin";
                  }
                  leaf relative {
                    type uint32 {
                      range "0..2147483647" {
                        description
                          "Relative metric margin value";
                      }
                    }
                    must "not(../absolute)";
                    description
                      "Relative metric margin";
                  }
                }
              }
              container disjoint-path {
                description
                  "Request disjoint path computation";
                leaf group-id {
                  type uint32 {
                    range "1..65535" {
                      description
                        "Group ID";
                    }
                  }
                  description
                    "Group ID";
                }
                container type {
                  description
                    "Disjointness type";
                  container link {
                    must
                      "not(../node or ../srlg
                       or ../srlg-node)";
                    presence "Indicates a link node is configured.";
                    description
                      "Link Disjointness";
                    leaf sub-id {
                      type uint32 {
                        range "1..65535" {
                          description
                            "Subgroup ID number";
                        }
                      }
                      description
                        "Subgroup ID";
                    }
                  }
                  container node {
                    must
                      "not(../link or ../srlg
                       or ../srlg-node)";
                    presence "Indicates a node node is configured.";
                    description
                      "Node Disjointness";
                    leaf sub-id {
                      type uint32 {
                        range "1..65535" {
                          description
                            "Subgroup ID number";
                        }
                      }
                      description
                        "Subgroup ID";
                    }
                  }
                  container srlg {
                    must
                      "not(../link or ../node
                       or ../srlg-node)";
                    presence "Indicates a srlg node is configured.";
                    description
                      "SRLG Disjointness";
                    leaf sub-id {
                      type uint32 {
                        range "1..65535" {
                          description
                            "Subgroup ID number";
                        }
                      }
                      description
                        "Subgroup ID";
                    }
                  }
                  container srlg-node {
                    must
                      "not(../link or ../node
                       or ../srlg)";
                    presence "Indicates a srlg-node node is configured.";
                    description
                      "SRLG Node Disjointness";
                    leaf sub-id {
                      type uint32 {
                        range "1..65535" {
                          description
                            "Subgroup ID number";
                        }
                      }
                      description
                        "Subgroup ID";
                    }
                  }
                }
              }
              leaf sid-algorithm {
                type uint32 {
                  range "128..255" {
                    description
                      "The Prefix-SID algorithm value";
                  }
                }
                description
                  "DEPRECATED in IOS-XR 7.5.1. Please use command segment-routing traffic-eng on-demand color <color> constraints segments sid-algorithm <sig-algorithm>. Specify the Prefix-SID aglorithm";
              }
              container bounds {
                description
                  "Assign anycast metric bounds to path";
                container cumulative {
                  description
                    "Cumulative metric bound";
                  container type {
                    description
                      "The metric type for the bound";
                    leaf te {
                      type uint32 {
                        range "1..4294967295" {
                          description
                            "Bound metric value";
                        }
                      }
                      description
                        "Bound metric type TE";
                    }
                    leaf igp {
                      type uint32 {
                        range "1..4294967295" {
                          description
                            "Bound metric value";
                        }
                      }
                      description
                        "Bound metric type IGP";
                    }
                    leaf latency {
                      type uint32 {
                        range "1..4294967295" {
                          description
                            "Bound metric value in microseconds";
                        }
                      }
                      description
                        "Bound metric type latency";
                    }
                    leaf hopcount {
                      type uint32 {
                        range "1..4294967295" {
                          description
                            "Bound metric value";
                        }
                      }
                      description
                        "Bound metric type hopcount";
                    }
                  }
                }
              }
              container affinity {
                description
                  "Assign affinities to path";
                container include-any {
                  description
                    "Affinity attributes - at least one must be included";
                  container name {
                    description
                      "Affinity name";
                    container affinity-colors {
                      description
                        "Affinity color name";
                      list affinity-color {
                        key "affinity-color-name";
                        description
                          "Affinity color name";
                        leaf affinity-color-name {
                          type string {
                            length "1..32" {
                              description
                                "Affinity color name";
                            }
                          }
                          description
                            "Affinity color name";
                        }
                      }
                    }
                  }
                }
                container include-all {
                  description
                    "Affinity attributes - all must be included";
                  container name {
                    description
                      "Affinity name";
                    container affinity-colors {
                      description
                        "Affinity color name";
                      list affinity-color {
                        key "affinity-color-name";
                        description
                          "Affinity color name";
                        leaf affinity-color-name {
                          type string {
                            length "1..32" {
                              description
                                "Affinity color name";
                            }
                          }
                          description
                            "Affinity color name";
                        }
                      }
                    }
                  }
                }
                container exclude-any {
                  description
                    "Affinity attributes to exclude - presence of at least one excludes link";
                  container name {
                    description
                      "Affinity name";
                    container affinity-colors {
                      description
                        "Affinity color name";
                      list affinity-color {
                        key "affinity-color-name";
                        description
                          "Affinity color name";
                        leaf affinity-color-name {
                          type string {
                            length "1..32" {
                              description
                                "Affinity color name";
                            }
                          }
                          description
                            "Affinity color name";
                        }
                      }
                    }
                  }
                }
              }
            }
            leaf bandwidth {
              type uint32 {
                range "1..4294967295" {
                  description
                    "Bandwidth value in kbps";
                }
              }
              description
                "Requested Bandwidth";
            }
            leaf maximum-sid-depth {
              type uint32 {
                range "1..255" {
                  description
                    "Maximum SID Depth";
                }
              }
              description
                "Maximum SID Depth";
            }
            leaf max-install-standby-cpaths {
              type uint32 {
                range "0..3" {
                  description
                    "Number of standby candidate path LSPs to allow";
                }
              }
              description
                "Allow additional candidate paths to warm up non forwarding LSPs";
            }
            container steering {
              presence "Indicates a steering node is configured.";
              description
                "Steering options for on-demand color";
              container labeled-services {
                description
                  "Steering options for labeled services";
                container disable {
                  presence "Indicates a disable node is configured.";
                  description
                    "Disable traffic steering for labeled services";
                }
              }
              container path-invalidation {
                description
                  "Path invalidation action, default is to fall back to unconstrained IGP path";
                container drop {
                  presence "Indicates a drop node is configured.";
                  description
                    "If path became invalid, keep policy up, but drop all traffic sent on the policy";
                }
              }
            }
            container performance-measurement {
              presence "Indicates a performance-measurement node is configured.";
              description
                "Performance Measurement configuration submode";
              container reverse-path {
                description
                  "Specify parameters about the reverse path back to the head-end";
                leaf label {
                  type uint32 {
                    range "16..1048575" {
                      description
                        "Reverse path label";
                    }
                  }
                  description
                    "PM packets return to head-end using a label";
                }
              }
              container liveness-detection {
                presence "Indicates a liveness-detection node is configured.";
                description
                  "Liveness detection configuration submode";
                container invalidation-action {
                  description
                    "Action to be taken when PM liveness session is invalidated";
                  container none {
                    must "not(../down)";
                    presence "Indicates a none node is configured.";
                    description
                      "PM liveness session state does not affect LSP state, use for diagnostic purposes";
                  }
                  container down {
                    must "not(../none)";
                    presence "Indicates a down node is configured.";
                    description
                      "LSP can only be operationally up if the PM liveness session is up";
                  }
                }
                container liveness-profile {
                  description
                    "SR Policy liveness profile name";
                  leaf name {
                    type xr:Cisco-ios-xr-string {
                      length "1..256" {
                        description
                          "Profile name";
                      }
                    }
                    description
                      "Profile name";
                  }
                  container backup {
                    description
                      "SR Policy liveness backup profile name";
                    leaf name {
                      type xr:Cisco-ios-xr-string {
                        length "1..256" {
                          description
                            "Profile name";
                        }
                      }
                      description
                        "Profile name";
                    }
                  }
                }
                container logging {
                  presence "Indicates a logging node is configured.";
                  description
                    "Syslog configuration options";
                  container session-state-change {
                    presence "Indicates a session-state-change node is configured.";
                    description
                      "Emit syslog when the state of the session changes";
                  }
                }
              }
              container delay-measurement {
                presence "Indicates a delay-measurement node is configured.";
                description
                  "Delay-measurement configuration submode";
                container delay-profile {
                  description
                    "SR Policy delay profile name";
                  leaf name {
                    type xr:Cisco-ios-xr-string {
                      length "1..256" {
                        description
                          "Profile name";
                      }
                    }
                    description
                      "Profile name";
                  }
                }
                container logging {
                  presence "Indicates a logging node is configured.";
                  description
                    "Syslog configuration options";
                  container delay-exceeded {
                    presence "Indicates a delay-exceeded node is configured.";
                    description
                      "Emit syslog when the delay exceeds the threshold";
                  }
                }
              }
            }
            container source-address {
              description
                "Source address of ODN policies";
              leaf ipv4 {
                type inet:ipv4-address-no-zone;
                must "not(../ipv6)";
                description
                  "IPv4 address";
              }
              leaf ipv6 {
                type inet:ipv6-address-no-zone;
                must "not(../ipv4)";
                description
                  "IPv6 address";
              }
            }
            container constraints {
              description
                "Candidate path constraints";
              container segments {
                description
                  "Path segments constraints";
                leaf sid-algorithm {
                  type uint32 {
                    range "0..255" {
                      description
                        "'0' for regular SIDs, '1' for strict-spf SIDs, '128' - '255' for algorithm SIDs";
                    }
                  }
                  description
                    "Specify the Prefix-SID algorithm";
                }
                container protection {
                  description
                    "Protection type";
                  container protected-preferred {
                    must
                      "not(../protected-only or ../unprotected-only
                       or ../unprotected-preferred)";
                    presence "Indicates a protected-preferred node is configured.";
                    description
                      "Protected adj-SID preferred (default)";
                  }
                  container protected-only {
                    must
                      "not(../protected-preferred or ../unprotected-only
                       or ../unprotected-preferred)";
                    presence "Indicates a protected-only node is configured.";
                    description
                      "Protected adj-SID only";
                  }
                  container unprotected-only {
                    must
                      "not(../protected-preferred or ../protected-only
                       or ../unprotected-preferred)";
                    presence "Indicates a unprotected-only node is configured.";
                    description
                      "Unprotected adj-SID only";
                  }
                  container unprotected-preferred {
                    must
                      "not(../protected-preferred or ../protected-only
                       or ../unprotected-only)";
                    presence "Indicates a unprotected-preferred node is configured.";
                    description
                      "Unprotected adj-SID preferred";
                  }
                }
              }
            }
            container bfd {
              presence "Indicates a bfd node is configured.";
              description
                "Bidirectional Forwarding Detection (BFD)";
              container disable {
                presence "Indicates a disable node is configured.";
                description
                  "Do not create BFD sessions";
              }
              container invalidation-action {
                description
                  "Action to be taken when BFD session is invalidated";
                container none {
                  must "not(../down)";
                  presence "Indicates a none node is configured.";
                  description
                    "BFD session state does not affect LSP state, use for diagnostic purposes";
                }
                container down {
                  must "not(../none)";
                  presence "Indicates a down node is configured.";
                  description
                    "LSP can only be operationally up if the BFD session is up";
                }
              }
              leaf minimum-interval {
                type uint32 {
                  range "50..30000" {
                    description
                      "Hello interval in milliseconds (default 150)";
                  }
                }
                description
                  "Hello interval (default 150)";
              }
              leaf multiplier {
                type uint32 {
                  range "1..10" {
                    description
                      "Number of missed BFD packets to declare session down (default 3)";
                  }
                }
                description
                  "Number of missed BFD packets to declare session down";
              }
              container logging {
                presence "Indicates a logging node is configured.";
                description
                  "Syslog configuration options";
                container session-state-change {
                  presence "Indicates a session-state-change node is configured.";
                  description
                    "Emit syslog when the state of the session changes";
                }
              }
            }
            container effective-metric {
              presence "Indicates a effective-metric node is configured.";
              description
                "Effective metric configuration submode";
              leaf value {
                type uint32 {
                  range "0..4294967295" {
                    description
                      "Integer value of metric";
                  }
                }
                description
                  "Metric value, advertised to other protocols";
              }
              container type {
                description
                  "Metric type, advertised to other protocols";
                container igp {
                  must
                    "not(../te or ../latency
                     or ../hopcount)";
                  presence "Indicates a igp node is configured.";
                  description
                    "IGP metric type";
                }
                container te {
                  must
                    "not(../igp or ../latency
                     or ../hopcount)";
                  presence "Indicates a te node is configured.";
                  description
                    "TE metric type";
                }
                container latency {
                  must
                    "not(../igp or ../te
                     or ../hopcount)";
                  presence "Indicates a latency node is configured.";
                  description
                    "LATENCY metric type";
                }
                container hopcount {
                  must
                    "not(../igp or ../te
                     or ../latency)";
                  presence "Indicates a hopcount node is configured.";
                  description
                    "HOPCOUNT metric type";
                }
              }
            }
            leaf pce-group {
              type xr:Cisco-ios-xr-string {
                length "1..16" {
                  description
                    "Name of the PCE group - maximum 16 characters";
                }
              }
              description
                "PCE group configuration";
            }
          }
        }
      }
      container binding-sid {
        description
          "Binding SID allocation options";
        container explicit {
          description
            "Explicit based options";
          container fallback-dynamic {
            must "not(../enforce-srlb)";
            presence "Indicates a fallback-dynamic node is configured.";
            description
              "Fallback to dynamic allocation if explicit binding SID is not available";
          }
          container enforce-srlb {
            must "not(../fallback-dynamic)";
            presence "Indicates a enforce-srlb node is configured.";
            description
              "Enforce explicit binding SID to be within SRLB range; explicit binding SIDs outside the range will be considered invalid";
          }
        }
        container dynamic {
          description
            "Dynamic based options";
          container disable {
            presence "Indicates a disable node is configured.";
            description
              "Disable dynamic binding SID allocation; candidate paths without an explicit binding SID will be considered invalid";
          }
        }
      }
      container te-latency {
        presence "Indicates a te-latency node is configured.";
        description
          "Use TE-latency algorithm";
      }
      leaf maximum-sid-depth {
        type uint32 {
          range "1..255" {
            description
              "Maximum SID Depth";
          }
        }
        description
          "Maximum number of SIDs that the PCC can impose on a packet";
      }
      leaf kshortest-paths {
        type uint32 {
          range "1..200" {
            description
              "Maximum number of attempted paths for cumulative bounds (default 100)";
          }
        }
        description
          "Maximum number of path attempts when applying Yen's algorithm";
      }
      container oor {
        description
          "Out-of-resources handling configuration";
        leaf maximum-paths {
          type uint32 {
            range "0..4294967295" {
              description
                "Number of paths (0 for no limit; default is 0)";
            }
          }
          description
            "Maximum number of LSP paths that can be created";
        }
        leaf maximum-paths-batch {
          type uint32 {
            range "0..4294967295" {
              description
                "Number of path operations (0 for no limit; default is 0)";
            }
          }
          description
            "Maximum total number of LSP path operations in a single batch";
        }
      }
      leaf max-install-standby-cpaths {
        type uint32 {
          range "1..3" {
            description
              "Number of standby candidate path LSPs to allow";
          }
        }
        description
          "Global Policy limit on installed standby cpaths";
      }
      container bfd {
        presence "Indicates a bfd node is configured.";
        description
          "Bidirectional Forwarding Detection (BFD)";
        container timers {
          presence "Indicates a timers node is configured.";
          description
            "BFD specific timers";
          leaf session-bringup {
            type uint32 {
              range "10..3600" {
                description
                  "Session bringup timer in seconds (default 60)";
              }
            }
            description
              "How long to wait for new BFD session to come up";
          }
        }
      }
      container separate-next-hop {
        presence "Indicates a separate-next-hop node is configured.";
        description
          "Next-hop seperation feature";
      }
      container effective-metric {
        presence "Indicates a effective-metric node is configured.";
        description
          "Effective metric configuration submode";
        container admin-distance {
          presence "Indicates a admin-distance node is configured.";
          description
            "Administrative distance";
          container metric-type {
            description
              "Metric type, advertised to other protocols";
            container igp {
              description
                "IGP metric type";
              leaf admin-distance {
                type uint32 {
                  range "1..4294967295" {
                    description
                      "AD for the IGP metric, default (30)";
                  }
                }
                description
                  "Administrative distance advertised for this metric type";
              }
            }
            container te {
              description
                "TE metric type";
              leaf admin-distance {
                type uint32 {
                  range "1..4294967295" {
                    description
                      "AD for the TE metric, default (20)";
                  }
                }
                description
                  "Administrative distance advertised for this metric type";
              }
            }
            container latency {
              description
                "LATENCY metric type";
              leaf admin-distance {
                type uint32 {
                  range "1..4294967295" {
                    description
                      "AD for the LATENCY metric, default (10)";
                  }
                }
                description
                  "Administrative distance advertised for this metric type";
              }
            }
            container hopcount {
              description
                "HOPCOUNT metric type";
              leaf admin-distance {
                type uint32 {
                  range "1..4294967295" {
                    description
                      "AD for the HOPCOUNT metric, default (40)";
                  }
                }
                description
                  "Administrative distance advertised for this metric type";
              }
            }
            container unknown {
              description
                "Unknown metric type";
              leaf admin-distance {
                type uint32 {
                  range "1..4294967295" {
                    description
                      "AD for the unknown metric type (used for explicit segment-lists), default (100)";
                  }
                }
                description
                  "Administrative distance advertised for this metric type";
              }
            }
          }
        }
      }
    }
  }
}
