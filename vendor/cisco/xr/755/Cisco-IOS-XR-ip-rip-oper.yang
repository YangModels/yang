module Cisco-IOS-XR-ip-rip-oper {
  namespace "http://cisco.com/ns/yang/Cisco-IOS-XR-ip-rip-oper";
  prefix ip-rip-oper;

  import ietf-inet-types {
    prefix inet;
  }
  import Cisco-IOS-XR-types {
    prefix xr;
  }
  import cisco-semver {
    prefix semver;
  }
  include Cisco-IOS-XR-ip-rip-oper-sub1 {
    revision-date 2022-03-31;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ip-rip package operational data.
     
     This module contains definitions
     for the following management objects:
       rip: RIP operational data
     
     Copyright (c) 2013-2022 by Cisco Systems, Inc.
     All rights reserved.";

  revision 2022-03-31 {
    description
      "Removed Unused leafs triggered rip and neighbor from IPv6 information of interfaces
       2021-12-10
         Corrected pathname for vrf global data
       2021-09-15
         Changed datatype of IPv6Prefix in IPv6Route
       2021-09-07
         Added support for RIPv6 in oper schema";
    semver:module-version "1.0.2M";
  }
  revision 2019-04-05 {
    description
      "Establish semantic version baseline.";
    semver:module-version "1.0.1";
  }
  revision 2015-11-09 {
    description
      "IOS XR 6.0 revision.";
  }

  grouping IPV6-INTERFACE-TABLE {
    description
      "Common node of ipv6-default-vrf, ipv6vrf";
    container ipv6-interfaces {
      description
        "RIPv6 interfaces";
      list ipv6-interface {
        key "interface-name";
        description
          "Information about a particular RIPv6 interface";
        leaf interface-name {
          type xr:Interface-name;
          description
            "Interface name";
        }
        uses V6-RIP-SHOW-INTERFACE-BD;
      }
    }
  }

  grouping ROUTE-TABLE {
    description
      "Common node of default-vrf, vrf";
    container routes {
      description
        "RIP route database";
      list route {
        description
          "A route in the RIP database";
        leaf prefix {
          type inet:ipv4-address-no-zone;
          description
            "Network prefix";
        }
        leaf prefix-length {
          type uint32 {
            range "0..32";
          }
          description
            "Prefix length";
        }
        uses RIP-SHOW-ROUTE-BD;
      }
    }
  }

  grouping IPV6-ROUTE-TABLE {
    description
      "Common node of ipv6-default-vrf, ipv6vrf";
    container ipv6-routes {
      description
        "RIPv6 route database";
      list ipv6-route {
        description
          "A route in the RIPv6 database";
        leaf ipv6-prefix {
          type inet:ipv6-address-no-zone;
          description
            "Network prefix";
        }
        leaf ipv6-prefix-length {
          type uint32 {
            range "0..128";
          }
          description
            "Prefix length";
        }
        uses V6-RIP-SHOW-ROUTE-BD;
      }
    }
  }

  grouping STATISTICS {
    description
      "Common node of default-vrf, vrf";
    container statistics {
      description
        "RIP statistics information";
      uses RIP-SHOW-STATISTICS-BD;
    }
  }

  grouping IPV6-STATISTICS {
    description
      "Common node of ipv6-default-vrf, ipv6vrf";
    container ipv6-statistics {
      description
        "RIP statistics information";
      uses V6-RIP-SHOW-STATISTICS-BD;
    }
  }

  grouping IPV6-CONFIGURATION {
    description
      "Common node of ipv6-default-vrf, ipv6vrf";
    container ipv6-configuration {
      description
        "RIPv6 global configuration";
      uses V6-RIP-SHOW-GLOBAL-CONFIG-BD;
    }
  }

  grouping DEFAULT-VRF {
    description
      "Common node of rip, protocol";
    container default-vrf {
      description
        "RIP operational data for Default VRF";
      uses ROUTE-TABLE;
      uses CONFIGURATION;
      uses STATISTICS;
      uses INTERFACE-TABLE;
    }
  }

  grouping CONFIGURATION {
    description
      "Common node of default-vrf, vrf";
    container configuration {
      description
        "RIP global configuration";
      uses RIP-SHOW-GLOBAL-CONFIG-BD;
    }
  }

  grouping INTERFACE-TABLE {
    description
      "Common node of default-vrf, vrf";
    container interfaces {
      description
        "RIP interfaces";
      list interface {
        key "interface-name";
        description
          "Information about a particular RIP interface";
        leaf interface-name {
          type xr:Interface-name;
          description
            "Interface name";
        }
        uses RIP-SHOW-INTERFACE-BD;
      }
    }
  }

  container rip {
    config false;
    description
      "RIP operational data";
    container vrfs {
      description
        "VRF related operational data";
      list vrf {
        key "vrf-name";
        description
          "Operational data for a particular VRF";
        leaf vrf-name {
          type xr:Cisco-ios-xr-string;
          description
            "Name of the VRF";
        }
        uses ROUTE-TABLE;
        uses CONFIGURATION;
        uses STATISTICS;
        uses INTERFACE-TABLE;
      }
    }
    container protocol {
      description
        "Protocol operational data";
      container protocol-vrf-names {
        description
          "Protocol VRF list";
        list protocol-vrf-name {
          key "vrf-name";
          description
            "Protocol data for a particular VRF";
          container global {
            description
              "Global Information ";
            uses RIP-SHOW-PROTO-VRF-BD;
          }
          leaf vrf-name {
            type xr:Cisco-ios-xr-string;
            description
              "Name of the VRF";
          }
        }
      }
      container process {
        description
          "RIP global process ";
        uses RIP-SHOW-PROTO-PROC-BD;
      }
      uses DEFAULT-VRF;
    }
    container ipv6-address-family {
      description
        "RIPv6 operational data";
      container ipv6vrfs {
        description
          "VRF related operational data for v6";
        list ipv6vrf {
          key "vrf-name";
          description
            "IPv6 Operational data for a particular VRF";
          leaf vrf-name {
            type xr:Cisco-ios-xr-string;
            description
              "Name of the VRF";
          }
          uses IPV6-ROUTE-TABLE;
          uses IPV6-STATISTICS;
          uses IPV6-CONFIGURATION;
          uses IPV6-INTERFACE-TABLE;
        }
      }
      container ipv6-protocol {
        description
          "IPv6 Protocol operational data";
        container ipv6-protocol-vrf-names {
          description
            "IPv6 Protocol VRF list";
          list ipv6-protocol-vrf-name {
            key "vrf-name";
            description
              "IPv6 Protocol data for a particular VRF";
            container ipv6-global {
              description
                "IPv6 Global Information for RIP";
              uses V6-RIP-SHOW-PROTO-VRF-BD;
            }
            leaf vrf-name {
              type xr:Cisco-ios-xr-string;
              description
                "Name of the VRF";
            }
          }
        }
        container ipv6-process {
          description
            "RIP global process ";
          uses V6-RIP-SHOW-PROTO-PROC-BD;
        }
      }
      container ipv6-default-vrf {
        description
          "RIPv6 operational data for Default VRF";
        uses IPV6-ROUTE-TABLE;
        uses IPV6-STATISTICS;
        uses IPV6-CONFIGURATION;
        uses IPV6-INTERFACE-TABLE;
      }
    }
    uses DEFAULT-VRF;
  }
}
