module Cisco-IOS-XR-orrspf-oper {
  namespace "http://cisco.com/ns/yang/Cisco-IOS-XR-orrspf-oper";
  prefix orrspf-oper;

  import Cisco-IOS-XR-types {
    prefix xr;
  }
  import cisco-semver {
    prefix semver;
  }
  include Cisco-IOS-XR-orrspf-oper-sub1 {
    revision-date 2019-04-05;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR orrspf package operational data.
     
     This module contains definitions
     for the following management objects:
       orrspf: ORRSPF operational data
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  typedef Orr-group-name {
    type xr:Cisco-ios-xr-string {
      length "1..33";
    }
    description
      "Orr group name";
  }

  container orrspf {
    config false;
    description
      "ORRSPF operational data";
    container contexts {
      description
        "ORR Context table";
      list context {
        key "name";
        description
          "Information about one ORR Context";
        container context-graphs {
          description
            "Graph table of an ORR Context";
          list context-graph {
            key "name";
            description
              "Graph data in graph table of an ORR Context";
            leaf name {
              type xr:Cisco-ios-xr-string;
              description
                "NodeId";
            }
            uses ORRSPF-SH-GRAPH;
          }
        }
        container context-info {
          description
            "Information about one ORR Context";
          uses ORRSPF-SH-CTX;
        }
        leaf name {
          type xr:Cisco-ios-xr-string;
          description
            "Context Name";
        }
      }
    }
    container orr-groups {
      description
        "ORRGroup table";
      list orr-group {
        key "group-name";
        description
          "Information about one ORR Group";
        container prefixes {
          description
            "Prefix table of an ORR Group";
          list prefix {
            key "name";
            description
              "Prefix in prefix table of an ORR group";
            leaf name {
              type xr:Cisco-ios-xr-string;
              description
                "Prefix";
            }
            uses ORRSPF-SH-PFX;
          }
        }
        container policy {
          description
            "Policy of an ORR group";
          uses ORRSPF-SH-POLICY;
        }
        container topologies {
          description
            "Topology table of an ORR Group";
          list topology {
            key "name";
            description
              "Topology data in topology table of an ORR
               Group";
            leaf name {
              type xr:Cisco-ios-xr-string;
              description
                "NodeId";
            }
            uses ORRSPF-SH-TOPO;
          }
        }
        container graphs {
          description
            "Graph table of an ORR Group";
          list graph {
            key "name";
            description
              "Graph data in graph table of an ORR Group";
            leaf name {
              type xr:Cisco-ios-xr-string;
              description
                "NodeId";
            }
            uses ORRSPF-SH-GRAPH;
          }
        }
        leaf group-name {
          type Orr-group-name;
          description
            "ORR Group Name";
        }
      }
    }
  }
}
