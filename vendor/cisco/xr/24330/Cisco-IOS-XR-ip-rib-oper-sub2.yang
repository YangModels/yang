submodule Cisco-IOS-XR-ip-rib-oper-sub2 {
  belongs-to Cisco-IOS-XR-ip-rib-oper {
    prefix Cisco-IOS-XR-ip-rib-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR ip-rib package operational data.
     
     Copyright (c) 2013-2025 by Cisco Systems, Inc.
     All rights reserved.";

  revision 2025-01-06 {
    description
      "Optimized route and path schema";
    semver:module-version "1.0.0";
  }
  revision 2024-05-07 {
    description
      "Added optional channel-id to rib-client-redist-proto list key";
  }
  revision 2024-03-11 {
    description
      "Add track XTBL flag to nexthop tracking key";
  }
  revision 2024-03-05 {
    description
      "Added labelstk_is_key to path and VPN attributes";
  }
  revision 2024-02-28 {
    description
      "Added route type";
  }
  revision 2024-02-14 {
    description
      "Added RIB-EDM-NHG";
  }
  revision 2024-02-01 {
    description
      "Added table-id field to IPV4-RIB-EDM-ROUTE grouping";
  }
  revision 2024-01-20 {
    description
      "Added HWACK status to route and VPN attributes";
  }
  revision 2024-01-16 {
    description
      "Add redist route bag fallback count to RIB-EDM-STATS-REDIST-ROUTE";
  }
  revision 2023-12-21 {
    description
      "Modify NH addr and add NH damp hist info";
  }
  revision 2023-12-15 {
    description
      "Add channel ID to NextHop clients";
  }
  revision 2023-12-14 {
    description
      "Add ribtph-entries";
  }
  revision 2023-11-27 {
    description
      "Introduce new merged ipv4/ipv6 RIB schema";
  }
  revision 2019-04-05 {
    description
      "Establish semantic version baseline.";
  }
  revision 2015-11-09 {
    description
      "IOS XR 6.0 revision.";
  }

  grouping RIB-EDM-PROTO {
    description
      "Information of a rib protocol";
    leaf protocol-name {
      type string;
      description
        "Name";
    }
    leaf protocol-instance {
      type string;
      description
        "Instance";
    }
    leaf protocol-version {
      type uint32;
      description
        "Proto version";
    }
    leaf number-of-redistribution-clients {
      type uint32;
      description
        "Number of redist clients";
    }
    leaf number-of-protocol-clients {
      type uint32;
      description
        "Number of proto clients";
    }
    leaf number-of-routes {
      type uint32;
      description
        "Number of routes (including deleted)";
    }
    leaf number-of-active-routes {
      type uint32;
      description
        "Number of active routes (not deleted)";
    }
    leaf number-of-deleted-routes {
      type uint32;
      description
        "Number of deleted routes";
    }
    leaf number-of-paths {
      type uint32;
      description
        "Number of paths for all routes";
    }
    leaf protocol-route-memory {
      type uint32;
      description
        "Memory for proto's routes and paths";
    }
    leaf backup-routes-count {
      type uint32;
      description
        "Number of backup routes";
    }
  }
}
