module Cisco-IOS-XR-flowspec-oper {
  namespace "http://cisco.com/ns/yang/Cisco-IOS-XR-flowspec-oper";
  prefix flowspec-oper;

  import Cisco-IOS-XR-types {
    prefix xr;
  }
  import cisco-semver {
    prefix semver;
  }
  include Cisco-IOS-XR-flowspec-oper-sub1 {
    revision-date 2023-11-22;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR flowspec package operational data.
     
     This module contains definitions
     for the following management objects:
       flow-spec: FlowSpec information
     
     Copyright (c) 2013-2023 by Cisco Systems, Inc.
     All rights reserved.";

  revision 2023-11-22 {
    description
      "Added support to include is-dscp-configured and is-rate-configured to infer values of dscp and rate
       2023-09-28
         Added support to include transmitted packets
       2023-07-03
         Added support to fetch total-inactive-flows.
       2023-01-19
         Modified bag file to add support for NOT in tcp flag.";
    semver:module-version "1.1.0";
  }
  revision 2019-04-05 {
    description
      "Establish semantic version baseline.";
    semver:module-version "1.0.0";
  }
  revision 2015-11-09 {
    description
      "IOS XR 6.0 revision.";
  }

  typedef Fs-client {
    type enumeration {
      enum "bgp" {
        value 0;
        description
          "FlowSpec BGP Client";
      }
      enum "one-pk" {
        value 1;
        description
          "FlowSpec OneP Client";
      }
      enum "policy" {
        value 2;
        description
          "FlowSpec Policy Client";
      }
      enum "ha" {
        value 3;
        description
          "FlowSpec HA Client";
      }
      enum "test" {
        value 4;
        description
          "FlowSpec Test Client";
      }
    }
    description
      "Fs client";
  }

  container flow-spec {
    config false;
    description
      "FlowSpec information";
    container clients {
      description
        "Table of Client";
      list client {
        description
          "FlowSpec client information";
        leaf client-type {
          type Fs-client;
          description
            "FlowSpec Client Type";
        }
        leaf client-id {
          type uint32;
          description
            "FlowSpec client ID";
        }
        uses FS-MGR-CLIENT;
      }
    }
    container summary {
      description
        "FlowSpec summary";
      uses FS-MGR-SUMMARY;
    }
    container vrfs {
      description
        "Table of VRF";
      list vrf {
        key "vrf-name";
        description
          "VRF information";
        container afs {
          description
            "Table of AF";
          list af {
            key "af-name";
            description
              "AFI Type (IPv4/IPv6)";
            container table-summary {
              description
                "FlowSpec summary for VRF+AFI tables";
              uses FS-MGR-TBL-SUMMARY;
            }
            container nlris {
              description
                "Table of NLRI";
              list nlri {
                key "nlri-bytes";
                description
                  "NLRI information (hexdump)";
                leaf nlri-bytes {
                  type xr:Cisco-ios-xr-string;
                  description
                    "Enter NLRI hex string";
                }
                uses FS-MGR-NLRI;
              }
            }
            container flows {
              description
                "Table of Flow";
              list flow {
                key "flow-notation";
                description
                  "Flow notation string";
                leaf flow-notation {
                  type string;
                  description
                    "Enter the Flow notation string";
                }
                uses FS-MGR-NLRI;
              }
            }
            leaf af-name {
              type xr:Cisco-ios-xr-string;
              description
                "Set string";
            }
          }
        }
        leaf vrf-name {
          type xr:Cisco-ios-xr-string {
            length "1..32";
          }
          description
            "VRF Name";
        }
      }
    }
  }
}
