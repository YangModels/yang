module Cisco-IOS-XR-l2-snoop-oper {
  namespace "http://cisco.com/ns/yang/Cisco-IOS-XR-l2-snoop-oper";
  prefix l2-snoop-oper;

  import ietf-inet-types {
    prefix inet;
  }
  import Cisco-IOS-XR-types {
    prefix xr;
  }
  import cisco-semver {
    prefix semver;
  }
  include Cisco-IOS-XR-l2-snoop-oper-sub1 {
    revision-date 2023-06-13;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR l2-snoop package operational data.
     
     This module contains definitions
     for the following management objects:
       mld-snooping: MLD snooping operational data
       igmp-snooping: IGMP snooping operational data
     
     Copyright (c) 2013-2023 by Cisco Systems, Inc.
     All rights reserved.";

  revision 2023-06-13 {
    description
      "Addition of 'container mh-entries'.
       2023-04-13
         backward compatible addition, in 'leaf enable_stats' was added
       2022-06-28
         backward compatible edit, in 'interface-name'.
       2022-03-30
         backward compatible addition, in 'leaf l2fib-replay-time' was added";
    semver:module-version "1.1.0";
  }
  revision 2021-06-21 {
    description
      "Added the Snooping oper yang model";
    semver:module-version "1.0.0";
  }
  revision 2019-04-05 {
    description
      "Establish semantic version baseline.";
  }
  revision 2015-11-09 {
    description
      "IOS XR 6.0 revision.";
  }

  container mld-snooping {
    config false;
    description
      "MLD snooping operational data";
    container profile-references {
      description
        "MLD Snooping Profile Reference Table";
      list profile-reference {
        key "profile-name";
        description
          "MLD Snooping Reference Profile";
        leaf profile-name {
          type xr:Cisco-ios-xr-string {
            length "1..32";
          }
          description
            "Profile name";
        }
        uses IGMPSN-EDM-PROFILE-REFERENCE-BAG;
      }
    }
    container mh-entries {
      description
        "MLD Snooping EVPN MH-DB";
      list mh-entry {
        key "xid";
        description
          "MLD Snooping EVPN MH XID Entry";
        leaf xid {
          type xr:Hex-integer;
          description
            "Bridgeport XID";
        }
        uses IGMPSN-EDM-EVPN-MH-ENTRY-BAG;
      }
    }
    container groups {
      description
        "MLD Snooping Group Table";
      list group {
        key "bd-name group-address";
        description
          "MLD Snooping Group";
        leaf bd-name {
          type xr:Cisco-ios-xr-string {
            length "1..64";
          }
          description
            "Bridge domain name";
        }
        leaf group-address {
          type inet:ipv6-address-no-zone;
          description
            "IP address of group";
        }
        uses IGMPSN-EDM-GROUP-BAG;
      }
    }
    container redundancy {
      description
        "MLD redundancy";
      container iccp {
        description
          "ICCP information";
        container ports {
          description
            "MLDSN ICCP ports";
          list port {
            key "port-name";
            description
              "MLDSN ICCP port";
            leaf port-name {
              type xr:Interface-name;
              description
                "Port name";
            }
            uses IGMPSN-ICCP-APP-RG-PORT-DATA-BAG;
          }
        }
        container group-statistics {
          description
            "ICCP group statistics";
          list group-statistic {
            key "group-id";
            description
              "ICCP group statistics";
            leaf group-id {
              type uint32 {
                range "1..4294967295";
              }
              description
                "ICCP group ID";
            }
            uses IGMPSN-ICCP-APP-RG-STATS-BAG;
          }
        }
        container groups {
          description
            "ICCP Groups";
          list group {
            key "group-id";
            description
              "ICCP group";
            leaf group-id {
              type uint32 {
                range "1..4294967295";
              }
              description
                "ICCP group ID";
            }
            uses IGMPSN-ICCP-APP-RG-DATA-BAG;
          }
        }
        container general {
          description
            "MLDSN ICCP general information";
          uses ICCP-APP-ICCP-STATE-BAG;
        }
        container group-peers {
          description
            "ICCP group peers";
          list group-peer {
            key "group-id";
            description
              "ICCP group peer";
            container peers {
              description
                "ICCP group peers";
              list peer {
                key "peer-address";
                description
                  "ICCP group peer";
                leaf peer-address {
                  type inet:ipv6-address-no-zone;
                  description
                    "Peer IP address";
                }
                uses IGMPSN-ICCP-APP-RG-PEER-DATA-BAG;
              }
            }
            leaf group-id {
              type uint32 {
                range "1..4294967295";
              }
              description
                "ICCP group ID";
            }
          }
        }
        container port-statistics {
          description
            "MLDSN ICCP port statistics";
          list port-statistic {
            key "port-name";
            description
              "MLDSN ICCP port statistics";
            leaf port-name {
              type xr:Interface-name;
              description
                "Port name";
            }
            uses IGMPSN-ICCP-APP-RG-PORT-STATS-BAG;
          }
        }
        container group-ports {
          description
            "ICCP group ports";
          list group-port {
            key "group-id";
            description
              "ICCP group port";
            container port-statistics {
              description
                "ICCP group port statistics";
              list port-statistic {
                key "port-name";
                description
                  "ICCP group port statistics";
                leaf port-name {
                  type xr:Interface-name;
                  description
                    "Port name";
                }
                uses IGMPSN-ICCP-APP-RG-PORT-STATS-BAG;
              }
            }
            container ports {
              description
                "ICCP group ports";
              list port {
                key "port-name";
                description
                  "ICCP group port";
                leaf port-name {
                  type xr:Interface-name;
                  description
                    "Port name";
                }
                uses IGMPSN-ICCP-APP-RG-PORT-DATA-BAG;
              }
            }
            leaf group-id {
              type uint32 {
                range "1..4294967295";
              }
              description
                "ICCP group ID";
            }
          }
        }
        container statistics {
          description
            "MLDSN ICCP statistics";
          uses IGMPSN-ICCP-APP-STATS-BAG;
        }
      }
    }
    container profiles {
      description
        "MLD Snooping Profile Table";
      list profile {
        key "profile-name";
        description
          "MLD Snooping Profile";
        leaf profile-name {
          type xr:Cisco-ios-xr-string {
            length "1..32";
          }
          description
            "Profile name";
        }
        uses IGMPSN-EDM-PROFILE-BAG;
      }
    }
    container bridge-domains {
      description
        "MLD Snooping Bridge Domain Table";
      list bridge-domain {
        key "bd-name";
        description
          "MLD Snooping BridgeDomain";
        leaf bd-name {
          type xr:Cisco-ios-xr-string {
            length "1..64";
          }
          description
            "Bridge domain name";
        }
        uses IGMPSN-EDM-BD-BAG;
      }
    }
    container route-entries {
      description
        "MLD Snooping EVPN Route-DB";
      list route-entry {
        key "bdid";
        description
          "IGMP Snooping EVPN Route Entry";
        leaf bdid {
          type xr:Hex-integer;
          description
            "Bridge-domain ID";
        }
        uses IGMPSN-EDM-EVPN-ROUTE-ENTRY-BAG;
      }
    }
    container profile-summary {
      description
        "MLD Snooping Profile Summary";
      uses IGMPSN-EDM-PROFILE-SUMMARY-BAG;
    }
    container ports {
      description
        "MLD Snooping Port Table";
      list port {
        key "port-name";
        description
          "MLD Snooping Port";
        leaf port-name {
          type xr:Interface-name;
          description
            "Port name";
        }
        uses IGMPSN-EDM-INTF-BAG;
      }
    }
    container summary {
      description
        "MLD Snooping Summary";
      uses IGMPSN-EDM-SUMMARY-BAG;
    }
    container port-groups {
      description
        "MLD Snooping Group Table";
      list port-group {
        key "bd-name port-name group-address";
        description
          "MLD Snooping Port Group";
        leaf bd-name {
          type xr:Cisco-ios-xr-string {
            length "1..64";
          }
          description
            "Bridge domain name";
        }
        leaf port-name {
          type xr:Interface-name;
          description
            "Port name";
        }
        leaf group-address {
          type inet:ipv6-address-no-zone;
          description
            "IP address of group";
        }
        uses IGMPSN-EDM-PORT-GROUP-BAG;
      }
    }
  }
  container igmp-snooping {
    config false;
    description
      "IGMP snooping operational data";
    container ports {
      description
        "IGMP Snooping Port Table";
      list port {
        key "port-name";
        description
          "IGMP Snooping Port";
        leaf port-name {
          type xr:Interface-name;
          description
            "Port name";
        }
        uses IGMPSN-EDM-INTF-BAG;
      }
    }
    container mh-entries {
      description
        "IGMP Snooping EVPN MH-DB";
      list mh-entry {
        key "xid";
        description
          "IGMP Snooping EVPN MH XID Entry";
        leaf xid {
          type xr:Hex-integer;
          description
            "Bridgeport XID";
        }
        uses IGMPSN-EDM-EVPN-MH-ENTRY-BAG;
      }
    }
    container port-groups {
      description
        "IGMP Snooping Group Table";
      list port-group {
        key "bd-name port-name group-address";
        description
          "IGMP Snooping Port Group";
        leaf bd-name {
          type xr:Cisco-ios-xr-string {
            length "1..64";
          }
          description
            "Bridge domain name";
        }
        leaf port-name {
          type xr:Interface-name;
          description
            "Port name";
        }
        leaf group-address {
          type inet:ipv4-address-no-zone;
          description
            "IP address of group";
        }
        uses IGMPSN-EDM-PORT-GROUP-BAG;
      }
    }
    container groups {
      description
        "IGMP Snooping Group Table";
      list group {
        key "bd-name group-address";
        description
          "IGMP Snooping Group";
        leaf bd-name {
          type xr:Cisco-ios-xr-string {
            length "1..64";
          }
          description
            "Bridge domain name";
        }
        leaf group-address {
          type inet:ipv4-address-no-zone;
          description
            "IP address of group";
        }
        uses IGMPSN-EDM-GROUP-BAG;
      }
    }
    container route-entries {
      description
        "IGMP Snooping EVPN Route-DB";
      list route-entry {
        key "bdid xid source-address group-address ver grt ert";
        description
          "IGMP Snooping EVPN Route Entry";
        leaf bdid {
          type xr:Hex-integer;
          description
            "Bridge-domain ID";
        }
        leaf xid {
          type xr:Hex-integer;
          description
            "Bridgeport XID";
        }
        leaf source-address {
          type inet:ipv4-address-no-zone;
          description
            "IP address of source";
        }
        leaf group-address {
          type inet:ipv4-address-no-zone;
          description
            "IP address of group";
        }
        leaf ver {
          type uint32;
          description
            "IGMP Version";
        }
        leaf grt {
          type uint32;
          description
            "Group Record Type";
        }
        leaf ert {
          type uint32;
          description
            "EVPN Route Type";
        }
        uses IGMPSN-EDM-EVPN-ROUTE-ENTRY-BAG;
      }
    }
    container summary {
      description
        "IGMP Snooping Summary";
      uses IGMPSN-EDM-SUMMARY-BAG;
    }
    container redundancy {
      description
        "IGMP redundancy";
      container iccp {
        description
          "ICCP information";
        container group-statistics {
          description
            "ICCP group statistics";
          list group-statistic {
            key "group-id";
            description
              "ICCP group statistics";
            leaf group-id {
              type uint32 {
                range "1..4294967295";
              }
              description
                "ICCP group ID";
            }
            uses IGMPSN-ICCP-APP-RG-STATS-BAG;
          }
        }
        container ports {
          description
            "IGMPSN ICCP ports";
          list port {
            key "port-name";
            description
              "IGMPSN ICCP port";
            leaf port-name {
              type xr:Interface-name;
              description
                "Port name";
            }
            uses IGMPSN-ICCP-APP-RG-PORT-DATA-BAG;
          }
        }
        container general {
          description
            "IGMPSN ICCP general information";
          uses ICCP-APP-ICCP-STATE-BAG;
        }
        container group-ports {
          description
            "ICCP group ports";
          list group-port {
            key "group-id";
            description
              "ICCP group port";
            container port-statistics {
              description
                "ICCP group port statistics";
              list port-statistic {
                key "port-name";
                description
                  "ICCP group port statistics";
                leaf port-name {
                  type xr:Interface-name;
                  description
                    "Port name";
                }
                uses IGMPSN-ICCP-APP-RG-PORT-STATS-BAG;
              }
            }
            container ports {
              description
                "ICCP group ports";
              list port {
                key "port-name";
                description
                  "ICCP group port";
                leaf port-name {
                  type xr:Interface-name;
                  description
                    "Port name";
                }
                uses IGMPSN-ICCP-APP-RG-PORT-DATA-BAG;
              }
            }
            leaf group-id {
              type uint32 {
                range "1..4294967295";
              }
              description
                "ICCP group ID";
            }
          }
        }
        container group-peers {
          description
            "ICCP group peers";
          list group-peer {
            key "group-id";
            description
              "ICCP group peer";
            container peers {
              description
                "ICCP group peers";
              list peer {
                key "peer-address";
                description
                  "ICCP group peer";
                leaf peer-address {
                  type inet:ipv4-address-no-zone;
                  description
                    "Peer IP address";
                }
                uses IGMPSN-ICCP-APP-RG-PEER-DATA-BAG;
              }
            }
            leaf group-id {
              type uint32 {
                range "1..4294967295";
              }
              description
                "ICCP group ID";
            }
          }
        }
        container statistics {
          description
            "IGMPSN ICCP statistics";
          uses IGMPSN-ICCP-APP-STATS-BAG;
        }
        container port-statistics {
          description
            "IGMPSN ICCP port statistics";
          list port-statistic {
            key "port-name";
            description
              "IGMPSN ICCP port statistics";
            leaf port-name {
              type xr:Interface-name;
              description
                "Port name";
            }
            uses IGMPSN-ICCP-APP-RG-PORT-STATS-BAG;
          }
        }
        container groups {
          description
            "ICCP Groups";
          list group {
            key "group-id";
            description
              "ICCP group";
            leaf group-id {
              type uint32 {
                range "1..4294967295";
              }
              description
                "ICCP group ID";
            }
            uses IGMPSN-ICCP-APP-RG-DATA-BAG;
          }
        }
      }
    }
    container bridge-domains {
      description
        "IGMP Snooping Bridge Domain Table";
      list bridge-domain {
        key "bd-name";
        description
          "IGMP Snooping BridgeDomain";
        leaf bd-name {
          type xr:Cisco-ios-xr-string {
            length "1..64";
          }
          description
            "Bridge domain name";
        }
        uses IGMPSN-EDM-BD-BAG;
      }
    }
    container profile-references {
      description
        "IGMP Snooping Profile Reference Table";
      list profile-reference {
        key "profile-name";
        description
          "IGMP Snooping Reference Profile";
        leaf profile-name {
          type xr:Cisco-ios-xr-string {
            length "1..32";
          }
          description
            "Profile name";
        }
        uses IGMPSN-EDM-PROFILE-REFERENCE-BAG;
      }
    }
    container profiles {
      description
        "IGMP Snooping Profile Table";
      list profile {
        key "profile-name";
        description
          "IGMP Snooping Profile";
        leaf profile-name {
          type xr:Cisco-ios-xr-string {
            length "1..32";
          }
          description
            "Profile name";
        }
        uses IGMPSN-EDM-PROFILE-BAG;
      }
    }
    container profile-summary {
      description
        "IGMP Snooping Profile Summary";
      uses IGMPSN-EDM-PROFILE-SUMMARY-BAG;
    }
  }
}
