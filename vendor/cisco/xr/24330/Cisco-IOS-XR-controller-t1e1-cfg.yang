module Cisco-IOS-XR-controller-t1e1-cfg {
  namespace "http://cisco.com/ns/yang/Cisco-IOS-XR-controller-t1e1-cfg";
  prefix controller-t1e1-cfg;

  import cisco-semver {
    prefix semver;
  }
  import Cisco-IOS-XR-ifmgr-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR controller-t1e1 package configuration.
     
     This YANG module augments the
       Cisco-IOS-XR-ifmgr-cfg
     module with configuration data.
     
     Copyright (c) 2013-2022 by Cisco Systems, Inc.
     All rights reserved.";

  revision 2022-01-12 {
    description
      "Added Config Schema for T1E1";
    semver:module-version "1.0.0";
  }
  revision 2019-04-05 {
    description
      "Establish semantic version baseline.";
  }
  revision 2015-11-09 {
    description
      "IOS XR 6.0 revision.";
  }

  typedef T1e1-prbspattern {
    type enumeration {
      enum "pn15" {
        value 1;
        description
          "prbs pattern pn15";
      }
    }
    description
      "T1e1 prbspattern";
  }

  typedef T1e1-prbsdirection {
    type enumeration {
      enum "line" {
        value 1;
        description
          "prbs direction line";
      }
      enum "system" {
        value 2;
        description
          "prbs direction system";
      }
    }
    description
      "T1e1 prbsdirection";
  }

  typedef T1e1-linecode {
    type enumeration {
      enum "ami" {
        value 1;
        description
          "AMI encoding(E1 default)";
      }
      enum "hdb3" {
        value 2;
        description
          "HDB3 encoding";
      }
    }
    description
      "T1e1 linecode";
  }

  typedef T1e1n-vloopbackmode {
    type enumeration {
      enum "local" {
        value 1;
        description
          "local looback mode";
      }
      enum "network-line" {
        value 2;
        description
          "network line loopback mode";
      }
    }
    description
      "T1e1n vloopbackmode";
  }

  typedef T1e1-clock-source {
    type enumeration {
      enum "source-internal" {
        value 1;
        description
          "source internal clock";
      }
      enum "source-line" {
        value 2;
        description
          "source line clock";
      }
      enum "source-recovered-acr" {
        value 3;
        description
          "source adaptive recovered clock";
      }
      enum "source-recovered-dcr" {
        value 4;
        description
          "source differential recovered clock";
      }
    }
    description
      "T1e1 clock source";
  }

  typedef Prbsmode {
    type enumeration {
      enum "sink" {
        value 1;
        description
          "sink prbs mode";
      }
      enum "source" {
        value 2;
        description
          "source prbs mode";
      }
      enum "source-sink" {
        value 3;
        description
          "source-sink prbs mode";
      }
    }
    description
      "Prbsmode";
  }

  augment "/a1:interface-configurations/a1:interface-configuration" {
    description
      "This augment extends the configuration data of
       'Cisco-IOS-XR-ifmgr-cfg'";
    container t1e1nv {
      description
        "t1/e1 controller configuration";
      container vlan {
        presence "Indicates a vlan node is configured.";
        description
          "Configure vlan id";
        leaf vlanid {
          type uint32 {
            range "1..4095";
          }
          mandatory true;
          description
            "select vlan id";
        }
        leaf ecid {
          type uint32 {
            range "1..1000";
          }
          description
            "select ecid";
        }
      }
      container prbs {
        presence "Indicates a prbs node is configured.";
        description
          "Configure pseudorandom binary sequence";
        leaf prbsmode {
          type Prbsmode;
          mandatory true;
          description
            "Sink,source,source-sink";
        }
        leaf patterntype {
          type T1e1-prbspattern;
          mandatory true;
          description
            "PN15";
        }
        leaf directiontype {
          type T1e1-prbsdirection;
          description
            "line,system";
        }
      }
      leaf clock {
        type T1e1-clock-source;
        description
          "Configure port TX clock source";
      }
      leaf linecoding {
        type T1e1-linecode;
        description
          "Configure linecoding";
      }
      leaf loopback {
        type T1e1n-vloopbackmode;
        description
          "Configure t1e1 loopback mode";
      }
      leaf cemclass {
        type string {
          length "1..32";
        }
        description
          "Attach CEM class(Circuit emulation) profile";
      }
    }
  }
}
