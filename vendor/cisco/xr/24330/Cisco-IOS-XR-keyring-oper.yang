module Cisco-IOS-XR-keyring-oper {
  namespace "http://cisco.com/ns/yang/Cisco-IOS-XR-keyring-oper";
  prefix keyring-oper;

  import Cisco-IOS-XR-types {
    prefix xr;
  }
  import cisco-semver {
    prefix semver;
  }
  include Cisco-IOS-XR-keyring-oper-sub1 {
    revision-date 2024-01-10;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR keyring package operational data.
     
     This module contains definitions
     for the following management objects:
       keyrings: IKEv2 keyrings operational data
     
     Copyright (c) 2013-2024 by Cisco Systems, Inc.
     All rights reserved.";

  revision 2024-01-10 {
    description
      "FQDN identity Support
       2023-01-30
         PPK support";
    semver:module-version "1.1.0";
  }
  revision 2019-04-05 {
    description
      "Establish semantic version baseline.";
    semver:module-version "1.0.1";
  }
  revision 2019-02-04 {
    description
      "Keyring Operational Yang Support";
  }
  revision 2015-11-09 {
    description
      "IOS XR 6.0 revision.";
  }

  container keyrings {
    config false;
    description
      "IKEv2 keyrings operational data";
    list keyring {
      key "name";
      description
        "IKEv2 keyring data";
      leaf name {
        type xr:Cisco-ios-xr-string {
          length "1..32";
        }
        description
          "Name of the IKEv2 keyring";
      }
      uses IKEV2-EDM-KEYRING;
    }
  }
}
