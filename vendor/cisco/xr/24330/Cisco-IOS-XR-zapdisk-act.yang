module Cisco-IOS-XR-zapdisk-act {
  namespace "http://cisco.com/ns/yang/Cisco-IOS-XR-zapdisk-act";
  prefix zapdisk-act;

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR action package configuration.
     
     Copyright (c) 2016-2020 by Cisco Systems, Inc.
     All rights reserved.";

  revision 2020-07-16 {
    description
      "IOS XR 7.1.2 revision.";
  }

  rpc zapdisk-show {
    description
      "Action to list zapdisk locations";
    output {
      leaf location {
        type string;
        mandatory true;
        description
          "Result of zapdisk show location";
      }
    }
  }
  rpc zapdisk-start {
    description
      "Action to start zapdisk operation";
    input {
      leaf location {
        type string;
        mandatory true;
        description
          "Location string to start zapdisk operation";
      }
    }
    output {
      leaf result {
        type string;
        mandatory true;
        description
          "Result of zapdisk operation";
      }
    }
  }
}
