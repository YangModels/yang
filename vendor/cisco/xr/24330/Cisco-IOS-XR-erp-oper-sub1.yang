submodule Cisco-IOS-XR-erp-oper-sub1 {
  belongs-to Cisco-IOS-XR-erp-oper {
    prefix Cisco-IOS-XR-erp-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR erp package operational data.
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  typedef Erp-ring-mode {
    type enumeration {
      enum "closed-ring" {
        description
          "Closed R-APS Channel Topology";
      }
      enum "open-ring" {
        description
          "Open R-APS Channel Topology";
      }
    }
    description
      "Ethernet Ring G.8032 R-APS Channel Topology Mode";
  }

  typedef Erp-revertive-mode {
    type enumeration {
      enum "non-revertive" {
        description
          "Non-revertive Mode";
      }
      enum "revertive" {
        description
          "Revertive Mode";
      }
    }
    description
      "Ethernet Ring G.8032 Revertive Mode";
  }

  typedef Erp-port-status {
    type enumeration {
      enum "unblocked" {
        description
          "Unblocked";
      }
      enum "blocked" {
        description
          "Blocked";
      }
    }
    description
      "Ethernet Ring G.8032 Port Status Information";
  }

  typedef Erp-fault-status {
    type enumeration {
      enum "no-fault" {
        description
          "No Fault Detected";
      }
      enum "faulty" {
        description
          "Fault Detected";
      }
    }
    description
      "Ethernet Ring G.8032 Port Fault Status";
  }

  typedef Erp-link {
    type enumeration {
      enum "non-rpl" {
        description
          "Non-RPL link";
      }
      enum "rpl" {
        description
          "RPL link";
      }
    }
    description
      "Ethernet Ring G.8032 Link Type";
  }

  typedef Erp-sm-state {
    type enumeration {
      enum "init" {
        description
          "Init State";
      }
      enum "idle" {
        description
          "Idle State";
      }
      enum "protection" {
        description
          "Protection State";
      }
      enum "manual-switch" {
        description
          "Manual Switch State";
      }
      enum "forced-switch" {
        description
          "Forced Switch State";
      }
      enum "pending" {
        description
          "Pending State";
      }
    }
    description
      "Ethernet Ring G.8032 State Machine State";
  }

  typedef Erp-bag-node {
    type enumeration {
      enum "normal" {
        description
          "Normal Node";
      }
      enum "rpl-owner" {
        description
          "RPL Owner";
      }
      enum "rpl-neighbor" {
        description
          "RPL Neighbor";
      }
      enum "rpl-next-neighbor" {
        description
          "RPL Next Neighbor";
      }
    }
    description
      "Ethernet Ring G.8032 Node Type";
  }

  grouping ERP-BRIEF-INFO {
    description
      "Ethernet Ring G.8032 Brief Information";
    leaf node-type {
      type Erp-bag-node;
      description
        "Node Type";
    }
    leaf ring-state {
      type Erp-sm-state;
      description
        "Ring State";
    }
    list ports {
      max-elements "2";
      description
        "Port Information";
      uses ERP-PORT-INFO;
    }
  }

  grouping ERP-SUMMARY-INFO {
    description
      "Ethernet Ring G.8032 Summary Information";
    leaf node {
      type string;
      description
        "Device Node ID";
    }
    leaf init-state {
      type uint16;
      description
        "Count of instances in Init state";
    }
    leaf idle-state {
      type uint16;
      description
        "Count of instances in Idle state";
    }
    leaf manual-switch-state {
      type uint16;
      description
        "Count of instances in Manual Switch state";
    }
    leaf forced-switch-state {
      type uint16;
      description
        "Count of instances in Forced Switch state";
    }
    leaf protection-state {
      type uint16;
      description
        "Count of instances in Protection state";
    }
    leaf pending-state {
      type uint16;
      description
        "Count of instances in Pending state";
    }
  }

  grouping ERP-INSTANCE-STATS-INFO {
    description
      "Ethernet Ring G.8032 Instance Statistics info";
    leaf init-time {
      type string;
      units "millisecond";
      description
        "Time the ring instance is last in Initialization
         state.  The time format is: Thu Jan 01 HH:MM:SS
         .000 ZZZ, where 000 is milliseconds and ZZZ is
         the timezone";
    }
    leaf idle-time {
      type string;
      units "millisecond";
      description
        "Time the ring instance is last in Idle state.
         The time format is: Thu Jan 01 HH:MM:SS.000 ZZZ,
         where 000 is milliseconds and ZZZ is the
         timezone";
    }
    leaf manual-switch-time {
      type string;
      units "millisecond";
      description
        "Time the ring instance is last in Manual Switch
         state.  The time format is: Thu Jan 01 HH:MM:SS
         .000 ZZZ, where 000 is milliseconds and ZZZ is
         the timezone";
    }
    leaf forced-switch-time {
      type string;
      units "millisecond";
      description
        "Time the ring instance is last in Forced Switch
         state.  The time format is: Thu Jan 01 HH:MM:SS
         .000 ZZZ, where 000 is milliseconds and ZZZ is
         the timezone";
    }
    leaf protection-time {
      type string;
      units "millisecond";
      description
        "Time the ring instance is last in Protection
         state.  The time format is: Thu Jan 01 HH:MM:SS
         .000 ZZZ, where 000 is milliseconds and ZZZ is
         the timezone";
    }
    leaf pending-time {
      type string;
      units "millisecond";
      description
        "Time the ring instance is last in Pending state.
         The time format is: Thu Jan 01 HH:MM:SS.000 ZZZ,
         where 000 is milliseconds and ZZZ is the
         timezone";
    }
  }

  grouping ERP-PORT-STATS-INFO {
    description
      "Ethernet Ring G.8032 Port Statistics info";
    leaf local-sf {
      type uint32;
      description
        "Count of local Signal Fail detected";
    }
    leaf nr-tx-count {
      type uint32;
      description
        "Count of R-APS(NR) transmitted";
    }
    leaf nr-rb-tx-count {
      type uint32;
      description
        "Count of R-APS(NR,RB) transmitted";
    }
    leaf sf-tx-count {
      type uint32;
      description
        "Count of R-APS(SF) transmitted";
    }
    leaf ms-tx-count {
      type uint32;
      description
        "Count of R-APS(MS) transmitted";
    }
    leaf fs-tx-count {
      type uint32;
      description
        "Count of R-APS(FS) transmitted";
    }
    leaf ev-tx-count {
      type uint32;
      description
        "Count of R-APS(EVENT) transmitted";
    }
    leaf nr-rx-count {
      type uint32;
      description
        "Count of R-APS(NR) received";
    }
    leaf nr-rb-rx-count {
      type uint32;
      description
        "Count of R-APS(NR,RB) received";
    }
    leaf sf-rx-count {
      type uint32;
      description
        "Count of R-APS(SF) received";
    }
    leaf ms-rx-count {
      type uint32;
      description
        "Count of R-APS(MS) received";
    }
    leaf fs-rx-count {
      type uint32;
      description
        "Count of R-APS(FS) received";
    }
    leaf ev-rx-count {
      type uint32;
      description
        "Count of R-APS(EVENT) received";
    }
    leaf last-nr-tx {
      type string;
      units "millisecond";
      description
        "Time the last R-APS(NR) was transmitted.  The
         time format is: Thu Jan 01 HH:MM:SS.000 ZZZ,
         where 000 is milliseconds and ZZZ is the
         timezone";
    }
    leaf last-nr-rb-tx {
      type string;
      units "millisecond";
      description
        "Time the last R-APS(NR,RB) was transmitted.  The
         time format is: Thu Jan 01 HH:MM:SS.000 ZZZ,
         where 000 is milliseconds and ZZZ is the
         timezone";
    }
    leaf last-sf-tx {
      type string;
      units "millisecond";
      description
        "Time the last R-APS(SF) was transmitted.  The
         time format is: Thu Jan 01 HH:MM:SS.000 ZZZ,
         where 000 is milliseconds and ZZZ is the
         timezone";
    }
    leaf last-ms-tx {
      type string;
      units "millisecond";
      description
        "Time the last R-APS(MS) was transmitted.  The
         time format is: Thu Jan 01 HH:MM:SS.000 ZZZ,
         where 000 is milliseconds and ZZZ is the
         timezone";
    }
    leaf last-fs-tx {
      type string;
      units "millisecond";
      description
        "Time the last R-APS(FS) was transmitted.  The
         time format is: Thu Jan 01 HH:MM:SS.000 ZZZ,
         where 000 is milliseconds and ZZZ is the
         timezone";
    }
    leaf last-ev-tx {
      type string;
      units "millisecond";
      description
        "Time the last R-APS(EVENT) was transmitted.  The
         time format is: Thu Jan 01 HH:MM:SS.000 ZZZ,
         where 000 is milliseconds and ZZZ is the
         timezone";
    }
    leaf last-nr-rx {
      type string;
      units "millisecond";
      description
        "Time the last R-APS(NR) was received.  The time
         format is: Thu Jan 01 HH:MM:SS.000 ZZZ, where
         000 is milliseconds and ZZZ is the timezone";
    }
    leaf last-nr-rb-rx {
      type string;
      units "millisecond";
      description
        "Time the last R-APS(NR,RB) was received.  The
         time format is: Thu Jan 01 HH:MM:SS.000 ZZZ,
         where 000 is milliseconds and ZZZ is the
         timezone";
    }
    leaf last-sf-rx {
      type string;
      units "millisecond";
      description
        "Time the last R-APS(SF) was received.  The time
         format is: Thu Jan 01 HH:MM:SS.000 ZZZ, where
         000 is milliseconds and ZZZ is the timezone";
    }
    leaf last-ms-rx {
      type string;
      units "millisecond";
      description
        "Time the last R-APS(MS) was received.  The time
         format is: Thu Jan 01 HH:MM:SS.000 ZZZ, where
         000 is milliseconds and ZZZ is the timezone";
    }
    leaf last-fs-rx {
      type string;
      units "millisecond";
      description
        "Time the last R-APS(FS) was received.  The time
         format is: Thu Jan 01 HH:MM:SS.000 ZZZ, where
         000 is milliseconds and ZZZ is the timezone";
    }
    leaf last-ev-rx {
      type string;
      units "millisecond";
      description
        "Time the last R-APS(EVENT) was received.  The
         time format is: Thu Jan 01 HH:MM:SS.000 ZZZ,
         where 000 is milliseconds and ZZZ is the
         timezone";
    }
  }

  grouping ERP-STATS-INFO {
    description
      "Ethernet Ring G.8032 Statistics Information";
    container instance-statistics {
      description
        "Ring instance statistics information";
      uses ERP-INSTANCE-STATS-INFO;
    }
    list port-statistic {
      max-elements "2";
      description
        "Port statistics information";
      uses ERP-PORT-STATS-INFO;
    }
  }

  grouping ERP-PROFILE-INFO {
    description
      "Ethernet Ring G.8032 Profile Information";
    leaf wtr-timer {
      type uint16;
      units "minute";
      description
        "WTR Timer Value in minutes";
    }
    leaf hold-off-timer {
      type uint16;
      units "millisecond";
      description
        "Hold-off Timer Value in milliseconds";
    }
    leaf guard-timer {
      type uint16;
      units "second";
      description
        "Guard Timer Value in seconds";
    }
    leaf revertive-mode {
      type Erp-revertive-mode;
      description
        "Revertive/Non-revertive Mode";
    }
  }

  grouping ERP-PORT-INFO {
    description
      "Ethernet Ring G.8032 Port Information";
    leaf interface-name {
      type string;
      description
        "Physical Interface Name";
    }
    leaf monitor-interface-name {
      type string;
      description
        "Monitoring Interface Name";
    }
    leaf aps-channel {
      type string;
      description
        "APS Channel";
    }
    leaf link-type {
      type Erp-link;
      description
        "RPL or Non-RPL";
    }
    leaf fault-detected {
      type Erp-fault-status;
      description
        "Fault detected on interface";
    }
    leaf present {
      type boolean;
      description
        "Interface is present";
    }
    leaf ring-port-status {
      type Erp-port-status;
      description
        "Status of ring port";
    }
    leaf local-fs {
      type boolean;
      description
        "Local forced switch of port";
    }
    leaf local-ms {
      type boolean;
      description
        "Local manual switch of port";
    }
    leaf node {
      type string;
      description
        "Remote R-APS Node ID";
    }
    leaf blocked-port-reference {
      type uint8;
      description
        "Blocked Port Reference";
    }
    leaf interface-handle {
      type uint64;
      description
        "Physical Interface Handle";
    }
    leaf monitor-interface-handle {
      type uint64;
      description
        "Monitoring Interface Handle";
    }
    leaf aps-interface-handle {
      type uint64;
      description
        "APS Interface Handle";
    }
  }

  grouping ERP-STATUS-INFO {
    description
      "Ethernet Ring G8032 Status Information";
    leaf node-type {
      type Erp-bag-node;
      description
        "Node Type";
    }
    leaf ring-state {
      type Erp-sm-state;
      description
        "Ring State";
    }
    leaf aps-level {
      type uint8;
      description
        "APS Level";
    }
    leaf profile-name {
      type string;
      description
        "Profile Name";
    }
    leaf wtr-timer {
      type uint16;
      units "minute";
      description
        "WTR Timer Value in minutes";
    }
    leaf hold-off-timer {
      type uint16;
      units "millisecond";
      description
        "Hold-off Timer Value in milliseconds";
    }
    leaf guard-timer {
      type uint16;
      units "second";
      description
        "Guard Timer Value in seconds";
    }
    leaf revertive-mode {
      type Erp-revertive-mode;
      description
        "Revertive or Non-revertive Mode";
    }
    leaf aps-channel-topology {
      type Erp-ring-mode;
      description
        "Open or Closed R-APS Topology";
    }
    list ports {
      max-elements "2";
      description
        "Port Information";
      uses ERP-PORT-INFO;
    }
  }
}
