module Cisco-IOS-XR-um-dyn-tmpl-service-policy-cfg {
  namespace "http://cisco.com/ns/yang/Cisco-IOS-XR-um-dyn-tmpl-service-policy-cfg";
  prefix um-dyn-tmpl-service-policy-cfg;

  import Cisco-IOS-XR-types {
    prefix xr;
  }
  import Cisco-IOS-XR-um-dynamic-template-cfg {
    prefix a1;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR dyn-tmpl-service-policy package configuration.
     
     This YANG module augments the
     modules with configuration data.
     
     Copyright (c) 2022 by Cisco Systems, Inc.
     All rights reserved.";

  revision 2022-07-11 {
    description
      "Added missing description statement to nodes";
    semver:module-version "1.1.0";
  }
  revision 2021-05-19 {
    description
      "Initial release";
    semver:module-version "1.0.0";
  }

  feature qos_ui_supp_qfab_cfg {
    description
      "qos ui supp qfab cfg";
  }

  feature qos_ui_supp_spi {
    description
      "qos ui supp spi";
  }

  grouping TEMPLATE-BODY {
    description
      "Grouping for template";
    container service-policy {
      description
        "Associate a service policy to the dynamic template";
      container input {
        presence "Indicates input node is configured.";
        description
          "Configure an ingress service policy";
        leaf service-policy-name {
          type xr:Cisco-ios-xr-string {
            length "1..800" {
              description
                "Name of the service policy";
            }
            pattern "[a-zA-Z0-9][a-zA-Z0-9._@$%+#:=<>-]{0,62}";
          }
          mandatory true;
          description
            "Configure an ingress service policy";
        }
        leaf merge {
          type uint32 {
            range "0..255" {
              description
                "Sequence number of the policy";
            }
          }
          description
            "Enable the policy to be merged";
        }
        container acct-stats {
          when "boolean(../../../../../a1:service/a1:template)";
          presence "Indicates a acct-stats node is configured.";
          description
            "Enable service accounting";
        }
        leaf shared-policy-instance {
          if-feature "qos_ui_supp_spi";
          type xr:Cisco-ios-xr-string {
            length "1..32" {
              description
                "Name of the shared-policy-instance";
            }
            pattern "[a-zA-Z0-9][a-zA-Z0-9._@$%+#:=<>-]{0,62}";
          }
          description
            "configure a shared-policy-instance";
        }
      }
      container output {
        presence "Indicates output node is configured.";
        description
          "Configure an egress service policy";
        leaf service-policy-name {
          type xr:Cisco-ios-xr-string {
            length "1..800" {
              description
                "Name of the service policy";
            }
            pattern "[a-zA-Z0-9][a-zA-Z0-9._@$%+#:=<>-]{0,62}";
          }
          mandatory true;
          description
            "Configure an egress service policy";
        }
        leaf merge {
          type uint32 {
            range "0..255" {
              description
                "Sequence number of the policy";
            }
          }
          description
            "Enable the policy to be merged";
        }
        container acct-stats {
          when "boolean(../../../../../a1:service/a1:template)";
          presence "Indicates a acct-stats node is configured.";
          description
            "Enable service accounting";
        }
        leaf shared-policy-instance {
          if-feature "qos_ui_supp_spi";
          type xr:Cisco-ios-xr-string {
            length "1..32" {
              description
                "Name of the shared-policy-instance";
            }
            pattern "[a-zA-Z0-9][a-zA-Z0-9._@$%+#:=<>-]{0,62}";
          }
          description
            "configure a shared-policy-instance";
        }
      }
    }
    container output {
      when "boolean(../../../a1:ppp/a1:template)";
      description
        "QoS applied on the egress direction";
      leaf minimum-bandwidth {
        type uint32 {
          range "1..4294967295" {
            description
              "Minimum bandwidth value for subscriber (in kbps)";
          }
        }
        description
          "Minimum bandwidth guaranteed for a subscriber";
      }
    }
    container account {
      when "boolean(../../../a1:ppp/a1:template)";
      description
        "L2 overhead accounting";
      leaf aal5 {
        type enumeration {
          enum "snap-pppoa" {
            value 1;
            description
              "snap-pppoa encap used between the DSLAM and CPE";
          }
          enum "mux-pppoa" {
            value 2;
            description
              "mux-pppoa encap used between the DSLAM and CPE";
          }
          enum "snap-1483routed" {
            value 3;
            description
              "snap-1483routed encap used between the DSLAM and CPE";
          }
          enum "mux-1483routed" {
            value 4;
            description
              "mux-1483routed encap used between the DSLAM and CPE";
          }
          enum "snap-rbe" {
            value 5;
            description
              "snap-rbe encap used between the DSLAM and CPE";
          }
          enum "snap-dot1q-rbe" {
            value 6;
            description
              "snap-dot1q-rbe encap used between the DSLAM and CPE";
          }
          enum "mux-rbe" {
            value 7;
            description
              "mux-rbe encap used between the DSLAM and CPE";
          }
          enum "mux-dot1q-rbe" {
            value 8;
            description
              "mux-dot1q-rbe encap used between the DSLAM and CPE";
          }
        }
        must "not(../user-defined)";
        description
          "ATM adaption layer AAL5";
      }
      leaf user-defined {
        type int32 {
          range "-63..63" {
            description
              "Sequence number of the policy";
          }
        }
        must "not(../aal5)";
        description
          "Configure a numeric l2 overhead offset";
      }
      container atm {
        must "../user-defined";
        presence "Indicates a atm node is configured.";
        description
          "Add ATM cell tax to the L2 overhead";
      }
    }
  }

  augment "/a1:dynamic-template/a1:type/a1:ppp/a1:template" {
    description
      "This augment extends dynamic-template ppp nodes
       configuration";
    uses TEMPLATE-BODY;
  }
  augment "/a1:dynamic-template/a1:type/a1:ipsubscriber/a1:template" {
    description
      "This augment extends dynamic-template ipsubscriber nodes
       configuration";
    uses TEMPLATE-BODY;
  }
  augment "/a1:dynamic-template/a1:type/a1:service/a1:template" {
    description
      "This augment extends dynamic-template service nodes
       configuration";
    uses TEMPLATE-BODY;
  }
}
