module Cisco-IOS-XR-linux-security-showenc-oper {
  namespace "http://cisco.com/ns/yang/Cisco-IOS-XR-linux-security-showenc-oper";
  prefix linux-security-showenc-oper;

  import Cisco-IOS-XR-types {
    prefix xr;
  }
  import cisco-semver {
    prefix semver;
  }
  include Cisco-IOS-XR-linux-security-showenc-oper-sub1 {
    revision-date 2021-07-01;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR linux-security-showenc package operational data.
     
     This module contains definitions
     for the following management objects:
       disk-encryption: ssd encryption status
     
     Copyright (c) 2013-2021 by Cisco Systems, Inc.
     All rights reserved.";

  revision 2021-07-01 {
    description
      "Adding show disk-encryption status yang model";
    semver:module-version "1.0.0";
  }
  revision 2019-04-05 {
    description
      "Establish semantic version baseline.";
  }
  revision 2015-11-09 {
    description
      "IOS XR 6.0 revision.";
  }

  container disk-encryption {
    config false;
    description
      "ssd encryption status";
    list node {
      key "node-name";
      description
        "Node ID";
      leaf node-name {
        type xr:Node-id;
        description
          "Node name";
      }
      uses SHOW-DISK-ENC-STATUS-DATA;
    }
  }
}
