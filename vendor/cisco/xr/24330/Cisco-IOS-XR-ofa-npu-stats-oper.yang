module Cisco-IOS-XR-ofa-npu-stats-oper {
  namespace "http://cisco.com/ns/yang/Cisco-IOS-XR-ofa-npu-stats-oper";
  prefix ofa-npu-stats-oper;

  import cisco-semver {
    prefix semver;
  }
  import Cisco-IOS-XR-platforms-ofa-oper {
    prefix a1;
  }
  include Cisco-IOS-XR-ofa-npu-stats-oper-sub1 {
    revision-date 2024-04-09;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ofa-npu-stats package operational data.
     
     This YANG module augments the
       Cisco-IOS-XR-platforms-ofa-oper
     module with state data.
     
     Copyright (c) 2013-2024 by Cisco Systems, Inc.
     All rights reserved.";

  revision 2024-04-09 {
    description
      "Updated right Parent for Stats and AsicStatistics
       2024-04-06
         Removed counter summary cmd changes. Use debug-utils get_counter
       2023-09-19
         Added cached stats timestamp (cached_ts)
       2023-07-02
         Added counters-drop/summary cmd changes";
    semver:module-version "4.0.0";
  }
  revision 2021-02-05 {
    description
      "Added src-interface show cmd changes";
    semver:module-version "3.0.0";
  }
  revision 2020-10-09 {
    description
      "Added task-id";
    semver:module-version "2.0.0";
  }
  revision 2020-06-25 {
    description
      "Updated task-name";
    semver:module-version "1.2.0";
  }
  revision 2019-12-14 {
    description
      "Updated date for npu stats model";
    semver:module-version "1.1.0";
  }
  revision 2019-04-05 {
    description
      "Establish semantic version baseline.";
    semver:module-version "1.0.0";
  }
  revision 2015-11-09 {
    description
      "IOS XR 6.0 revision.";
  }

  typedef Max-trap-s {
    type uint32 {
      range "0..4294967295";
    }
    description
      "Max trap s";
  }

  typedef Max-lc-intf-hand-les {
    type uint32 {
      range "0..4294967295";
    }
    description
      "Max lc intf hand les";
  }

  augment "/a1:ofa/a1:stats/a1:nodes/a1:node" {
    description
      "This augment extends the operational data of
       'Cisco-IOS-XR-platforms-ofa-oper'";
    container asic-statistics {
      description
        "ASIC statistics table";
      container asic-statistics-detail-for-npu-ids {
        description
          "Detailed ASIC statistics";
        list asic-statistics-detail-for-npu-id {
          key "npu-id";
          description
            "Detailed ASIC statistics for a particular NPU";
          leaf npu-id {
            type uint32;
            description
              "NPU number";
          }
          uses FIA-EDM-STATS-INFO;
        }
      }
      container asic-statistics-drop-for-npu-ids {
        description
          "Drop ASIC statistics";
        list asic-statistics-drop-for-npu-id {
          key "npu-id";
          description
            "Drop ASIC statistics for a particular NPU";
          leaf npu-id {
            type uint32;
            description
              "NPU number";
          }
          uses NPU-EDM-STATS-INFO-SUMMARY;
        }
      }
      container asic-statistics-for-npu-ids {
        description
          "ASIC statistics";
        list asic-statistics-for-npu-id {
          key "npu-id";
          description
            "ASIC statistics for a particular NPU";
          leaf npu-id {
            type uint32;
            description
              "NPU number";
          }
          uses FIA-EDM-STATS-BRIEF-INFO;
        }
      }
    }
  }
  augment "/a1:ofa/a1:stats/a1:nodes/a1:node" {
    description
      "This augment extends the operational data of
       'Cisco-IOS-XR-platforms-ofa-oper'";
    container npu-numbers {
      description
        "Ingress Stats";
      list npu-number {
        key "npu-id";
        description
          "Stats for a particular npu";
        container display {
          description
            "show npu specific voq or trap stats";
          container dest-interface-handles {
            description
              "Voq stats grouped by interface handle";
            list dest-interface-handle {
              key "interface-handle";
              description
                "Voq stats for a particular interface handle";
              container src-interface-handles {
                description
                  "Voq stats grouped by src interface handle";
                list src-interface-handle {
                  key "interface-handle";
                  description
                    "Voq stats for a particular src interface
                     handle";
                  leaf interface-handle {
                    type Max-lc-intf-hand-les;
                    description
                      "Src Interface Handle";
                  }
                  uses DPA-VOQ-INTF-PORT;
                }
              }
              leaf interface-handle {
                type Max-lc-intf-hand-les;
                description
                  "Interface Handle";
              }
            }
          }
          container trap-ids {
            description
              "Trap stats for a particular npu";
            list trap-id {
              key "trap-id";
              description
                "Filter by specific trap id";
              leaf trap-id {
                type Max-trap-s;
                description
                  "Trap ID";
              }
              uses DPA-TRAP-STATS;
            }
          }
          container fair-voq-base-numbers {
            description
              "Voq stats grouped by voq base numbers";
            list fair-voq-base-number {
              key "base-number";
              description
                "Voq Base Number for a particular voq";
              container src-slice-numbers {
                description
                  "show npu specific src slice stats";
                list src-slice-number {
                  key "src-slice-id";
                  description
                    "Stats for a particular voq on given src
                     slice";
                  leaf src-slice-id {
                    type uint32;
                    description
                      "Src Slice number";
                  }
                  uses DPA-VOQ-INTF-PORT;
                }
              }
              leaf base-number {
                type Max-lc-intf-hand-les;
                description
                  "Interface handle";
              }
            }
          }
          container interface-handles {
            description
              "Voq stats grouped by interface handle";
            list interface-handle {
              key "interface-handle";
              description
                "Voq stats for a particular interface handle";
              leaf interface-handle {
                type Max-lc-intf-hand-les;
                description
                  "Interface Handle";
              }
              uses DPA-VOQ-INTF-PORT;
            }
          }
          container base-numbers {
            description
              "Voq stats grouped by voq base numbers";
            list base-number {
              key "base-number";
              description
                "Voq Base Number for a particular voq";
              leaf base-number {
                type Max-lc-intf-hand-les;
                description
                  "Interface handle";
              }
              uses DPA-VOQ-INTF-PORT;
            }
          }
        }
        leaf npu-id {
          type uint32;
          description
            "Npu number";
        }
      }
    }
  }
}
