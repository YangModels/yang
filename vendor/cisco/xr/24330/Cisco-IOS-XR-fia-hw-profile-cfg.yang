module Cisco-IOS-XR-fia-hw-profile-cfg {
  namespace "http://cisco.com/ns/yang/Cisco-IOS-XR-fia-hw-profile-cfg";
  prefix fia-hw-profile-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR fia-hw-profile package configuration.
     
     This module contains definitions
     for the following management objects:
       hw-module-profile-config: none
       hw-module-profile-disable-trap: none
       hw-module-profile-config-npu: none
       hw-module-profile-config-oversubscription: none
       hw-module-profile-config-tcam: none
     
     Copyright (c) 2013-2024 by Cisco Systems, Inc.
     All rights reserved.";

  revision 2024-10-15 {
    description
      "Added bgp-ip/if-peering/collapse to enable BGP interface peering collapse
       2024-07-12
         Added new CLI to disable hw-offload of V6 BFD and handle it in LC CPU
       2024-03-20
         Add new config leaf for profile/qos/etm-low-rate-connector
       2024-03-18
         Added new profile fat-based-hash under hw-module profile load-balance algorithm
       2024-03-06
         Add new CLI for disabling/enabling the RxTrapIpCompMcInvalidIp trap
       2024-02-07
         Added profile/vxlan/explicit-null/vxlan-enable
       2023-12-19
         Added new profile ecmp-hash-index under hw-module profile load-balance algorithm
       2023-12-15
         Schema updated for srv6 traffic-class policy-map-extend
       2023-07-14
         Added new CLI to enable bfd stats for singlepath
       2023-06-21
         Add new config leaf for profile/qos/lag-scheduler
       2023-03-31
         Add new config leaf for mcast/evpn/ole_collapse_disable
       2023-03-17
         Add node EvpnOleCollapseDisable to schema
       2023-03-08
         Added new CLI to enable multipath auto protection
       2023-03-04
         Add SRv6 path-mtu enable
       2023-02-24
         Schema updated for v6 dscp preserve config
       2023-02-08
         Schema added for Egress Compensation CLI
       2023-02-02
         Schema updated for tcam format
       2023-01-19
         Schema updated for max-classmap-size, ingress-model, hqos-enable, nif-hp-fifo-reserve, policer-scale, physical-hqos-enable, wred-stats-enable and qosg-dscp-mark-enable
       2022-12-14
         Schema updated for the l2pt-extended-protocols
       2022-12-14
         Added new command for the core replication optimization for L2 BUM Traffic
       2022-12-13
         Schema updated for physical-hqos-enable and ipv6 short-etm.
       2022-10-12
         Data type updated for bgppa stats-mode leaf
       2022-10-07
         Added PFC native support
       2022-09-06
         Removed sat-enable hw-module CLI
       2022-08-10
         Added new profile under hw-module profile load-balance algorithm
       2022-07-28
         Schema updated for IRB Recycle port bandwidth.
       2022-07-26
         Schema added for BGPPA feature CLI
       2022-07-18
         Data type updated for qos-policer leaf
       2022-07-08
         Added functionality for L2PT extended protocol set
       2022-06-17
         Yang models updated for ecn-marking-stats, shared-policer-per-class-stats, ipv6-short-l2qos-enable, qos-stats-collection
       2022-05-20
         Added new profile mpls-lsr-ler under hw-module profile load-balance algorithm
       2022-05-17
         Added new profile under hw-module profile load-balance algorithm
       2022-05-08
         Schema added.
       2022-04-25
         Renamed free-buf-int-thresh-set-clear container and added support to configure set and clear interrupt threshold values.
       2022-04-20
         Added span filter support for tx
       2022-04-05
         Schema change to have a single leaf for acl compression
       2022-04-01
         Add SRv6 l3-traffic option traffic-class-with-hoplimit
       2022-03-21
         Schema udpated for span l2 filter CLI
       2022-03-17
         Added Qos multicast Egress queue threshold and buffer parameters.
       2022-02-28
         Schema updated for qos policer scale CLI.
       2022-01-31
         Schema added for span l2 filter CLI
       2022-01-15
         Schema updated for qos free buffer int threshold configuration CLI.
       2022-01-10
         Schema updated for qos nif prd allocation CLI.
       2021-12-20
         Add SRv6 mode base-and-micro-segment-f3216
       2021-12-16
         Schema updated for egress compression CLI
       2021-11-09
         Add SRv6 L2/L3 config separation to encapsulation config. Add policy-map option to l3-traffic.
       2021-10-28
         Schema updated for qos stats push model CLI.";
    semver:module-version "5.0.0";
  }
  revision 2021-10-19 {
    description
      "Added functionality for L2PT extended protocol set
       2021-08-26
          Schema updated for support for match on ipv4/ipv6 destination address in L2 QOS database.
       2021-07-27
          Added functionality to disable Urpf
       2021-07-22
          Schema updated for Enabling and Disabling eTCAM LPTS profile CLI.
       2021-07-19
          Schema updated LoadBalanceProfile datatype changed to enum.
       2021-06-24
          Schema updated for QoS physical hqos profile CLI.
       2021-06-01
          Schema updated for ISIS/ARP priority";
    semver:module-version "4.0.0";
  }
  revision 2021-05-12 {
    description
      "Schema updated for sync between sysdb and schema for all platforms.
       2021-05-07
           Schema updated for QoS IPv6 short ETM profile CLI.
       2021-02-04
           Schema updated for native mode CLI.
       2020-09-18
           New leaf to specify routing profile as core
       2020-08-14
           SRV6 leaf deprecated and replaced by SRv6 Mode leaf
       2020-07-27
           Schema updated.
       2020-07-16
           Schema added.";
    semver:module-version "3.0.0";
  }
  revision 2020-04-30 {
    description
      "ACL UDK config changes: Added Common-ACL, replaced ProtType with NextHdr and Precedence with TraffClass
       2020-04-22
         SRV6 leaf deprecated and replaced by SRv6 Mode leaf
       2020-01-07
         Schema added.
       2020-01-05
         MGBL Sync config missmatch.";
    semver:module-version "2.0.0";
  }
  revision 2019-04-05 {
    description
      "Establish semantic version baseline.";
    semver:module-version "1.1.0";
  }
  revision 2016-06-22 {
    description
      "Schema added.";
  }
  revision 2015-11-09 {
    description
      "IOS XR 6.0 revision.";
  }

  typedef Data-plane {
    type enumeration {
      enum "all-dp" {
        value 0;
        description
          "All dataplanes";
      }
    }
    description
      "Data plane";
  }

  typedef Load-balance-profile {
    type enumeration {
      enum "layer2" {
        value 1;
        description
          "Layer 2 optimized";
      }
      enum "ip-tunnel" {
        value 2;
        description
          "IP tunnel optimized";
      }
      enum "mpls-safe-speculative-parsing" {
        value 3;
        description
          "MPLS safe Speculative parsing";
      }
      enum "gtp" {
        value 4;
        description
          "GTP optimized";
      }
      enum "l3-only" {
        value 5;
        description
          "L3 Header only Hash";
      }
      enum "gtp-mpls" {
        value 6;
        description
          "GTP over MPLS optimized hash";
      }
      enum "mpls-lsr-ler" {
        value 7;
        description
          "MPLS lsr ler LB profile";
      }
      enum "mpls-lsr-ler-optimized" {
        value 8;
        description
          "MPLS lsr ler optimized LB profile";
      }
      enum "pppoe" {
        value 9;
        description
          "PPPoE session based optimized hash and Reload
           is required for this option";
      }
      enum "inner-l2-field" {
        value 10;
        description
          "Inner MAC based optimised hashing";
      }
      enum "pppoe-decap-fat-based-hashing" {
        value 11;
        description
          "PPPoE session based optimized hash and Reload
           is required for this option";
      }
      enum "fat-based-hash" {
        value 12;
        description
          "FAT label based hash in l2vpn session on decap
           node and Reload is required for this option";
      }
    }
    description
      "Load balance profile";
  }

  typedef Srv6-traffic-class-l2 {
    type enumeration {
      enum "propagate" {
        value 2;
        description
          "Propagate traffic-class from incoming
           packet/frame";
      }
      enum "value" {
        value 3;
        description
          "Set traffic-class value";
      }
    }
    description
      "Srv6 traffic class l2";
  }

  typedef Bgppa-stats-mode {
    type enumeration {
      enum "main-intf" {
        value 1;
        description
          "BGP-PA stats for main interface";
      }
      enum "sub-intf" {
        value 2;
        description
          "BGP-PA stats for sub interface";
      }
    }
    description
      "Bgppa stats mode";
  }

  typedef Srv6-mode {
    type enumeration {
      enum "base" {
        value 3;
        description
          "SRv6 base mode";
      }
      enum "base-and-micro-segment-f3216" {
        value 5;
        description
          "SRv6 dual mode with base and micro-segment
           f3216";
      }
      enum "micro-segment-f3216" {
        value 12;
        description
          "SRv6 32-bit block and 16-bit IDs";
      }
    }
    description
      "Srv6 mode";
  }

  typedef Plane-rack {
    type uint32 {
      range "0..15";
    }
    description
      "Plane rack";
  }

  typedef Router-role {
    type enumeration {
      enum "core" {
        value 3;
        description
          "Core router";
      }
    }
    description
      "Router role";
  }

  typedef Qos-policer-scale {
    type enumeration {
      enum "max-policer-scale-48000" {
        value 48000;
        description
          "QOS policer scale 48000";
      }
      enum "max-policer-scale-64000" {
        value 64000;
        description
          "QOS policer scale 64000";
      }
    }
    description
      "Qos policer scale";
  }

  typedef Srv6-traffic-class-value {
    type uint32 {
      range "0..255";
    }
    description
      "Srv6 traffic class value";
  }

  typedef Qos-classmap-size {
    type enumeration {
      enum "max-classmap-size-1" {
        value 1;
        description
          "QOS classmap size 1";
      }
      enum "max-classmap-size-2" {
        value 2;
        description
          "QOS classmap size 2";
      }
      enum "max-classmap-size-4" {
        value 4;
        description
          "QOS classmap size 4";
      }
      enum "max-classmap-size-8" {
        value 8;
        description
          "QOS classmap size 8";
      }
      enum "max-classmap-size-16" {
        value 16;
        description
          "QOS classmap size 16";
      }
      enum "base" {
        value 32;
        description
          "QOS default classmap size 32";
      }
    }
    description
      "Qos classmap size";
  }

  typedef Srv6-traffic-class-l3 {
    type enumeration {
      enum "propagate" {
        value 2;
        description
          "Propagate traffic-class from incoming packet";
      }
      enum "value" {
        value 3;
        description
          "Set traffic-class value";
      }
      enum "policy-map" {
        value 4;
        description
          "Set traffic-class by policy-map";
      }
      enum "propagate-with-ttl" {
        value 5;
        description
          "Propagate traffic-class and TTL from incoming
           packet";
      }
      enum "policy-map-ext" {
        value 6;
        description
          "Set 6 bit traffic-class by policy-map";
      }
    }
    description
      "Srv6 traffic class l3";
  }

  container hw-module-profile-config {
    description
      "none";
    container irb {
      description
        "Configure irb mod.";
      leaf mode-l3l2 {
        type uint32;
        description
          "irb mode L3-L2";
      }
      leaf mode-l2l3 {
        type uint32;
        description
          "irb mode L2-L3";
      }
    }
    container profile {
      description
        "Configure profile.";
      container routing {
        description
          "Configure the node's routing profile";
        container data-planes {
          description
            "Configure the routing profile for a specific
             dataplane";
          list data-plane {
            key "dataplane";
            description
              "Configure the dataplane type";
            leaf role {
              type Router-role;
              description
                "Configure the node's routing role";
            }
            leaf dataplane {
              type Data-plane;
              description
                "Dataplane type";
            }
          }
        }
      }
      container netflow {
        description
          "Configure Netflow profile.";
        container sflow-netflow-locations {
          description
            "none";
          list sflow-netflow-location {
            key "location-string";
            description
              "none";
            leaf location-string {
              type xr:Cisco-ios-xr-string;
              description
                "Location of NETFLOW config";
            }
            list sflow-netflow-location-leaf {
              key "location-id";
              description
                "none";
              leaf location-id {
                type uint32;
                description
                  "Location ID";
              }
              leaf enable-val {
                type uint32;
                mandatory true;
                description
                  "If Enabled set value to 65535";
              }
            }
          }
        }
        container ipfix-location-all {
          description
            "IPFIX315 Location All";
          leaf ipfix-location-all-leaf {
            type uint32;
            description
              "If Enabled set value to 65535";
          }
        }
        container sflow-location-all {
          description
            "SFLOW Location All";
          leaf sflow-location-all-leaf {
            type uint32;
            description
              "If Enabled set value to 65535";
          }
        }
        container fpc-netflow-locations {
          description
            "none";
          list fpc-netflow-location {
            key "location-string";
            description
              "none";
            leaf location-string {
              type xr:Cisco-ios-xr-string;
              description
                "Location of NETFLOW config";
            }
            list fpc-netflow-location-leaf {
              key "location-id";
              description
                "none";
              leaf location-id {
                type uint32;
                description
                  "Location ID";
              }
              leaf enable-val {
                type uint32;
                mandatory true;
                description
                  "If Enabled set value to 65535";
              }
            }
          }
        }
        container ipfix-netflow-locations {
          description
            "none";
          list ipfix-netflow-location {
            key "location-string";
            description
              "none";
            leaf location-string {
              type xr:Cisco-ios-xr-string;
              description
                "Location of NETFLOW config";
            }
            list ipfix-netflow-location-leaf {
              key "location-id";
              description
                "none";
              leaf location-id {
                type uint32;
                description
                  "Location ID";
              }
              leaf enable-val {
                type uint32;
                mandatory true;
                description
                  "If Enabled set value to 65535";
              }
            }
          }
        }
        container fpc-location-all {
          description
            "FPC Location All";
          leaf fpc-location-all-leaf {
            type uint32;
            description
              "If Enabled set value to 65535";
          }
        }
      }
      container flowspec-table {
        description
          "Configure Flowspec profile.";
        container flowspecs {
          description
            "Configure v6 enable on Flowspec profile.";
          list flowspec {
            key "location-string location-id";
            description
              "none";
            leaf location-string {
              type xr:Cisco-ios-xr-string;
              description
                "Location of FLOWSPEC config";
            }
            leaf location-id {
              type uint32;
              description
                "Location ID hex to Decimal 65535";
            }
            leaf enable-val {
              type uint32;
              mandatory true;
              description
                "If Enabled set value to 1";
            }
          }
        }
      }
      container md-bprofile {
        description
          "Configure MDB profile.";
        leaf md-bprofile-type {
          type uint32;
          description
            "Configure MDB profile type";
        }
      }
      container span-filter {
        description
          "Configure span filter profile for DNS, HTTP,
           HTTPS and TLS packet mirror filtering";
        leaf l2l3-tx-span-filter-enable {
          type boolean;
          description
            "enable the l2 l3 traffic tx span filtering
             profile";
        }
        leaf l2-rx-span-filter-enable {
          type boolean;
          description
            "enable the l2 traffic rx span filtering
             profile";
        }
      }
      container bundle-hash {
        description
          "Configure Bundle Hash related parameters";
        container hash-index-locations {
          description
            "Bundle hash polynomial config";
          list hash-index-location {
            key "node-name";
            description
              "Bundle hash polynomial config location";
            leaf node-name {
              type xr:Cisco-ios-xr-string;
              description
                "NodeName";
            }
            list hash-index-location-leaf {
              key "location";
              description
                "Bundle hash polynomial config location leaf";
              leaf hash-index-location-leaf {
                type uint32;
                mandatory true;
                description
                  "Hash Index Location Leaf";
              }
              leaf location {
                type uint32;
                description
                  "Location";
              }
            }
          }
        }
        leaf per-pkt-round-robin {
          type boolean;
          description
            "bundlehash global per_pkt_round_robin mode";
        }
        leaf ignore-ing-port {
          type boolean;
          description
            "bundlehash ignore_ingress_port flag";
        }
      }
      container bgp-mp-pic {
        description
          "Configure bgp-mp-pic";
        leaf enable {
          type boolean;
          description
            "Enabled or disabled";
        }
      }
      container load-balance {
        description
          "Configure load balance parameters";
        leaf load-balance-profile {
          type Load-balance-profile;
          description
            "Configure load balance parameters";
        }
        leaf hash-poly-index {
          type uint32 {
            range "1..6";
          }
          description
            "hash polynomial index";
        }
      }
      container priority-flow-control-nodes {
        description
          "PriorityFlowControl config";
        list priority-flow-control-node {
          key "node-name";
          description
            "Configure PriorityFlowControl";
          leaf node-name {
            type xr:Cisco-ios-xr-string;
            description
              "NodeName";
          }
          list priority-flow-control-traffic-class {
            key "tcvalue";
            description
              "PriorityFlowControlTrafficClass";
            leaf tcvalue {
              type uint32;
              description
                "tcValue";
            }
            list priority-flow-control-threshold {
              key "location";
              description
                "PriorityFlowControl Threshold";
              container priority-flow-control-threshold-values {
                description
                  "PriorityFlowControl Threshold values";
                leaf pause-threshold {
                  type uint32 {
                    range "1..4294967295";
                  }
                  description
                    "PFC PauseThreshold";
                }
                leaf resume-threshold {
                  type uint32 {
                    range "1..4294967295";
                  }
                  description
                    "PFC ResumeThreshold";
                }
                leaf headroom {
                  type uint32 {
                    range "1..4294967295";
                  }
                  description
                    "PFC Headroom";
                }
              }
              leaf location {
                type uint32;
                description
                  "Location";
              }
            }
          }
        }
      }
      container stats {
        description
          "Configure stats";
        container stats-profile-modes {
          description
            "Configure stats for qos-enhanced, acl-permit
             and ingress-sr";
          list stats-profile-mode {
            key "counter-profile";
            description
              "Stats mode";
            leaf mode {
              type uint32;
              mandatory true;
              description
                "Stats Mode";
            }
            leaf counter-profile {
              type uint32;
              description
                "none";
            }
          }
        }
      }
      container bgp-multipath-path-auto-protection {
        description
          "Configure bgp-mp-auto-protect";
        leaf enable {
          type boolean;
          description
            "Enable BGP MP Auto Protection feature";
        }
      }
      container vxlan {
        description
          "Configure vxlan over mpls";
        container explicit-null {
          description
            "Configure vxlan over mpls explicit null";
          leaf vxlan-enable {
            type boolean;
            description
              "Enabled or disabled";
          }
        }
      }
      container mpls-dscp {
        description
          "Configure to preserve dscp with large label
           stack";
        leaf v6-enable {
          type empty;
          description
            "Enable to preserve dscp for ipv6 unicast
             traffic";
        }
        leaf enable {
          type boolean;
          description
            "Enable to preseve dscp for ipv4 unicast
             traffic";
        }
      }
      container bgp-ip {
        description
          "Configure bgp-ip";
        container if-peering {
          description
            "Configure bgp-ip if-peering";
          leaf collapse {
            type empty;
            description
              "Enable a BGP-IP Interface Peering collapse
               node";
          }
        }
      }
      container segment-routing {
        description
          "Configure Segment Routing profile.";
        container srv6 {
          description
            "Configure SRv6 profile.";
          container encapsulation {
            description
              "Configure encapsulation related parameters";
            container traffic-l3 {
              description
                "Configure encapsulation related parameters
                 for l3-traffic type";
              container traffic-class-l3 {
                presence "Contains mandatory nodes that used to set default values";
                description
                  "Configure traffic-class field of SRv6 IPv6
                   header";
                leaf type {
                  type Srv6-traffic-class-l3;
                  description
                    "Traffic-class type";
                }
                leaf value {
                  type Srv6-traffic-class-value;
                  mandatory true;
                  description
                    "Traffic-class value";
                }
              }
            }
            container traffic-l2 {
              description
                "Configure encapsulation related parameters
                 for l2-traffic type";
              container traffic-class-l2 {
                presence "Contains mandatory nodes that used to set default values";
                description
                  "Configure traffic-class field of SRv6 IPv6
                   header";
                leaf type {
                  type Srv6-traffic-class-l2;
                  description
                    "Traffic-class type";
                }
                leaf value {
                  type Srv6-traffic-class-value;
                  mandatory true;
                  description
                    "Traffic-class value";
                }
              }
            }
          }
          leaf mode {
            type Srv6-mode;
            description
              "Enable SRv6 mode/profile";
          }
          leaf path-mtu {
            type empty;
            description
              "Enable Path-MTU discovery for SRv6";
          }
        }
      }
      container profile-acl {
        description
          "Configure acl profile";
        container acl-ingress-compress-enable-locations {
          description
            "ingress compress enable";
          list acl-ingress-compress-enable-location {
            key "location-string";
            description
              "ingress compress enable location";
            leaf location-string {
              type xr:Cisco-ios-xr-string;
              description
                "Location of ACL config";
            }
          }
        }
        container acl-egress-compress-enable-locations {
          description
            "egress compress enable";
          list acl-egress-compress-enable-location {
            key "location-string";
            description
              "egress compress enable location";
            leaf location-string {
              type xr:Cisco-ios-xr-string;
              description
                "Location of ACL config";
            }
          }
        }
        leaf egress {
          type boolean;
          description
            "Enabled or disabled";
        }
        leaf acl-egress-compress-enable-location-all {
          type empty;
          description
            "Enable ACL egress compression on all locations";
        }
        leaf acl-ingress-compress-enable-location-all {
          type empty;
          description
            "Enable ACL ingress compression on all
             locations";
        }
        leaf ipv6-ext-hdr {
          type boolean;
          description
            "IPv6 Extension Hdr Permit";
        }
      }
      container bfd {
        description
          "Configure BFD profile.";
        leaf bfd-stats-enable-single-path {
          type empty;
          description
            "Enabled BFD Stats for Singlepath session(s)";
        }
        leaf bfd-offload-disable-v6 {
          type empty;
          description
            "Disabled BFD offload for V6 sessions";
        }
      }
      container sr-policies {
        description
          "Configure IPV6 NULL label autopush for SR
           policy.";
        list sr-policy {
          key "null-label-autopush";
          description
            "none";
          leaf null-label-autopush {
            type xr:Cisco-ios-xr-string;
            description
              "none";
          }
          leaf enable-val {
            type uint32;
            mandatory true;
            description
              "If Enabled set value to 1";
          }
        }
      }
      container bundle-scale {
        description
          "Configure Bundle profile.";
        leaf trunk-size {
          type uint32;
          description
            "Configure Max Trunk Size";
        }
      }
      container offload {
        description
          "Configure offload profile for NCS5501-SE";
        leaf offload-profile {
          type uint32;
          description
            "Configure offload profile for NCS5501-SE";
        }
      }
      container igp-dlb {
        description
          "configure igp_dlb";
        leaf enable {
          type boolean;
          description
            "fib dlb level-1 value";
        }
      }
      container qos {
        description
          "Configure profile.";
        container qos-policer-all {
          description
            "Configure qos policer scale";
          leaf qos-policer {
            type Qos-policer-scale;
            description
              "Qos policer scale value";
          }
        }
        container qos-nif-high-prio-fifo-reserve-root-all {
          description
            "Configure Reserve percentage of NIF FIFO for
             High Priority packet Global";
          leaf qos-nif-high-prio-fifo-reserve-percent-all {
            type uint32 {
              range "0..100";
            }
            units "percentage";
            description
              "Reserve percentage of NIF FIFO for High
               Priority packet Global";
          }
        }
        container qos-nif-high-prio-fifo-reserve-percent-nodes {
          description
            "Configure Reserve percentage of NIF FIFO for
             High Priority Root for node";
          list qos-nif-high-prio-fifo-reserve-percent-node {
            key "node-name";
            description
              "Reserve percentage of NIF FIFO for High
               Priority packet";
            leaf qos-nif-high-prio-fifo-reserve-percent {
              type uint32 {
                range "0..100";
              }
              units "percentage";
              mandatory true;
              description
                "Percentage to reserve NIF FIFO for High
                 Priority packets";
            }
            leaf node-name {
              type xr:Cisco-ios-xr-string;
              description
                "NodeName";
            }
          }
        }
        container hqos-enable-all {
          description
            "Configure Hqos profile";
          leaf hqos-enable {
            type uint32;
            description
              " Hqos profile value";
          }
        }
        container ingress-model-root-def {
          description
            "Configure Ingress Model Default";
          leaf ingress-model-leaf-def {
            type uint32;
            description
              "Ingress Model Default";
          }
        }
        container multicast-egr-rsrc {
          description
            "Configure Multicast Egress Resources";
          container multicast-egr-rsrc-thrld {
            description
              "Multicast Egress Resource Queue Threshold and
               Buffer";
            leaf multicast-egr-rsrc-thrld {
              type uint32;
              description
                "MulticastEgrRsrcThrld";
            }
            leaf multicast-egr-rsrc-queue {
              type uint32;
              description
                "MulticastEgrRsrcQueue";
            }
            leaf multicast-egr-rsrc-buffer {
              type uint32;
              description
                "MulticastEgrRsrcBuffer";
            }
          }
        }
        container qos-dscp-mark-enable {
          description
            "Enable both 'set qos-group' and 'set dscp/prec
             edence' actions in the same ingress QoS policy";
          container qos-dscp-mark-enable-values {
            description
              "Configure DSCP/Precedence value";
            leaf set-value1 {
              type uint32 {
                range "0..63";
              }
              description
                "First DSCP/Precedence value";
            }
            leaf set-value2 {
              type uint32 {
                range "0..63";
              }
              description
                "Second DSCP/Precedence value";
            }
            leaf set-value3 {
              type uint32 {
                range "0..63";
              }
              description
                "Third DSCP/Precedence value";
            }
            leaf set-value4 {
              type uint32 {
                range "0..63";
              }
              description
                "Fourth DSCP/Precedence value";
            }
            leaf set-value5 {
              type uint32 {
                range "0..63";
              }
              description
                "Fifth DSCP/Precedence value";
            }
            leaf set-value6 {
              type uint32 {
                range "0..63";
              }
              description
                "Sixth DSCP/Precedence value";
            }
            leaf set-value7 {
              type uint32 {
                range "0..63";
              }
              description
                "Seventh DSCP/Precedence value";
            }
            leaf set-value8 {
              type uint32 {
                range "0..63";
              }
              description
                "Eighth DSCP/Precedence value";
            }
          }
        }
        container ingress-model-leafs {
          description
            "Configure Ingress Model Root";
          list ingress-model-leaf {
            key "node-name";
            description
              "Configure Ingress Model Leaf";
            leaf ingress-model-leaf {
              type uint32;
              mandatory true;
              description
                "IngressModelLeaf";
            }
            leaf node-name {
              type xr:Cisco-ios-xr-string;
              description
                "NodeName";
            }
          }
        }
        container irb-recycle-root {
          description
            "Configure IRB Recycle Bandwidth";
          leaf irb-recycle-all {
            type uint32;
            description
              "IRB Recycle Bandwidth value";
          }
        }
        container class-maps-root-def {
          description
            "Configure Class Maps Default";
          leaf class-map-size-def {
            type uint32;
            description
              "Class Map Size Default";
          }
        }
        container free-buf-interrupt-thresh {
          description
            "Configure Free Buffer Interrupt Threshold
             Values";
          container free-buf-interrupt-thresh-set-clear {
            description
              "Configure Free Buffer Interrupt Threshold set
               and clear values";
            leaf set-value {
              type uint32 {
                range "0..99";
              }
              units "percentage";
              description
                "set value in percent (must be less than
                 clear value)";
            }
            leaf clear-value {
              type uint32 {
                range "1..100";
              }
              units "percentage";
              description
                "clear value in percent (must be more than
                 set value)";
            }
          }
        }
        container ecn-marking-stats-all {
          description
            "ecn marking stats value";
          leaf ecn-marking-stats {
            type uint32;
            description
              "EcnMarkingStats";
          }
        }
        container physical-hqos-enable-all {
          description
            "Configure physical intf Hqos profile";
          leaf physical-hqos-enable {
            type uint32;
            description
              " Physical Hqos profile value (enable:1)";
          }
        }
        container etm-low-rate-connector-reserve-npu-alls {
          description
            "Low rate connector allocation for ETM
             interfaces on SE platforms with J2 family of
             ASICs)";
          list etm-low-rate-connector-reserve-npu-all {
            key "npu-id";
            description
              "Number of connector range (1024 connectors
               per range) to be reserved (0 indicates no
               reservation/feature disabled)";
            leaf reserve-conn-range {
              type uint32 {
                range "0..64";
              }
              mandatory true;
              description
                "connector range value in decimal
                 Jericho2C(P): <0-64> and Jericho2: <0-32>";
            }
            leaf npu-id {
              type uint32 {
                range "0..5";
              }
              description
                "NPU ID in Decimal";
            }
          }
        }
        container class-map-sizes {
          description
            "Configure Class Map Root";
          list class-map-size {
            key "node-name";
            description
              "Class Map Size";
            leaf class-map-size {
              type Qos-classmap-size;
              mandatory true;
              description
                "ClassMapSize";
            }
            leaf node-name {
              type xr:Cisco-ios-xr-string;
              description
                "NodeName";
            }
          }
        }
        container etm-low-rate-connector-reserve-npu-nodes {
          description
            "Low rate connector allocation for ETM
             interfaces on SE platforms with J2 family of
             ASICs)";
          list etm-low-rate-connector-reserve-npu-node {
            key "node-name";
            description
              "Location to apply Low rate connector range
               reservation configuration";
            leaf node-name {
              type xr:Cisco-ios-xr-string;
              description
                "NodeName";
            }
            list etm-low-rate-connector-reserve-value {
              key "npu-id";
              description
                "Number of connector range (1024 connectors
                 per range) to be reserved (0 indicates no
                 reservation/feature disabled)";
              leaf reserve-conn-range {
                type uint32 {
                  range "0..64";
                }
                mandatory true;
                description
                  "connector range value in decimal
                   Jericho2C(P): <0-64> and Jericho2: <0-32>";
              }
              leaf npu-id {
                type uint32 {
                  range "0..5";
                }
                description
                  "NPU ID in Decimal";
              }
            }
          }
        }
        container wred-stats-enable-all {
          description
            "wred stats enable";
          leaf wred-stats-enable {
            type uint32;
            description
              "WredStatsEnable";
          }
        }
        container irb-recycle-nodes {
          description
            "Configure IRB Recycle Bandwidth for Node";
          list irb-recycle-node {
            key "node-name";
            description
              "IRB Recycle Bandwidth value";
            leaf irb-recycle-node {
              type uint32;
              mandatory true;
              description
                "IrbRecycleNode";
            }
            leaf node-name {
              type xr:Cisco-ios-xr-string;
              description
                "NodeName";
            }
          }
        }
        leaf qos-stats-collection {
          type uint32;
          description
            "QoS stats push model profile value";
        }
        leaf egr-comp-force-set-enable {
          type uint32;
          description
            "Forcefully allows to configure non-unique
             egress compensation values ignoring ASIC
             limitation (not recommended).";
        }
        leaf conform-aware-policer {
          type uint32;
          description
            "Configure Conform Aware Policer mode";
        }
        leaf lag-scheduler {
          type empty;
          description
            "Enable LAG Scheduler profile";
        }
        leaf gre-exp-cls {
          type uint32;
          description
            "Enable EXP classification for MPLSoGRE";
        }
        leaf shared-policer-per-class-stats {
          type uint32;
          description
            "Shared policer (per class stats) mode profile
             value";
        }
        leaf qos-stats-push-model-enable {
          type uint32;
          description
            " Qos stats push model profile value";
        }
        leaf l2-match-destination-address-ipv4-ipv6 {
          type uint32;
          description
            "Enable L2 match dest address feature";
        }
        leaf arp-isis-priority {
          type uint32;
          description
            "Enable ARP/ISIS priority";
        }
      }
      container oam {
        description
          "Configure oam sat profile.";
        leaf cfm-maid-enable {
          type boolean;
          description
            "Oam CFM Maid enable value";
        }
      }
    }
    container storm-control-combine-policer-bw {
      description
        "Configure strorm control profile.";
      leaf enable {
        type boolean;
        description
          "Enabled or disabled";
      }
    }
    container fib-scale {
      description
        "Configure Fib for Scale for noTcam LC.";
      container ipv4-unicast-scale-no-tcam {
        description
          "IPv4 table for NOTCAM LC Scale.";
        container scale-ipv4-no-tcam {
          description
            "Scale for IPv4 table for NoTCAM LC.";
          leaf optimized-ipv4-no-tcam {
            type string;
            description
              "Optimized Scale for IPv4 table for NoTCAM LC.";
          }
        }
      }
    }
    container l2pt-extended-protocols {
      description
        "Configure profile.";
      leaf enable {
        type boolean;
        description
          "L2PT Extended Protocols Enable value";
      }
    }
    container fib-table {
      description
        "Configure FIB profile.";
      container mpls-table {
        description
          "Configure mpls protocol";
        container propagate-exceptions {
          description
            "Configure TTL propagation behaviour";
          list propagate-exception {
            key "propagate-exception";
            description
              "Propagate TTL on disposition in mixed paths
               use case";
            leaf propagate-exception {
              type xr:Cisco-ios-xr-string;
              description
                "none";
            }
            leaf enable-val {
              type uint32;
              mandatory true;
              description
                "If Enabled set value to 1";
            }
          }
        }
      }
      container bgppa {
        description
          "Configure bgppa enable";
        leaf bgppa-stats-mode {
          type Bgppa-stats-mode;
          description
            "stats mode";
        }
      }
      container service-over-rsvptes {
        description
          "Recycle traffic for BGP services going over
           RSVP TE transport";
        list service-over-rsvpte {
          key "service-over-rsvpte";
          description
            "none";
          leaf service-over-rsvpte {
            type xr:Cisco-ios-xr-string;
            description
              "none";
          }
          leaf enable-val {
            type uint32;
            mandatory true;
            description
              "If Enabled set value to 1";
          }
        }
      }
      container urpf {
        description
          "Configure Urpf disable";
        leaf urpf-disable {
          type boolean;
          description
            "Enabled or disabled";
        }
      }
    }
    container orchestrated-linecard-reload {
      description
        "Configure OLR.";
      container plane-table-entries {
        description
          "Plane type";
        list plane-table-entry {
          key "plane-name";
          description
            "Plane : A or B";
          container rack-table-entries {
            description
              "Rack Information";
            list rack-table-entry {
              key "rack-num";
              description
                "Rack Number";
              leaf nodes-list {
                type string;
                description
                  "Please enter linecards separated via comma
                   eg 0,3,6,11,13";
              }
              leaf rack-num {
                type Plane-rack;
                description
                  "Rack Number";
              }
            }
          }
          leaf plane-name {
            type xr:Cisco-ios-xr-string;
            description
              "Plane Name";
          }
        }
      }
    }
    container vrrp-scale {
      description
        "Configure vrrpscale profile.";
      leaf enable {
        type boolean;
        description
          "vrrpscale profile value";
      }
    }
    container multicast {
      description
        "Configure multicast properties.";
      leaf mode-multicast-l3l2 {
        type uint32;
        description
          "access pw enable with irb mode Mcast L3-L2";
      }
      leaf evpn-ole-collapse-disable {
        type empty;
        description
          "Disable collapsing of EVPN OLEs in multicast
           routes";
      }
    }
    container qosqppb {
      description
        "Configure profile.";
      container ipv6-scale {
        description
          "Configure IPv6 destination short profile";
        leaf ipv6-short {
          type boolean;
          description
            "ipv6 short profile value";
        }
      }
      container ipv6-short-etm-profile {
        description
          "Configure IPv6 short ETM profile";
        leaf ipv6-short-etm-profile-leaf {
          type boolean;
          description
            "IPv6 short ETM profile value";
        }
      }
      leaf ipv6-short-l2-qos-enable {
        type boolean;
        description
          "L2qos short profile value";
      }
    }
    container gue {
      description
        "Configure gue udp port";
      container udp {
        description
          "Configure udp port number";
        leaf ipv4 {
          type uint32 {
            range "0..64000";
          }
          description
            "Configure udp dest port for ipv4, 0 will set
             to default";
        }
        leaf mpls {
          type uint32 {
            range "0..64000";
          }
          description
            "Configure udp dest port for mpls, , 0 will set
             to default";
        }
        leaf ipv6 {
          type uint32 {
            range "0..64000";
          }
          description
            "Configure udp dest port for ipv6, 0 will set
             to default";
        }
      }
    }
    container l2-replication {
      description
        "Configure replication optimization profile.";
      leaf replication-mode-enable {
        type empty;
        description
          "Enable core replication optimization";
      }
    }
  }
  container hw-module-profile-disable-trap {
    description
      "none";
    container disable-trap {
      description
        "Disable trap in h/w";
      leaf trap-id {
        type uint32;
        description
          "Disable trap in hw";
      }
    }
  }
  container hw-module-profile-config-npu {
    description
      "none";
    container profile-npu {
      description
        "Configure profile.";
      container npu-native-mode-enable {
        description
          "Configure NPU to work in Native Mode.";
        leaf enable {
          type boolean;
          description
            "NPU Native Mode Enable value";
        }
      }
    }
  }
  container hw-module-profile-config-oversubscription {
    description
      "none";
    container oversub-interfaces {
      description
        "Configure Oversubscription.";
      list oversub-interface {
        key "interface-name";
        description
          "Oversubscription Interface.";
        leaf interface-name {
          type xr:Cisco-ios-xr-string;
          description
            "InterfaceName";
        }
        list cos-value {
          key "cosvalue";
          description
            "Configured cos";
          leaf enable {
            type uint32;
            description
              "Enabled/Disabled";
          }
          leaf cosvalue {
            type uint32;
            description
              "cosvalue";
          }
        }
      }
    }
  }
  container hw-module-profile-config-tcam {
    description
      "none";
    container tcam {
      description
        "Configure Tcam.";
      container fib-tcam-scale {
        description
          "Configure Fib scale for Tcam.";
        container ipv4-unicast-scale {
          description
            "IPv4 table for TCAM LC Scale.";
          leaf ipv4-scale {
            type boolean;
            description
              "Scale for IPv4 table for TCAM LC.";
          }
        }
      }
    }
    container profile-tcam {
      description
        "Configure Tcam profile.";
      container tcam-table {
        description
          "Configure profile for TCAM LC cards";
        container fib-table {
          description
            "FIB table for TCAM LC cards";
          container ipv4-address {
            description
              "IPv4 table for TCAM LC cards";
            container ipv4-unicast {
              description
                "Unicast table for TCAM LC cards";
              container ipv4-unicast-prefix-lengths {
                description
                  "IPv4 Unicast prefix ";
                list ipv4-unicast-prefix-length {
                  key "prefix-length";
                  description
                    "IPv4 Unicast prefix length";
                  leaf ipv4-unicast-prefix-percent {
                    type string;
                    units "percentage";
                    description
                      "curve out percentage of TCAM table
                       entries";
                  }
                  leaf prefix-length {
                    type uint32 {
                      range "0..32";
                    }
                    description
                      "prefix length";
                  }
                }
              }
              leaf ipv4-unicast-percent {
                type uint32 {
                  range "0..100";
                }
                units "percentage";
                description
                  "curve out percentage of TCAM table entries";
              }
            }
          }
          container ipv6-address {
            description
              "IPv6 table for TCAM LC cards";
            container ipv6-unicast {
              description
                "Unicast table for TCAM LC cards";
              container ipv6-unicast-prefix-lengths {
                description
                  "IPv6 Unicast prefix ";
                list ipv6-unicast-prefix-length {
                  key "prefix-length";
                  description
                    "IPv6 Unicast prefix length";
                  leaf ipv6-unicast-prefix-percent {
                    type string;
                    units "percentage";
                    description
                      "curve out percentage of TCAM table
                       entries";
                  }
                  leaf prefix-length {
                    type uint32 {
                      range "0..128";
                    }
                    description
                      "prefix length";
                  }
                }
              }
              leaf ipv6-unicast-percent {
                type uint32 {
                  range "0..100";
                }
                units "percentage";
                description
                  "curve out percentage of TCAM table entries";
              }
            }
          }
        }
        container acl-prefix {
          description
            "ACL table to configure";
          leaf acl-prefix-percent {
            type uint32 {
              range "0..100";
            }
            units "percentage";
            description
              "Percent to configure";
          }
        }
        leaf lpts-internal {
          type boolean;
          description
            "Switch to internal TCAM";
        }
      }
      container profile-tcam-key {
        description
          "Configure Tcam Profile";
        container key-format {
          description
            "none";
          container key-format-acl-table {
            description
              "Configure acl profile";
            container ipv6-acl-default {
              description
                "Configure ipv6 acl profile";
              container ipv6-acl-default-table {
                description
                  "Configure format for ipv6 acl profile for
                   all locations";
                leaf source-addr {
                  type uint32;
                  description
                    "Source Address";
                }
                leaf source-port {
                  type uint32;
                  description
                    "Source Port";
                }
                leaf destination-addr {
                  type uint32;
                  description
                    "Destination Address";
                }
                leaf dest-port {
                  type uint32;
                  description
                    "Destination Port";
                }
                leaf next-hdr {
                  type uint32;
                  description
                    "Next Header Type";
                }
                leaf tcp-flag {
                  type uint32;
                  description
                    "TCP Flags";
                }
                leaf payload-len {
                  type uint32;
                  description
                    "Payload Length";
                }
                leaf traff-class {
                  type uint32;
                  description
                    "Traffic Class";
                }
                leaf frag-bit {
                  type uint32;
                  description
                    "Fragment Bit";
                }
                leaf udf1 {
                  type string;
                  description
                    "UDF name";
                }
                leaf udf2 {
                  type string;
                  description
                    "UDF name";
                }
                leaf udf3 {
                  type string;
                  description
                    "UDF name";
                }
                leaf udf4 {
                  type string;
                  description
                    "UDF name";
                }
                leaf udf5 {
                  type string;
                  description
                    "UDF name";
                }
                leaf udf6 {
                  type string;
                  description
                    "UDF name";
                }
                leaf udf7 {
                  type string;
                  description
                    "UDF name";
                }
                leaf udf8 {
                  type string;
                  description
                    "UDF name";
                }
                leaf en-capture {
                  type uint32;
                  description
                    "Enable Capture";
                }
                leaf en-ttl {
                  type uint32;
                  description
                    "Enable Setting TTL";
                }
                leaf en-match {
                  type uint32;
                  description
                    "Enable Matching TTL";
                }
                leaf en-share-acl {
                  type uint32;
                  description
                    "Enable Non Shared Interface ACL";
                }
                leaf common-acl {
                  type uint32;
                  description
                    "Enable Common-ACL";
                }
              }
            }
            container ipv4-acl-default {
              description
                "Configure ipv4 acl profile";
              container ipv4-acl-default-table {
                description
                  "Configure format for ipv4 acl profile for
                   all locations";
                leaf source-addr {
                  type uint32;
                  description
                    "Source Address";
                }
                leaf destination-addr {
                  type uint32;
                  description
                    "Destination Address";
                }
                leaf source-port {
                  type uint32;
                  description
                    "Source Port";
                }
                leaf dest-port {
                  type uint32;
                  description
                    "Destination Port";
                }
                leaf prot-type {
                  type uint32;
                  description
                    "Protocol Type";
                }
                leaf tcp-flag {
                  type uint32;
                  description
                    "TCP Flags";
                }
                leaf pack-len {
                  type uint32;
                  description
                    "Packet Length";
                }
                leaf frag-bit {
                  type uint32;
                  description
                    "Fragment Bit";
                }
                leaf precedence {
                  type uint32;
                  description
                    "Precedence";
                }
                leaf port-range {
                  type uint32;
                  description
                    "PortRange";
                }
                leaf udf1 {
                  type string;
                  description
                    "UDF name";
                }
                leaf udf2 {
                  type string;
                  description
                    "UDF name";
                }
                leaf udf3 {
                  type string;
                  description
                    "UDF name";
                }
                leaf udf4 {
                  type string;
                  description
                    "UDF name";
                }
                leaf udf5 {
                  type string;
                  description
                    "UDF name";
                }
                leaf udf6 {
                  type string;
                  description
                    "UDF name";
                }
                leaf udf7 {
                  type string;
                  description
                    "UDF name";
                }
                leaf udf8 {
                  type string;
                  description
                    "UDF name";
                }
                leaf en-capture {
                  type uint32;
                  description
                    "Enable Capture";
                }
                leaf en-ttl {
                  type uint32;
                  description
                    "Enable Setting TTL";
                }
                leaf en-match {
                  type uint32;
                  description
                    "Enable Matching TTL";
                }
                leaf en-share-acl {
                  type uint32;
                  description
                    "Enable Non Shared Interface ACL";
                }
                leaf common-acl {
                  type uint32;
                  description
                    "Enable Common-ACL";
                }
              }
            }
            container ipv6-acl-tables {
              description
                "Configure ipv6 acl profile";
              list ipv6-acl-table {
                key "location-string";
                description
                  "Configure format for ipv6 acl profile";
                leaf location-string {
                  type xr:Cisco-ios-xr-string;
                  description
                    "Location string (all) if for all LCs";
                }
                leaf source-addr {
                  type uint32;
                  description
                    "Source Address";
                }
                leaf source-port {
                  type uint32;
                  description
                    "Source Port";
                }
                leaf destination-addr {
                  type uint32;
                  description
                    "Destination Address";
                }
                leaf dest-port {
                  type uint32;
                  description
                    "Destination Port";
                }
                leaf next-hdr {
                  type uint32;
                  description
                    "Next Header Type";
                }
                leaf tcp-flag {
                  type uint32;
                  description
                    "TCP Flags";
                }
                leaf payload-len {
                  type uint32;
                  description
                    "Payload Length";
                }
                leaf traff-class {
                  type uint32;
                  description
                    "Traffic Class";
                }
                leaf frag-bit {
                  type uint32;
                  description
                    "Fragment Bit";
                }
                leaf udf1 {
                  type string;
                  description
                    "UDF name";
                }
                leaf udf2 {
                  type string;
                  description
                    "UDF name";
                }
                leaf udf3 {
                  type string;
                  description
                    "UDF name";
                }
                leaf udf4 {
                  type string;
                  description
                    "UDF name";
                }
                leaf udf5 {
                  type string;
                  description
                    "UDF name";
                }
                leaf udf6 {
                  type string;
                  description
                    "UDF name";
                }
                leaf udf7 {
                  type string;
                  description
                    "UDF name";
                }
                leaf udf8 {
                  type string;
                  description
                    "UDF name";
                }
                leaf en-capture {
                  type uint32;
                  description
                    "Enable Capture";
                }
                leaf en-ttl {
                  type uint32;
                  description
                    "Enable Setting TTL";
                }
                leaf en-match {
                  type uint32;
                  description
                    "Enable Matching TTL";
                }
                leaf en-share-acl {
                  type uint32;
                  description
                    "Enable Non Shared Interface ACL";
                }
                leaf common-acl {
                  type uint32;
                  description
                    "Enable Common-ACL";
                }
              }
            }
            container ipv4-acl-tables {
              description
                "Configure ipv4 acl profile";
              list ipv4-acl-table {
                key "location-string";
                description
                  "Configure format for ipv4 acl profile";
                leaf location-string {
                  type xr:Cisco-ios-xr-string;
                  description
                    "Location string (all) if for all LCs";
                }
                leaf source-addr {
                  type uint32;
                  description
                    "Source Address";
                }
                leaf destination-addr {
                  type uint32;
                  description
                    "Destination Address";
                }
                leaf source-port {
                  type uint32;
                  description
                    "Source Port";
                }
                leaf dest-port {
                  type uint32;
                  description
                    "Destination Port";
                }
                leaf prot-type {
                  type uint32;
                  description
                    "Protocol Type";
                }
                leaf tcp-flag {
                  type uint32;
                  description
                    "TCP Flags";
                }
                leaf pack-len {
                  type uint32;
                  description
                    "Packet Length";
                }
                leaf frag-bit {
                  type uint32;
                  description
                    "Fragment Bit";
                }
                leaf precedence {
                  type uint32;
                  description
                    "Precedence";
                }
                leaf port-range {
                  type uint32;
                  description
                    "PortRange";
                }
                leaf udf1 {
                  type string;
                  description
                    "UDF name";
                }
                leaf udf2 {
                  type string;
                  description
                    "UDF name";
                }
                leaf udf3 {
                  type string;
                  description
                    "UDF name";
                }
                leaf udf4 {
                  type string;
                  description
                    "UDF name";
                }
                leaf udf5 {
                  type string;
                  description
                    "UDF name";
                }
                leaf udf6 {
                  type string;
                  description
                    "UDF name";
                }
                leaf udf7 {
                  type string;
                  description
                    "UDF name";
                }
                leaf udf8 {
                  type string;
                  description
                    "UDF name";
                }
                leaf en-capture {
                  type uint32;
                  description
                    "Enable Capture";
                }
                leaf en-ttl {
                  type uint32;
                  description
                    "Enable Setting TTL";
                }
                leaf en-match {
                  type uint32;
                  description
                    "Enable Matching TTL";
                }
                leaf en-share-acl {
                  type uint32;
                  description
                    "Enable Non Shared Interface ACL";
                }
                leaf common-acl {
                  type uint32;
                  description
                    "Enable Common-ACL";
                }
              }
            }
          }
        }
      }
    }
  }
}
