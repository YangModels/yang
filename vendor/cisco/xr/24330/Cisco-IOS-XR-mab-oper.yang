module Cisco-IOS-XR-mab-oper {
  namespace "http://cisco.com/ns/yang/Cisco-IOS-XR-mab-oper";
  prefix mab-oper;

  import Cisco-IOS-XR-types {
    prefix xr;
  }
  import cisco-semver {
    prefix semver;
  }
  include Cisco-IOS-XR-mab-oper-sub1 {
    revision-date 2024-03-21;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR mab package operational data.
     
     This module contains definitions
     for the following management objects:
       mab: MAB operational data
     
     Copyright (c) 2013-2024 by Cisco Systems, Inc.
     All rights reserved.";

  revision 2024-03-21 {
    description
      "Added l2-transport leaf under mab interface detail";
    semver:module-version "1.0.0";
  }
  revision 2022-03-14 {
    description
      "Added fields to display AuthRetry Timeout and timer status";
  }
  revision 2021-11-23 {
    description
      "Added field to display Held Timeout and timer status";
  }
  revision 2021-10-11 {
    description
      "New Oper Model added to support MAC Authentication Bypass feature";
  }
  revision 2019-04-05 {
    description
      "Establish semantic version baseline.";
  }
  revision 2015-11-09 {
    description
      "IOS XR 6.0 revision.";
  }

  container mab {
    config false;
    description
      "MAB operational data";
    container nodes {
      description
        "Node-specific MAB operational data";
      list node {
        key "node-name";
        description
          "MAB operational data for a particular node";
        container statistics {
          description
            "MAB Node Specific Statistics";
          uses MAB-NODE-STATISTICS;
        }
        leaf node-name {
          type xr:Node-id;
          description
            "The node name";
        }
      }
    }
    container interfaces {
      description
        "List of MAB enabled interfaces";
      list interface {
        key "name";
        description
          "MAB enabled interface name";
        container statistics {
          description
            "MAB Interface Statistics";
          uses MAB-IF-STATISTICS;
        }
        container detail {
          description
            "MAB Interface Detail";
          uses MAB-INTERFACE-DETAIL;
        }
        leaf name {
          type xr:Interface-name;
          description
            "Interface Name";
        }
      }
    }
  }
}
