module Cisco-IOS-XR-pmengine-oper {
  namespace "http://cisco.com/ns/yang/Cisco-IOS-XR-pmengine-oper";
  prefix pmengine-oper;

  import Cisco-IOS-XR-types {
    prefix xr;
  }
  import cisco-semver {
    prefix semver;
  }
  include Cisco-IOS-XR-pmengine-oper-sub1 {
    revision-date 2024-04-24;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR pmengine package operational data.
     
     This module contains definitions
     for the following management objects:
       performance-management: performace data
       performance-management-history: performace data
     
     Copyright (c) 2013-2024 by Cisco Systems, Inc.
     All rights reserved.";

  revision 2024-04-24 {
    description
      "New parameters supported for Protect Path
       2023-08-11
         Added support for SLR, SLT, SLR(C+L), SLT(C+L), SLR(s), SLT(s) parameters in Optics layer.
       2023-08-03
         Added support for 7 days history data for 24-hour bucket.
       2023-08-02
         Support added for new parameters like 'raman-br', 'raman-brr' in OTS layer.
       2023-05-15
         Added support for OPBRR parameters in Optics layer.
       2023-04-18
         Added support for SNR-X and SNR-Y parameters in Optics layer.
       2022-10-20
         Added 30-sec bucket history yang support for ODU controllers
       2022-08-16
         Changed data type of some leaf nodes from uint32 to uint64
       2022-05-10
         Removed unsupported parameters for OSC controller
       2022-05-10
         Removed unsupported parameters for OMS controller
       2022-05-10
         Removed unsupported parameters for OCH controller
       2022-05-10
         Removed unsupported parameters for DFB controller
       2022-04-03
         Added opt_min_50dbm_cap caps to set dBm Optics Parameter mininal value to -50.0dBm
       2022-03-06
         Support added for user-defined and pn9 patterns in prbs layer.
       2021-12-17
         Added oper support for Host PM parameters in FEC layer.
       2021-10-13
         Support added for cumulative-bad-sh and cumulative-frm-err in pcs layer.
       2021-10-06
         Support added for new counters in Optics layer.";
    semver:module-version "1.5.0";
  }
  revision 2021-07-09 {
    description
      "Support added for prbs layer for fibre-channel, ocn, stm and ethernet controllers. Support added for cem layer and controller. Container cem added.
       2021-04-26
          Support added for E1 controller.
       2021-04-14
          Support added for pcs and fec layers for fibre-channel controller.
       2021-02-24
          Support added for fc layer and controller. Container fibre-channel added.";
    semver:module-version "1.4.0";
  }
  revision 2020-09-02 {
    description
      "Added PM support for PRBS direction feature.
       2020-07-20
           Added parameter for cumulative BIP count in pcs pmengine bag.
       2020-04-17
           Added Instantaneous Q Margin in fec layer.
       2020-04-07
           Changes made to support TCA for OTU PRBS layer.";
    semver:module-version "1.3.0";
  }
  revision 2019-10-10 {
    description
      "Added support for flexible bin.";
    semver:module-version "1.2.0";
  }
  revision 2019-09-30 {
    description
      "Existing optics parameter PMD is deprecated and SOPMD is added to use instead.
       2019-08-28
         Max and Min time support for fec and optics layer parameters.
       2019-06-01
         Added Range attribute for the history buckets.";
    semver:module-version "1.1.0";
  }
  revision 2019-04-05 {
    description
      "Establish semantic version baseline.";
    semver:module-version "1.0.0";
  }
  revision 2017-09-07 {
    description
      "Fixed type translation error.";
  }
  revision 2017-05-01 {
    description
      "Fixing backward compatibility error in module.";
  }
  revision 2017-03-30 {
    description
      "OTU PRBS Stats Added";
  }
  revision 2015-11-09 {
    description
      "IOS XR 6.0 revision.";
  }

  container performance-management {
    config false;
    description
      "performace data";
    container macsec {
      description
        "MACSEC controller performance data";
      container macsec-ports {
        description
          "Port performance data";
        list macsec-port {
          key "name";
          description
            "Port performance data";
          container macsec-prev {
            description
              "port prev performance data";
            container macsec-prev-flex-interval {
              description
                "port prev performance data";
              container macsec-prev-flex-interval-ether-s {
                description
                  "port prev performance data";
                list macsec-prev-flex-interval-ether {
                  key "number";
                  description
                    "port flex-sec ether performance data";
                  leaf number {
                    type uint32;
                    description
                      "channel number";
                  }
                  uses PM-ETHERNET-PARAS;
                }
              }
              container macsec-prev-flex-interval-secyifs {
                description
                  "port prev performance data";
                list macsec-prev-flex-interval-secyif {
                  key "number";
                  description
                    "port flex-sec secy-if performance data";
                  leaf number {
                    type uint32;
                    description
                      "channel number";
                  }
                  uses PM-SECY-IF-PARAS;
                }
              }
              container macsec-prev-flex-interval-secyrxes {
                description
                  "port prev performance data";
                list macsec-prev-flex-interval-secyrx {
                  key "number";
                  description
                    "port flex-sec secy-rx performance data";
                  leaf number {
                    type uint32;
                    description
                      "channel number";
                  }
                  uses PM-SECY-RX-PARAS;
                }
              }
              container macsec-prev-flex-interval-secytxes {
                description
                  "port prev performance data";
                list macsec-prev-flex-interval-secytx {
                  key "number";
                  description
                    "port flex-sec secy-tx performance data";
                  leaf number {
                    type uint32;
                    description
                      "channel number";
                  }
                  uses PM-SECY-TX-PARAS;
                }
              }
            }
          }
          container macsec-current {
            description
              "port current performance data";
            container macsec-minute15 {
              description
                "port current performance data";
              container macsec-minute15secyifs {
                description
                  "port current performance data";
                list macsec-minute15secyif {
                  key "number";
                  description
                    "port 15-minute secy-if performance data";
                  leaf number {
                    type uint32;
                    description
                      "channel number";
                  }
                  uses PM-SECY-IF-PARAS;
                }
              }
              container macsec-minute15secyrxes {
                description
                  "port current performance data";
                list macsec-minute15secyrx {
                  key "number";
                  description
                    "port 15-minute secy-rx performance data";
                  leaf number {
                    type uint32;
                    description
                      "channel number";
                  }
                  uses PM-SECY-RX-PARAS;
                }
              }
              container macsec-minute15secytxes {
                description
                  "port current performance data";
                list macsec-minute15secytx {
                  key "number";
                  description
                    "port 15-minute secy-tx performance data";
                  leaf number {
                    type uint32;
                    description
                      "channel number";
                  }
                  uses PM-SECY-TX-PARAS;
                }
              }
              container macsec-minute15-ether-s {
                description
                  "port current performance data";
                list macsec-minute15-ether {
                  key "number";
                  description
                    "port 15-minute ether performance data";
                  leaf number {
                    type uint32;
                    description
                      "channel number";
                  }
                  uses PM-ETHERNET-PARAS;
                }
              }
            }
            container macsec-second30 {
              description
                "port current performance data";
              container macsec-second30secyifs {
                description
                  "port current performance data";
                list macsec-second30secyif {
                  key "number";
                  description
                    "port 30-sec secy-if performance data";
                  leaf number {
                    type uint32;
                    description
                      "channel number";
                  }
                  uses PM-SECY-IF-PARAS;
                }
              }
              container macsec-second30secyrxes {
                description
                  "port current performance data";
                list macsec-second30secyrx {
                  key "number";
                  description
                    "port 30-sec secy-rx performance data";
                  leaf number {
                    type uint32;
                    description
                      "channel number";
                  }
                  uses PM-SECY-RX-PARAS;
                }
              }
              container macsec-second30-ether-s {
                description
                  "port current performance data";
                list macsec-second30-ether {
                  key "number";
                  description
                    "port 30-sec ether performance data";
                  leaf number {
                    type uint32;
                    description
                      "channel number";
                  }
                  uses PM-ETHERNET-PARAS;
                }
              }
              container macsec-second30secytxes {
                description
                  "port current performance data";
                list macsec-second30secytx {
                  key "number";
                  description
                    "port 30-sec secy-tx performance data";
                  leaf number {
                    type uint32;
                    description
                      "channel number";
                  }
                  uses PM-SECY-TX-PARAS;
                }
              }
            }
            container macsec-flex-interval {
              description
                "port current performance data";
              container macsec-flex-interval-secyifs {
                description
                  "port current performance data";
                list macsec-flex-interval-secyif {
                  key "number";
                  description
                    "port flex-sec secy-if performance data";
                  leaf number {
                    type uint32;
                    description
                      "channel number";
                  }
                  uses PM-SECY-IF-PARAS;
                }
              }
              container macsec-flex-interval-secyrxes {
                description
                  "port current performance data";
                list macsec-flex-interval-secyrx {
                  key "number";
                  description
                    "port flex-sec secy-rx performance data";
                  leaf number {
                    type uint32;
                    description
                      "channel number";
                  }
                  uses PM-SECY-RX-PARAS;
                }
              }
              container macsec-flex-interval-ether-s {
                description
                  "port current performance data";
                list macsec-flex-interval-ether {
                  key "number";
                  description
                    "port flex-sec ether performance data";
                  leaf number {
                    type uint32;
                    description
                      "channel number";
                  }
                  uses PM-ETHERNET-PARAS;
                }
              }
              container macsec-flex-interval-secytxes {
                description
                  "port current performance data";
                list macsec-flex-interval-secytx {
                  key "number";
                  description
                    "port flex-sec secy-tx performance data";
                  leaf number {
                    type uint32;
                    description
                      "channel number";
                  }
                  uses PM-SECY-TX-PARAS;
                }
              }
            }
            container macsec-hour24 {
              description
                "port current performance data";
              container macsec-hour24-ether-s {
                description
                  "port current performance data";
                list macsec-hour24-ether {
                  key "number";
                  description
                    "port 24 hour ether performance data";
                  leaf number {
                    type uint32;
                    description
                      "channel number";
                  }
                  uses PM-ETHERNET-PARAS;
                }
              }
              container macsec-hour24secyifs {
                description
                  "port current performance data";
                list macsec-hour24secyif {
                  key "number";
                  description
                    "port 24 hour secy-if performance data";
                  leaf number {
                    type uint32;
                    description
                      "channel number";
                  }
                  uses PM-SECY-IF-PARAS;
                }
              }
              container macsec-hour24secyrxes {
                description
                  "port current performance data";
                list macsec-hour24secyrx {
                  key "number";
                  description
                    "port 24 hour secy-rx performance data";
                  leaf number {
                    type uint32;
                    description
                      "channel number";
                  }
                  uses PM-SECY-RX-PARAS;
                }
              }
              container macsec-hour24secytxes {
                description
                  "port current performance data";
                list macsec-hour24secytx {
                  key "number";
                  description
                    "port 24 hour secy-tx performance data";
                  leaf number {
                    type uint32;
                    description
                      "channel number";
                  }
                  uses PM-SECY-TX-PARAS;
                }
              }
            }
          }
          leaf name {
            type xr:Interface-name;
            description
              "Port name";
          }
        }
      }
    }
    container ho-vc {
      description
        "HO_VC controller performance data";
      container ho-vc-ports {
        description
          "Port performance data";
        list ho-vc-port {
          key "name";
          description
            "Port performance data";
          container ho-vc-current {
            description
              "port current performance data";
            container ho-vc-hour24 {
              description
                "port current performance data";
              container ho-vc-hour24-paths {
                description
                  "port current performance data";
                list ho-vc-hour24-path {
                  key "number";
                  description
                    "port 24 hour Path performance data";
                  leaf number {
                    type uint32;
                    description
                      "channel number";
                  }
                  uses PM-HO-VC-PARAS;
                }
              }
            }
            container ho-vc-minute15 {
              description
                "port current performance data";
              container ho-vc-minute15-paths {
                description
                  "port current performance data";
                list ho-vc-minute15-path {
                  key "number";
                  description
                    "port 15-minute Path performance data";
                  leaf number {
                    type uint32;
                    description
                      "channel number";
                  }
                  uses PM-HO-VC-PARAS;
                }
              }
            }
          }
          leaf name {
            type xr:Interface-name;
            description
              "Port name";
          }
        }
      }
    }
    container fibre-channel {
      description
        "Fibre Channel controller performance data";
      container fc-ports {
        description
          "Port performance data";
        list fc-port {
          key "name";
          description
            "Port performance data";
          container fc-current {
            description
              "FC controller current performance data";
            container fc-minute15 {
              description
                "FC controller current 15 minute performance
                 data";
              container fc-minute15fecs {
                description
                  "FC controller 15 minute FEC layer current
                   performance data";
                list fc-minute15fec {
                  key "slot-number";
                  description
                    "FC controller 15 minute FEC layer current
                     performance data";
                  leaf slot-number {
                    type uint32;
                    description
                      "interval slot number";
                  }
                  uses PM-FEC-PARAS;
                }
              }
              container minute15fcs {
                description
                  "FC controller 15 minute current FC layer
                   performance data";
                list minute15fc {
                  key "slot-number";
                  description
                    "FC controller 15 minute current FC layer
                     performance data";
                  leaf slot-number {
                    type uint32;
                    description
                      "interval slot number";
                  }
                  uses PM-FC-PARAS;
                }
              }
              container fc-minute15prbses {
                description
                  "FC controller 15 minute PRBS layer current
                   performance data";
                list fc-minute15prbs {
                  key "number";
                  description
                    "FC controller 15 minute PRBS layer current
                     performance data";
                  leaf number {
                    type uint32;
                    description
                      "channel number";
                  }
                  uses PM-PRBS-PARAS;
                }
              }
              container fc-minute15pcses {
                description
                  "FC controller 15 minute PCS layer current
                   performance data";
                list fc-minute15pcs {
                  key "slot-number";
                  description
                    "FC controller 15 minute PCS layer current
                     performance data";
                  leaf slot-number {
                    type uint32;
                    description
                      "interval slot number";
                  }
                  uses PM-PCS-PARAS;
                }
              }
            }
            container fc-second30 {
              description
                "FC controller current 30 second performance
                 data";
              container fc-second30fecs {
                description
                  "FC controller 30 second FEC layer current
                   performance data";
                list fc-second30fec {
                  key "slot-number";
                  description
                    "FC controller 30 second FEC layer current
                     performance data";
                  leaf slot-number {
                    type uint32;
                    description
                      "interval slot number";
                  }
                  uses PM-FEC-PARAS;
                }
              }
              container second30fcs {
                description
                  "FC controller 30 second current FC layer
                   performance data";
                list second30fc {
                  key "slot-number";
                  description
                    "FC controller 30 second current FC layer
                     performance data";
                  leaf slot-number {
                    type uint32;
                    description
                      "interval slot number";
                  }
                  uses PM-FC-PARAS;
                }
              }
              container fc-second30prbses {
                description
                  "FC controller 30 second PRBS layer current
                   performance data";
                list fc-second30prbs {
                  key "number";
                  description
                    "FC controller 30 second PRBS layer current
                     performance data";
                  leaf number {
                    type uint32;
                    description
                      "channel number";
                  }
                  uses PM-PRBS-PARAS;
                }
              }
              container fc-second30pcses {
                description
                  "FC controller 30 second PCS layer current
                   performance data";
                list fc-second30pcs {
                  key "slot-number";
                  description
                    "FC controller 30 second PCS layer current
                     performance data";
                  leaf slot-number {
                    type uint32;
                    description
                      "interval slot number";
                  }
                  uses PM-PCS-PARAS;
                }
              }
            }
            container fc-flex-interval {
              description
                "FC controller flex-bin current performance
                 data";
              container fc-flex-interval-pcses {
                description
                  "FC controller flex-bin PCS layer current
                   performance data";
                list fc-flex-interval-pcs {
                  key "slot-number";
                  description
                    "FC controller flex-bin PCS layer current
                     performance data";
                  leaf slot-number {
                    type uint32;
                    description
                      "interval slot number";
                  }
                  uses PM-PCS-PARAS;
                }
              }
              container fc-flex-interval-fcs {
                description
                  "FC controller flex-bin FC layer current
                   performance data";
                list fc-flex-interval-fc {
                  key "number";
                  description
                    "FC controller flex-bin FC layer current
                     performance data";
                  leaf number {
                    type uint32;
                    description
                      "channel number";
                  }
                  uses PM-FC-PARAS;
                }
              }
              container fc-flex-interval-fecs {
                description
                  "FC controller flex-bin FEC layer current
                   performance data";
                list fc-flex-interval-fec {
                  key "slot-number";
                  description
                    "FC controller flex-bin FEC layer current
                     performance data";
                  leaf slot-number {
                    type uint32;
                    description
                      "interval slot number";
                  }
                  uses PM-FEC-PARAS;
                }
              }
              container fc-flex-interval-prbses {
                description
                  "FC controller flex-bin PRBS layer current
                   performance data";
                list fc-flex-interval-prbs {
                  key "number";
                  description
                    "FC controller flex-bin PRBS layer current
                     performance data";
                  leaf number {
                    type uint32;
                    description
                      "channel number";
                  }
                  uses PM-PRBS-PARAS;
                }
              }
            }
            container fc-hour24 {
              description
                "FC controller current 24 hour performance
                 data";
              container fc-hour24prbses {
                description
                  "FC controller 24 hour PRBS layer current
                   performance data";
                list fc-hour24prbs {
                  key "number";
                  description
                    "FC controller 24 hour PRBS layer current
                     performance data";
                  leaf number {
                    type uint32;
                    description
                      "channel number";
                  }
                  uses PM-PRBS-PARAS;
                }
              }
              container fc-hour24fcs {
                description
                  "FC controller 24 hour FC layer current
                   performance data";
                list fc-hour24fc {
                  key "number";
                  description
                    "FC controller 24 hour FC layer current
                     performance data";
                  leaf number {
                    type uint32;
                    description
                      "channel number";
                  }
                  uses PM-FC-PARAS;
                }
              }
              container fc-hour24pcses {
                description
                  "FC controller 24 hour PCS layer current
                   performance data";
                list fc-hour24pcs {
                  key "number";
                  description
                    "FC controller 24 hour PCS layer current
                     performance data";
                  leaf number {
                    type uint32;
                    description
                      "channel number";
                  }
                  uses PM-PCS-PARAS;
                }
              }
              container fc-hour24fecs {
                description
                  "FC controller 24 hour FEC layer current
                   performance data";
                list fc-hour24fec {
                  key "number";
                  description
                    "FC controller 24 hour FEC layer current
                     performance data";
                  leaf number {
                    type uint32;
                    description
                      "channel number";
                  }
                  uses PM-FEC-PARAS;
                }
              }
            }
          }
          container fc-prev {
            description
              "FC controller previous performance data";
            container fc-prev-flex-interval {
              description
                "FC controller flex-bin previous performance
                 data";
              container fc-prev-flex-interval-fcs {
                description
                  "FC controller flex-bin previous FC layer
                   performance data";
                list fc-prev-flex-interval-fc {
                  key "number";
                  description
                    "FC controller flex-bin previous FC layer
                     performance data";
                  leaf number {
                    type uint32;
                    description
                      "channel number";
                  }
                  uses PM-FC-PARAS;
                }
              }
              container fc-prev-flex-interval-prbses {
                description
                  "FC controller flex-bin PRBS layer previous
                   performance data";
                list fc-prev-flex-interval-prbs {
                  key "number";
                  description
                    "FC controller flex-bin PRBS layer previous
                     performance data";
                  leaf number {
                    type uint32;
                    description
                      "channel number";
                  }
                  uses PM-PRBS-PARAS;
                }
              }
              container fc-prev-flex-interval-pcses {
                description
                  "FC controller flex-bin PCS layer previous
                   performance data";
                list fc-prev-flex-interval-pcs {
                  key "slot-number";
                  description
                    "FC controller flex-bin PCS layer previous
                     performance data";
                  leaf slot-number {
                    type uint32;
                    description
                      "interval slot number";
                  }
                  uses PM-PCS-PARAS;
                }
              }
              container fc-prev-flex-interval-fecs {
                description
                  "FC controller flex-bin FEC layer previous
                   performance data";
                list fc-prev-flex-interval-fec {
                  key "slot-number";
                  description
                    "FC controller flex-bin FEC layer previous
                     performance data";
                  leaf slot-number {
                    type uint32;
                    description
                      "interval slot number";
                  }
                  uses PM-FEC-PARAS;
                }
              }
            }
          }
          leaf name {
            type xr:Interface-name;
            description
              "Port name";
          }
        }
      }
    }
    container odu {
      description
        "ODU controller performance data";
      container odu-ports {
        description
          "Port performance data";
        list odu-port {
          key "name";
          description
            "Port performance data";
          container odu-prev {
            description
              "port prev performance data";
            container odu-prev-flex-interval {
              description
                "port prev performance data";
              container odu-prev-flex-interval-otns {
                description
                  "port prev performance data";
                list odu-prev-flex-interval-otn {
                  key "number";
                  description
                    "port flex-sec otn performance data";
                  leaf number {
                    type uint32;
                    description
                      "channel number";
                  }
                  uses PM-OTN-PARAS;
                }
              }
              container odu-prev-flex-interval-prbses {
                description
                  "port prev performance data";
                list odu-prev-flex-interval-prbs {
                  key "number";
                  description
                    "port flex-sec prbs performance data";
                  leaf number {
                    type uint32;
                    description
                      "channel number";
                  }
                  uses PM-PRBS-PARAS;
                }
              }
              container odu-prev-flex-interval-otn-all-table {
                description
                  "port flex-sec otn all channels performance
                   data";
                uses PM-OTN-ALL-CHANS;
              }
              container odu-prev-flex-interval-otnsecs {
                description
                  "flex-sec odu performance data";
                list odu-prev-flex-interval-otnsec {
                  key "number";
                  description
                    "otnsec flex-sec performance data";
                  leaf number {
                    type uint32;
                    description
                      "channel number";
                  }
                  uses PM-OTNSEC-PARAS;
                }
              }
              container odu-prev-flex-interval-gfps {
                description
                  "port prev performance data";
                list odu-prev-flex-interval-gfp {
                  key "number";
                  description
                    "port flex-sec otn performance data";
                  leaf number {
                    type uint32;
                    description
                      "channel number";
                  }
                  uses PM-GFP-PARAS;
                }
              }
            }
          }
          container odu-current {
            description
              "port current performance data";
            container odu-minute15 {
              description
                "port current performance data";
              container odu-minute15gfps {
                description
                  "port current performance data";
                list odu-minute15gfp {
                  key "number";
                  description
                    "port 15-minute otn performance data";
                  leaf number {
                    type uint32;
                    description
                      "channel number";
                  }
                  uses PM-GFP-PARAS;
                }
              }
              container odu-minute15prbses {
                description
                  "port current performance data";
                list odu-minute15prbs {
                  key "number";
                  description
                    "port 15-minute prbs performance data";
                  leaf number {
                    type uint32;
                    description
                      "channel number";
                  }
                  uses PM-PRBS-PARAS;
                }
              }
              container odu-minute15otnsecs {
                description
                  "15-min odu performance data";
                list odu-minute15otnsec {
                  key "number";
                  description
                    "otnsec 15-min performance data";
                  leaf number {
                    type uint32;
                    description
                      "channel number";
                  }
                  uses PM-OTNSEC-PARAS;
                }
              }
              container odu-minute15otns {
                description
                  "port current performance data";
                list odu-minute15otn {
                  key "number";
                  description
                    "port 15-minute otn performance data";
                  leaf number {
                    type uint32;
                    description
                      "channel number";
                  }
                  uses PM-OTN-PARAS;
                }
              }
            }
            container odu-flex-interval {
              description
                "port current performance data";
              container odu-flex-interval-prbses {
                description
                  "port current performance data";
                list odu-flex-interval-prbs {
                  key "number";
                  description
                    "port flex-sec prbs performance data";
                  leaf number {
                    type uint32;
                    description
                      "channel number";
                  }
                  uses PM-PRBS-PARAS;
                }
              }
              container odu-flex-interval-gfps {
                description
                  "port current performance data";
                list odu-flex-interval-gfp {
                  key "number";
                  description
                    "port flex-sec otn performance data";
                  leaf number {
                    type uint32;
                    description
                      "channel number";
                  }
                  uses PM-GFP-PARAS;
                }
              }
              container odu-flex-interval-otns {
                description
                  "port current performance data";
                list odu-flex-interval-otn {
                  key "number";
                  description
                    "port flex-sec otn performance data";
                  leaf number {
                    type uint32;
                    description
                      "channel number";
                  }
                  uses PM-OTN-PARAS;
                }
              }
              container odu-flex-interval-otnsecs {
                description
                  "flex-sec odu performance data";
                list odu-flex-interval-otnsec {
                  key "number";
                  description
                    "otnsec flexi-sec performance data";
                  leaf number {
                    type uint32;
                    description
                      "channel number";
                  }
                  uses PM-OTNSEC-PARAS;
                }
              }
            }
            container odu-second30 {
              description
                "port current performance data";
              container odu-second30prbses {
                description
                  "30-sec odu performance data";
                list odu-second30prbs {
                  key "number";
                  description
                    "PRBS 30-sec performance data";
                  leaf number {
                    type uint32;
                    description
                      "channel number";
                  }
                  uses PM-PRBS-PARAS;
                }
              }
              container odu-second30otns {
                description
                  "30-sec odu performance data";
                list odu-second30otn {
                  key "number";
                  description
                    "port 30-sec otn performance data";
                  leaf number {
                    type uint32;
                    description
                      "channel number";
                  }
                  uses PM-OTN-PARAS;
                }
              }
              container odu-second30otnsecs {
                description
                  "30-sec odu performance data";
                list odu-second30otnsec {
                  key "number";
                  description
                    "otnsec 30-sec performance data";
                  leaf number {
                    type uint32;
                    description
                      "channel number";
                  }
                  uses PM-OTNSEC-PARAS;
                }
              }
              container odu-second30gfps {
                description
                  "30-sec odu performance data";
                list odu-second30gfp {
                  key "number";
                  description
                    "GFP 30-sec performance data";
                  leaf number {
                    type uint32;
                    description
                      "channel number";
                  }
                  uses PM-GFP-PARAS;
                }
              }
            }
            container odu-hour24 {
              description
                "port current performance data";
              container odu-hour24prbses {
                description
                  "port 24 hour performance data";
                list odu-hour24prbs {
                  key "number";
                  description
                    "port 24 hour otn performance data";
                  leaf number {
                    type uint32;
                    description
                      "channel number";
                  }
                  uses PM-PRBS-PARAS;
                }
              }
              container odu-hour24otnsecs {
                description
                  "24-hr odu performance data";
                list odu-hour24otnsec {
                  key "number";
                  description
                    "otnsec 24-hr performance data";
                  leaf number {
                    type uint32;
                    description
                      "channel number";
                  }
                  uses PM-OTNSEC-PARAS;
                }
              }
              container odu-hour24gfps {
                description
                  "port 24 hour performance data";
                list odu-hour24gfp {
                  key "number";
                  description
                    "port 24 hour otn performance data";
                  leaf number {
                    type uint32;
                    description
                      "channel number";
                  }
                  uses PM-GFP-PARAS;
                }
              }
              container odu-hour24otns {
                description
                  "port 24 hour performance data";
                list odu-hour24otn {
                  key "number";
                  description
                    "port 24 hour otn performance data";
                  leaf number {
                    type uint32;
                    description
                      "channel number";
                  }
                  uses PM-OTN-PARAS;
                }
              }
            }
          }
          leaf name {
            type xr:Interface-name;
            description
              "Port name";
          }
        }
      }
    }
    container otu {
      description
        "OTU controller performance data";
      container otu-ports {
        description
          "Port performance data";
        list otu-port {
          key "name";
          description
            "Port performance data";
          container otu-prev {
            description
              "port prev performance data";
            container otu-prev-flex-interval {
              description
                "port prev performance data";
              container otu-prev-flex-interval-fecs {
                description
                  "port prev performance data";
                list otu-prev-flex-interval-fec {
                  key "number";
                  description
                    "port flex-sec fec performance data";
                  leaf number {
                    type uint32;
                    description
                      "channel number";
                  }
                  uses PM-FEC-PARAS;
                }
              }
              container otu-prev-flex-interval-prbses {
                description
                  "port current performance data";
                list otu-prev-flex-interval-prbs {
                  key "number";
                  description
                    "port flex-sec prbs performance data";
                  leaf number {
                    type uint32;
                    description
                      "channel number";
                  }
                  uses PM-PRBS-PARAS;
                }
              }
              container otu-prev-flex-interval-otns {
                description
                  "port prev performance data";
                list otu-prev-flex-interval-otn {
                  key "number";
                  description
                    "port flex-sec otn performance data";
                  leaf number {
                    type uint32;
                    description
                      "channel number";
                  }
                  uses PM-OTN-PARAS;
                }
              }
            }
          }
          container otu-current {
            description
              "port current performance data";
            container otu-minute15 {
              description
                "port current performance data";
              container otu-minute15fecs {
                description
                  "port current performance data";
                list otu-minute15fec {
                  key "number";
                  description
                    "port 15-minute fec performance data";
                  leaf number {
                    type uint32;
                    description
                      "channel number";
                  }
                  uses PM-FEC-PARAS;
                }
              }
              container otu-minute15otns {
                description
                  "port current performance data";
                list otu-minute15otn {
                  key "number";
                  description
                    "port 15-minute otn performance data";
                  leaf number {
                    type uint32;
                    description
                      "channel number";
                  }
                  uses PM-OTN-PARAS;
                }
              }
              container otu-minute15prbses {
                description
                  "port current performance data";
                list otu-minute15prbs {
                  key "number";
                  description
                    "port 15-minute prbs performance data";
                  leaf number {
                    type uint32;
                    description
                      "channel number";
                  }
                  uses PM-PRBS-PARAS;
                }
              }
            }
            container otu-second30 {
              description
                "port current performance data";
              container otu-second30fecs {
                description
                  "port current performance data";
                list otu-second30fec {
                  key "number";
                  description
                    "port 30-sec fec performance data";
                  leaf number {
                    type uint32;
                    description
                      "channel number";
                  }
                  uses PM-FEC-PARAS;
                }
              }
              container otu-second30otns {
                description
                  "port current performance data";
                list otu-second30otn {
                  key "number";
                  description
                    "port 30-sec otn performance data";
                  leaf number {
                    type uint32;
                    description
                      "channel number";
                  }
                  uses PM-OTN-PARAS;
                }
              }
              container otu-second30prbses {
                description
                  "prbs 30-sec performance data";
                list otu-second30prbs {
                  key "number";
                  description
                    "prbs 30-sec otn performance data";
                  leaf number {
                    type uint32;
                    description
                      "channel number";
                  }
                  uses PM-PRBS-PARAS;
                }
              }
            }
            container otu-flex-interval {
              description
                "port current performance data";
              container otu-flex-interval-prbses {
                description
                  "port current performance data";
                list otu-flex-interval-prbs {
                  key "number";
                  description
                    "port flex-sec prbs performance data";
                  leaf number {
                    type uint32;
                    description
                      "channel number";
                  }
                  uses PM-PRBS-PARAS;
                }
              }
              container otu-flex-interval-fecs {
                description
                  "port current performance data";
                list otu-flex-interval-fec {
                  key "number";
                  description
                    "port flex-sec fec performance data";
                  leaf number {
                    type uint32;
                    description
                      "channel number";
                  }
                  uses PM-FEC-PARAS;
                }
              }
              container otu-flex-interval-otns {
                description
                  "port current performance data";
                list otu-flex-interval-otn {
                  key "number";
                  description
                    "port flex-sec otn performance data";
                  leaf number {
                    type uint32;
                    description
                      "channel number";
                  }
                  uses PM-OTN-PARAS;
                }
              }
            }
            container otu-hour24 {
              description
                "port current performance data";
              container otu-hour24fecs {
                description
                  "port current performance data";
                list otu-hour24fec {
                  key "number";
                  description
                    "port 24 hour fec performance data";
                  leaf number {
                    type uint32;
                    description
                      "channel number";
                  }
                  uses PM-FEC-PARAS;
                }
              }
              container otu-hour24prbses {
                description
                  "port 24 hour performance data";
                list otu-hour24prbs {
                  key "number";
                  description
                    "port 24 hour otn performance data";
                  leaf number {
                    type uint32;
                    description
                      "channel number";
                  }
                  uses PM-PRBS-PARAS;
                }
              }
              container otu-hour24otns {
                description
                  "port 24 hour performance data";
                list otu-hour24otn {
                  key "number";
                  description
                    "port 24 hour otn performance data";
                  leaf number {
                    type uint32;
                    description
                      "channel number";
                  }
                  uses PM-OTN-PARAS;
                }
              }
            }
          }
          leaf name {
            type xr:Interface-name;
            description
              "Port name";
          }
        }
      }
    }
    container stm {
      description
        "STM controller performance data";
      container stm-ports {
        description
          "Port performance data";
        list stm-port {
          key "name";
          description
            "Port performance data";
          container stm-current {
            description
              "port current performance data";
            container stm-hour24 {
              description
                "port current performance data";
              container stm-hour24prbses {
                description
                  "STM controller 24 hour PRBS layer current
                   performance data";
                list stm-hour24prbs {
                  key "number";
                  description
                    "STM controller 24 hour PRBS layer current
                     performance data";
                  leaf number {
                    type uint32;
                    description
                      "channel number";
                  }
                  uses PM-PRBS-PARAS;
                }
              }
              container stm-hour24stms {
                description
                  "port current performance data";
                list stm-hour24stm {
                  key "number";
                  description
                    "port 24 hour stm performance data";
                  leaf number {
                    type uint32;
                    description
                      "channel number";
                  }
                  uses PM-STM-PARAS;
                }
              }
            }
            container stm-flex-interval {
              description
                "STM controller flex-bin current performance
                 data";
              container stm-flex-interval-prbses {
                description
                  "STM controller flex-bin PRBS layer current
                   performance data";
                list stm-flex-interval-prbs {
                  key "number";
                  description
                    "STM controller flex-bin PRBS layer current
                     performance data";
                  leaf number {
                    type uint32;
                    description
                      "channel number";
                  }
                  uses PM-PRBS-PARAS;
                }
              }
            }
            container stm-minute15 {
              description
                "port current performance data";
              container stm-minute15prbses {
                description
                  "STM controller 15 minute PRBS layer current
                   performance data";
                list stm-minute15prbs {
                  key "number";
                  description
                    "STM controller 15 minute PRBS layer
                     current performance data";
                  leaf number {
                    type uint32;
                    description
                      "channel number";
                  }
                  uses PM-PRBS-PARAS;
                }
              }
              container stm-minute15stms {
                description
                  "port current performance data";
                list stm-minute15stm {
                  key "number";
                  description
                    "port 15-minute stm performance data";
                  leaf number {
                    type uint32;
                    description
                      "channel number";
                  }
                  uses PM-STM-PARAS;
                }
              }
            }
            container stm-second30 {
              description
                "port current performance data";
              container stm-second30prbses {
                description
                  "STM controller 30 second PRBS layer current
                   performance data";
                list stm-second30prbs {
                  key "number";
                  description
                    "STM controller 30 second PRBS layer
                     current performance data";
                  leaf number {
                    type uint32;
                    description
                      "channel number";
                  }
                  uses PM-PRBS-PARAS;
                }
              }
            }
          }
          container stm-prev {
            description
              "STM controller previous performance data";
            container stm-prev-flex-interval {
              description
                "STM controller flex-bin previous performance
                 data";
              container stm-prev-flex-interval-prbses {
                description
                  "STM controller flex-bin PRBS layer previous
                   performance data";
                list stm-prev-flex-interval-prbs {
                  key "number";
                  description
                    "STM controller flex-bin PRBS layer
                     previous performance data";
                  leaf number {
                    type uint32;
                    description
                      "channel number";
                  }
                  uses PM-PRBS-PARAS;
                }
              }
            }
          }
          leaf name {
            type xr:Interface-name;
            description
              "Port name";
          }
        }
      }
    }
    container sonet {
      description
        "SONET controller performance data";
      container sonet-ports {
        description
          "Port performance data";
        list sonet-port {
          key "name";
          description
            "Port performance data";
          container sonet-current {
            description
              "port current performance data";
            container sonet-minute15 {
              description
                "port current performance data";
              container sonet-minute15-paths {
                description
                  "port current performance data";
                list sonet-minute15-path {
                  key "number";
                  description
                    "port 15-minute Path performance data";
                  leaf number {
                    type uint32;
                    description
                      "channel number";
                  }
                  uses PM-SONET-PATH-PARAS;
                }
              }
              container sonet-minute15ocns {
                description
                  "port current performance data";
                list sonet-minute15ocn {
                  key "number";
                  description
                    "port 15-minute ocn performance data";
                  leaf number {
                    type uint32;
                    description
                      "channel number";
                  }
                  uses PM-SONET-PARAS;
                }
              }
            }
            container sonet-hour24 {
              description
                "port current performance data";
              container sonet-hour24ocns {
                description
                  "port current performance data";
                list sonet-hour24ocn {
                  key "number";
                  description
                    "port 24 hour ocn performance data";
                  leaf number {
                    type uint32;
                    description
                      "channel number";
                  }
                  uses PM-SONET-PARAS;
                }
              }
              container sonet-hour24-paths {
                description
                  "port current performance data";
                list sonet-hour24-path {
                  key "number";
                  description
                    "port 24 hour Path performance data";
                  leaf number {
                    type uint32;
                    description
                      "channel number";
                  }
                  uses PM-SONET-PATH-PARAS;
                }
              }
            }
          }
          leaf name {
            type xr:Interface-name;
            description
              "Port name";
          }
        }
      }
    }
    container optics {
      description
        "OPTICS controller performance data";
      container optics-ports {
        description
          "Port performance data";
        list optics-port {
          key "name";
          description
            "Port performance data";
          container optics-current {
            description
              "port current performance data";
            container optics-flex-interval {
              description
                "port current performance data";
              container optics-flex-interval-fecs {
                description
                  "port current performance data";
                list optics-flex-interval-fec {
                  key "number";
                  description
                    "port variable-second fec performance data";
                  leaf number {
                    type uint32;
                    description
                      "channel number";
                  }
                  uses PM-FEC-PARAS;
                }
              }
              container optics-flex-interval-optics {
                description
                  "port current performance data";
                list optics-flex-interval-optic {
                  key "number";
                  description
                    "port variable-second optics performance
                     data";
                  leaf number {
                    type uint32;
                    description
                      "channel number";
                  }
                  uses PM-OPTICS-PARAS;
                }
              }
            }
            container optics-hour24 {
              description
                "port current performance data";
              container optics-hour24-optics {
                description
                  "port 24 hour performance data";
                list optics-hour24-optic {
                  key "number";
                  description
                    "port 24 hour optics performance data";
                  leaf number {
                    type uint32;
                    description
                      "channel number";
                  }
                  uses PM-OPTICS-PARAS;
                }
              }
              container optics-hour24fecs {
                description
                  "port current performance data";
                list optics-hour24fec {
                  key "number";
                  description
                    "port 24 hour fec performance data";
                  leaf number {
                    type uint32;
                    description
                      "channel number";
                  }
                  uses PM-FEC-PARAS;
                }
              }
            }
            container optics-minute15 {
              description
                "port current performance data";
              container optics-minute15-optics {
                description
                  "port current performance data";
                list optics-minute15-optic {
                  key "number";
                  description
                    "port 15-minute optics performance data";
                  leaf number {
                    type uint32;
                    description
                      "channel number";
                  }
                  uses PM-OPTICS-PARAS;
                }
              }
              container optics-minute15fecs {
                description
                  "port current performance data";
                list optics-minute15fec {
                  key "number";
                  description
                    "port 15-minute fec performance data";
                  leaf number {
                    type uint32;
                    description
                      "channel number";
                  }
                  uses PM-FEC-PARAS;
                }
              }
            }
            container optics-second30 {
              description
                "port current performance data";
              container optics-second30fecs {
                description
                  "port current performance data";
                list optics-second30fec {
                  key "number";
                  description
                    "port 30-second fec performance data";
                  leaf number {
                    type uint32;
                    description
                      "channel number";
                  }
                  uses PM-FEC-PARAS;
                }
              }
              container optics-second30-optics {
                description
                  "port current performance data";
                list optics-second30-optic {
                  key "number";
                  description
                    "port 30-second optics performance data";
                  leaf number {
                    type uint32;
                    description
                      "channel number";
                  }
                  uses PM-OPTICS-PARAS;
                }
              }
            }
          }
          container optics-prev {
            description
              "port current performance data";
            container optics-prev-flex-interval {
              description
                "port prev performance data";
              container optics-prev-flex-interval-fecs {
                description
                  "port prev performance data";
                list optics-prev-flex-interval-fec {
                  key "number";
                  description
                    "port variable-second fec performance data";
                  leaf number {
                    type uint32;
                    description
                      "channel number";
                  }
                  uses PM-FEC-PARAS;
                }
              }
              container optics-prev-flex-interval-optics {
                description
                  "port prev performance data";
                list optics-prev-flex-interval-optic {
                  key "number";
                  description
                    "port variable-second optics performance
                     data";
                  leaf number {
                    type uint32;
                    description
                      "channel number";
                  }
                  uses PM-OPTICS-PARAS;
                }
              }
            }
          }
          leaf name {
            type xr:Interface-name;
            description
              "Port name";
          }
        }
      }
    }
    container sts {
      description
        "STS controller performance data";
      container sts-ports {
        description
          "Port performance data";
        list sts-port {
          key "name";
          description
            "Port performance data";
          container sts-current {
            description
              "port current performance data";
            container sts-minute15 {
              description
                "port current performance data";
              container sts-minute15-paths {
                description
                  "port current performance data";
                list sts-minute15-path {
                  key "number";
                  description
                    "port 15-minute Path performance data";
                  leaf number {
                    type uint32;
                    description
                      "channel number";
                  }
                  uses PM-SONET-PATH-PARAS;
                }
              }
            }
            container sts-hour24 {
              description
                "port current performance data";
              container sts-hour24-paths {
                description
                  "port current performance data";
                list sts-hour24-path {
                  key "number";
                  description
                    "port 24 hour Path performance data";
                  leaf number {
                    type uint32;
                    description
                      "channel number";
                  }
                  uses PM-SONET-PATH-PARAS;
                }
              }
            }
          }
          leaf name {
            type xr:Interface-name;
            description
              "Port name";
          }
        }
      }
    }
    container cem {
      description
        "CEM performance data";
      container cem-ports {
        description
          "Port performance data";
        list cem-port {
          key "name";
          description
            "Port performance data";
          container cem-current {
            description
              "CEM controller current performance data";
            container cem-minute15 {
              description
                "CEM controller current 15 minute performance
                 data";
              container minute15cems {
                description
                  "CEM controller 15 minute current CEM layer
                   performance data";
                list minute15cem {
                  key "slot-number";
                  description
                    "CEM controller 15 minute current CEM layer
                     performance data";
                  leaf slot-number {
                    type uint32;
                    description
                      "interval slot number";
                  }
                  uses PM-CEM-PARAS;
                }
              }
            }
            container cem-second30 {
              description
                "CEM controller current 30 second performance
                 data";
              container second30cems {
                description
                  "CEM controller 30 second current CEM layer
                   performance data";
                list second30cem {
                  key "slot-number";
                  description
                    "CEM controller 30 second current CEM layer
                     performance data";
                  leaf slot-number {
                    type uint32;
                    description
                      "interval slot number";
                  }
                  uses PM-CEM-PARAS;
                }
              }
            }
            container cem-hour24 {
              description
                "CEM controller current 24 hour performance
                 data";
              container cem-hour24cems {
                description
                  "CEM controller 24 hour CEM layer current
                   performance data";
                list cem-hour24cem {
                  key "number";
                  description
                    "CEM controller 24 hour CEM layer current
                     performance data";
                  leaf number {
                    type uint32;
                    description
                      "channel number";
                  }
                  uses PM-CEM-PARAS;
                }
              }
            }
            container cem-flex-interval {
              description
                "CEM controller flex-bin current performance
                 data";
              container cem-flex-interval-cems {
                description
                  "CEM controller flex-bin CEM layer current
                   performance data";
                list cem-flex-interval-cem {
                  key "number";
                  description
                    "CEM controller flex-bin CEM layer current
                     performance data";
                  leaf number {
                    type uint32;
                    description
                      "channel number";
                  }
                  uses PM-CEM-PARAS;
                }
              }
            }
          }
          container cem-prev {
            description
              "CEM controller previous performance data";
            container cem-prev-flex-interval {
              description
                "CEM controller flex-bin previous performance
                 data";
              container cem-prev-flex-interval-cems {
                description
                  "CEM controller flex-bin previous CEM layer
                   performance data";
                list cem-prev-flex-interval-cem {
                  key "number";
                  description
                    "CEM controller flex-bin previous CEM layer
                     performance data";
                  leaf number {
                    type uint32;
                    description
                      "channel number";
                  }
                  uses PM-CEM-PARAS;
                }
              }
            }
          }
          leaf name {
            type xr:Interface-name;
            description
              "Port name";
          }
        }
      }
    }
    container dwdm {
      description
        "DWDM controller performance data";
      container dwdm-ports {
        description
          "Port performance data";
        list dwdm-port {
          key "name";
          description
            "Port performance data";
          container dwdm-current {
            description
              "port current performance data";
            container dwdm-minute15 {
              description
                "port current performance data";
              container dwdm-minute15fecs {
                description
                  "port current performance data";
                list dwdm-minute15fec {
                  key "number";
                  description
                    "port 15-minute fec performance data";
                  leaf number {
                    type uint32;
                    description
                      "channel number";
                  }
                  uses PM-FEC-PARAS;
                }
              }
              container dwdm-minute15-optics {
                description
                  "port current performance data";
                list dwdm-minute15-optic {
                  key "number";
                  description
                    "port 15-minute optics performance data";
                  leaf number {
                    type uint32;
                    description
                      "channel number";
                  }
                  uses PM-OPTICS-PARAS;
                }
              }
              container dwdm-minute15otns {
                description
                  "port current performance data";
                list dwdm-minute15otn {
                  key "number";
                  description
                    "port 15-minute otn performance data";
                  leaf number {
                    type uint32;
                    description
                      "channel number";
                  }
                  uses PM-OTN-PARAS;
                }
              }
            }
            container dwdm-hour24 {
              description
                "port current performance data";
              container dwdm-hour24-optics {
                description
                  "port 24 hour performance data";
                list dwdm-hour24-optic {
                  key "number";
                  description
                    "port 24 hour optics performance data";
                  leaf number {
                    type uint32;
                    description
                      "channel number";
                  }
                  uses PM-OPTICS-PARAS;
                }
              }
              container dwdm-hour24fecs {
                description
                  "port current performance data";
                list dwdm-hour24fec {
                  key "number";
                  description
                    "port 24 hour fec performance data";
                  leaf number {
                    type uint32;
                    description
                      "channel number";
                  }
                  uses PM-FEC-PARAS;
                }
              }
              container dwdm-hour24otns {
                description
                  "port 24 hour performance data";
                list dwdm-hour24otn {
                  key "number";
                  description
                    "port 24 hour otn performance data";
                  leaf number {
                    type uint32;
                    description
                      "channel number";
                  }
                  uses PM-OTN-PARAS;
                }
              }
            }
          }
          leaf name {
            type xr:Interface-name;
            description
              "Port name";
          }
        }
      }
    }
    container oc {
      description
        "OC controller performance data";
      container oc-ports {
        description
          "Port performance data";
        list oc-port {
          key "name";
          description
            "Port performance data";
          container oc-current {
            description
              "port current performance data";
            container oc-hour24 {
              description
                "port current performance data";
              container oc-hour24prbses {
                description
                  "OC controller 24 hour PRBS layer current
                   performance data";
                list oc-hour24prbs {
                  key "number";
                  description
                    "OC controller 24 hour PRBS layer current
                     performance data";
                  leaf number {
                    type uint32;
                    description
                      "channel number";
                  }
                  uses PM-PRBS-PARAS;
                }
              }
              container oc-hour24ocns {
                description
                  "port current performance data";
                list oc-hour24ocn {
                  key "number";
                  description
                    "port 24 hour ocn performance data";
                  leaf number {
                    type uint32;
                    description
                      "channel number";
                  }
                  uses PM-SONET-PARAS;
                }
              }
            }
            container oc-minute15 {
              description
                "port current performance data";
              container oc-minute15prbses {
                description
                  "OC controller 15 minute PRBS layer current
                   performance data";
                list oc-minute15prbs {
                  key "number";
                  description
                    "OC controller 15 minute PRBS layer current
                     performance data";
                  leaf number {
                    type uint32;
                    description
                      "channel number";
                  }
                  uses PM-PRBS-PARAS;
                }
              }
              container oc-minute15ocns {
                description
                  "port current performance data";
                list oc-minute15ocn {
                  key "number";
                  description
                    "port 15-minute ocn performance data";
                  leaf number {
                    type uint32;
                    description
                      "channel number";
                  }
                  uses PM-SONET-PARAS;
                }
              }
            }
            container oc-second30 {
              description
                "port current performance data";
              container oc-second30prbses {
                description
                  "OC controller 30 second PRBS layer current
                   performance data";
                list oc-second30prbs {
                  key "number";
                  description
                    "OC controller 30 second PRBS layer current
                     performance data";
                  leaf number {
                    type uint32;
                    description
                      "channel number";
                  }
                  uses PM-PRBS-PARAS;
                }
              }
            }
            container oc-flex-interval {
              description
                "OC controller flex-bin current performance
                 data";
              container oc-flex-interval-prbses {
                description
                  "OC controller flex-bin PRBS layer current
                   performance data";
                list oc-flex-interval-prbs {
                  key "number";
                  description
                    "OC controller flex-bin PRBS layer current
                     performance data";
                  leaf number {
                    type uint32;
                    description
                      "channel number";
                  }
                  uses PM-PRBS-PARAS;
                }
              }
            }
          }
          container oc-prev {
            description
              "OC controller previous performance data";
            container oc-prev-flex-interval {
              description
                "OC controller flex-bin previous performance
                 data";
              container oc-prev-flex-interval-prbses {
                description
                  "OC controller flex-bin PRBS layer previous
                   performance data";
                list oc-prev-flex-interval-prbs {
                  key "number";
                  description
                    "OC controller flex-bin PRBS layer previous
                     performance data";
                  leaf number {
                    type uint32;
                    description
                      "channel number";
                  }
                  uses PM-PRBS-PARAS;
                }
              }
            }
          }
          leaf name {
            type xr:Interface-name;
            description
              "Port name";
          }
        }
      }
    }
    container e1 {
      description
        "E1 controller performance data";
      container e1-ports {
        description
          "Port performance data";
        list e1-port {
          key "name";
          description
            "Port performance data";
          container e1-current {
            description
              "port current performance data";
            container e1-minute15 {
              description
                "port current performance data";
              container e1-minute15e1s {
                description
                  "port current performance data";
                list e1-minute15e1 {
                  key "number";
                  description
                    "port 15-minute e1 performance data";
                  leaf number {
                    type uint32;
                    description
                      "channel number";
                  }
                  uses PM-E1-PARAS;
                }
              }
            }
            container e1-hour24 {
              description
                "port current performance data";
              container e1-hour24e1s {
                description
                  "port current performance data";
                list e1-hour24e1 {
                  key "number";
                  description
                    "port 24 hour e1 performance data";
                  leaf number {
                    type uint32;
                    description
                      "channel number";
                  }
                  uses PM-E1-PARAS;
                }
              }
            }
          }
          leaf name {
            type xr:Interface-name;
            description
              "Port name";
          }
        }
      }
    }
    container ethernet {
      description
        "EHERNET controller performance data";
      container ethernet-ports {
        description
          "Port performance data";
        list ethernet-port {
          key "name";
          description
            "Port performance data";
          container ethernet-current {
            description
              "port current performance data";
            container ethernet-flex-interval {
              description
                "port current performance data";
              container ethernet-flex-interval-prbses {
                description
                  "Ethernet controller flex-bin PRBS layer
                   current performance data";
                list ethernet-flex-interval-prbs {
                  key "number";
                  description
                    "Ethernet controller flex-bin PRBS layer
                     current performance data";
                  leaf number {
                    type uint32;
                    description
                      "channel number";
                  }
                  uses PM-PRBS-PARAS;
                }
              }
              container ethernet-flex-interval-pcses {
                description
                  "ETHERNET port interval performance data";
                list ethernet-flex-interval-pcs {
                  key "slot-number";
                  description
                    "Ethernet port flex second pcs  performance
                     data";
                  leaf slot-number {
                    type uint32;
                    description
                      "interval slot number";
                  }
                  uses PM-PCS-PARAS;
                }
              }
              container ethernet-flex-interval-fecs {
                description
                  "port current performance data";
                list ethernet-flex-interval-fec {
                  key "number";
                  description
                    "port flex sec ethernet performance data";
                  leaf number {
                    type uint32;
                    description
                      "channel number";
                  }
                  uses PM-FEC-PARAS;
                }
              }
              container ethernet-flex-interval-ether-s {
                description
                  "port current performance data";
                list ethernet-flex-interval-ether {
                  key "number";
                  description
                    "port flex sec ethernet performance data";
                  leaf number {
                    type uint32;
                    description
                      "channel number";
                  }
                  uses PM-ETHERNET-PARAS;
                }
              }
            }
            container ethernet-second30 {
              description
                "port current performance data";
              container second30-fecs {
                description
                  "ETHERNET port interval performance data";
                list second30-fec {
                  key "slot-number";
                  description
                    "ETHERNET port 30 second fec performance
                     data";
                  leaf slot-number {
                    type uint32;
                    description
                      "interval slot number";
                  }
                  uses PM-FEC-PARAS;
                }
              }
              container second30pcses {
                description
                  "ETHERNET port interval performance data";
                list second30pcs {
                  key "slot-number";
                  description
                    "Ethernet port 30 second pcs  performance
                     data";
                  leaf slot-number {
                    type uint32;
                    description
                      "interval slot number";
                  }
                  uses PM-PCS-PARAS;
                }
              }
              container ethernet-second30prbses {
                description
                  "Ethernet controller 30 second PRBS layer
                   current performance data";
                list ethernet-second30prbs {
                  key "number";
                  description
                    "Ethernet controller 30 second PRBS layer
                     current performance data";
                  leaf number {
                    type uint32;
                    description
                      "channel number";
                  }
                  uses PM-PRBS-PARAS;
                }
              }
              container second30-ethers {
                description
                  "ETHERNET port interval performance data";
                list second30-ether {
                  key "slot-number";
                  description
                    "ETHERNET port 30 second ether performance
                     data";
                  leaf slot-number {
                    type uint32;
                    description
                      "interval slot number";
                  }
                  uses PM-ETHERNET-PARAS;
                }
              }
            }
            container ethernet-hour24 {
              description
                "port current performance data";
              container ethernet-hour24-ether-s {
                description
                  "port current performance data";
                list ethernet-hour24-ether {
                  key "number";
                  description
                    "port 24 hour ethernet performance data";
                  leaf number {
                    type uint32;
                    description
                      "channel number";
                  }
                  uses PM-ETHERNET-PARAS;
                }
              }
              container ethernet-hour24prbses {
                description
                  "Ethernet controller 24 hour PRBS layer
                   current performance data";
                list ethernet-hour24prbs {
                  key "number";
                  description
                    "Ethernet controller 24 hour PRBS layer
                     current performance data";
                  leaf number {
                    type uint32;
                    description
                      "channel number";
                  }
                  uses PM-PRBS-PARAS;
                }
              }
              container hour24pcses {
                description
                  "port current performance data";
                list hour24pcs {
                  key "number";
                  description
                    "Ethernet port 24 hour pcs performance data";
                  leaf number {
                    type uint32;
                    description
                      "channel number";
                  }
                  uses PM-PCS-PARAS;
                }
              }
              container ethernet-hour24fecs {
                description
                  "port current performance data";
                list ethernet-hour24fec {
                  key "number";
                  description
                    "port 24 hour ethernet performance data";
                  leaf number {
                    type uint32;
                    description
                      "channel number";
                  }
                  uses PM-FEC-PARAS;
                }
              }
            }
            container minute15 {
              description
                "port current performance data";
              container minute15-fecs {
                description
                  "ETHERNET port interval performance data";
                list minute15-fec {
                  key "slot-number";
                  description
                    "ETHERNET port 15-minute fec performance
                     data";
                  leaf slot-number {
                    type uint32;
                    description
                      "interval slot number";
                  }
                  uses PM-FEC-PARAS;
                }
              }
              container minute15pcses {
                description
                  "ETHERNET port interval performance data";
                list minute15pcs {
                  key "slot-number";
                  description
                    "ETHERNET port 15-minute pcs performance
                     data";
                  leaf slot-number {
                    type uint32;
                    description
                      "interval slot number";
                  }
                  uses PM-PCS-PARAS;
                }
              }
              container minute15-ethers {
                description
                  "ETHERNET port interval performance data";
                list minute15-ether {
                  key "slot-number";
                  description
                    "ETHERNET port 15-minute ether performance
                     data";
                  leaf slot-number {
                    type uint32;
                    description
                      "interval slot number";
                  }
                  uses PM-ETHERNET-PARAS;
                }
              }
              container ethernet-minute15prbses {
                description
                  "Ethernet controller 15 minute PRBS layer
                   current performance data";
                list ethernet-minute15prbs {
                  key "number";
                  description
                    "Ethernet controller 15 minute PRBS layer
                     current performance data";
                  leaf number {
                    type uint32;
                    description
                      "channel number";
                  }
                  uses PM-PRBS-PARAS;
                }
              }
            }
          }
          container ethernet-prev {
            description
              "port prev performance data";
            container ethernet-prev-flex-interval {
              description
                "port prev performance data";
              container ethernet-prev-flex-interval-prbses {
                description
                  "Ethernet controller flex-bin PRBS layer
                   previous performance data";
                list ethernet-prev-flex-interval-prbs {
                  key "number";
                  description
                    "Ethernet controller flex-bin PRBS layer
                     previous performance data";
                  leaf number {
                    type uint32;
                    description
                      "channel number";
                  }
                  uses PM-PRBS-PARAS;
                }
              }
              container ethernet-prev-flex-interval-ether-s {
                description
                  "port prev performance data";
                list ethernet-prev-flex-interval-ether {
                  key "number";
                  description
                    "port flex sec ethernet performance data";
                  leaf number {
                    type uint32;
                    description
                      "channel number";
                  }
                  uses PM-ETHERNET-PARAS;
                }
              }
              container ethernet-prev-flex-interval-pcses {
                description
                  "ETHERNET port interval performance data";
                list ethernet-prev-flex-interval-pcs {
                  key "slot-number";
                  description
                    "Ethernet port flex second pcs performance
                     data";
                  leaf slot-number {
                    type uint32;
                    description
                      "interval slot number";
                  }
                  uses PM-PCS-PARAS;
                }
              }
              container ethernet-prev-flex-interval-fecs {
                description
                  "port prev performance data";
                list ethernet-prev-flex-interval-fec {
                  key "number";
                  description
                    "port flex sec ethernet performance data";
                  leaf number {
                    type uint32;
                    description
                      "channel number";
                  }
                  uses PM-FEC-PARAS;
                }
              }
            }
          }
          leaf name {
            type xr:Interface-name;
            description
              "Port name";
          }
        }
      }
    }
  }
  container performance-management-history {
    config false;
    description
      "performace data";
    container global {
      description
        "global History performace data";
      container periodic {
        description
          "History performace data";
        container sonet-history {
          description
            "SONET controller History performance data";
          container sonet-port-histories {
            description
              "Port performance data";
            list sonet-port-history {
              key "name";
              description
                "Port performance data";
              container sonet-minute15-history {
                description
                  "port current performance data";
                container sonet-minute15ocn-histories {
                  description
                    "port current performance data";
                  list sonet-minute15ocn-history {
                    key "number";
                    description
                      "port 15-minute ocn performance data";
                    container sonet-minute15ocn-time-line-instances {
                      description
                        "port current performance data";
                      list sonet-minute15ocn-time-line-instance {
                        key "number";
                        description
                          "port 15-minute otn performance data";
                        leaf number {
                          type uint32 {
                            range "1..32";
                          }
                          description
                            "History Index number";
                        }
                        uses PM-SONET-PARAS;
                      }
                    }
                    leaf number {
                      type uint32;
                      description
                        "channel number";
                    }
                  }
                }
                container sonet-minute15-path-histories {
                  description
                    "port current performance data";
                  list sonet-minute15-path-history {
                    key "number";
                    description
                      "port 15-minute Path performance data";
                    container sonet-minute15-path-time-line-instances {
                      description
                        "port current performance data";
                      list sonet-minute15-path-time-line-instance {
                        key "number";
                        description
                          "port 15-minute otn performance data";
                        leaf number {
                          type uint32 {
                            range "1..32";
                          }
                          description
                            "History Index number";
                        }
                        uses PM-SONET-PATH-PARAS;
                      }
                    }
                    leaf number {
                      type uint32;
                      description
                        "channel number";
                    }
                  }
                }
              }
              container sonet-hour24-history {
                description
                  "port current performance data";
                container sonet-hour24-path-histories {
                  description
                    "port current performance data";
                  list sonet-hour24-path-history {
                    key "number";
                    description
                      "port 24 hour Path performance data";
                    container sonet-hour24-path-time-line-instances {
                      description
                        "port current performance data";
                      list sonet-hour24-path-time-line-instance {
                        key "number";
                        description
                          "port 15-minute otn performance data";
                        leaf number {
                          type uint32 {
                            range "1";
                          }
                          description
                            "History Index number";
                        }
                        uses PM-SONET-PATH-PARAS;
                      }
                    }
                    leaf number {
                      type uint32;
                      description
                        "channel number";
                    }
                  }
                }
                container sonet-hour24ocn-histories {
                  description
                    "port current performance data";
                  list sonet-hour24ocn-history {
                    key "number";
                    description
                      "port 24 hour ocn performance data";
                    container sonet-hour24ocn-time-line-instances {
                      description
                        "port current performance data";
                      list sonet-hour24ocn-time-line-instance {
                        key "number";
                        description
                          "port 15-minute otn performance data";
                        leaf number {
                          type uint32 {
                            range "1";
                          }
                          description
                            "History Index number";
                        }
                        uses PM-SONET-PARAS;
                      }
                    }
                    leaf number {
                      type uint32;
                      description
                        "channel number";
                    }
                  }
                }
              }
              leaf name {
                type xr:Interface-name;
                description
                  "Port name";
              }
            }
          }
        }
        container sts-history {
          description
            "STS controller History performance data";
          container sts-port-histories {
            description
              "Port performance data";
            list sts-port-history {
              key "name";
              description
                "Port performance data";
              container sts-minute15-history {
                description
                  "port current performance data";
                container sts-minute15-path-histories {
                  description
                    "port current performance data";
                  list sts-minute15-path-history {
                    key "number";
                    description
                      "port 15-minute Path performance data";
                    container sts-minute15-path-time-line-instances {
                      description
                        "port current performance data";
                      list sts-minute15-path-time-line-instance {
                        key "number";
                        description
                          "port 15-minute otn performance data";
                        leaf number {
                          type uint32 {
                            range "1..32";
                          }
                          description
                            "History Index number";
                        }
                        uses PM-SONET-PATH-PARAS;
                      }
                    }
                    leaf number {
                      type uint32;
                      description
                        "channel number";
                    }
                  }
                }
              }
              container sts-hour24-history {
                description
                  "port current performance data";
                container sts-hour24-path-histories {
                  description
                    "port current performance data";
                  list sts-hour24-path-history {
                    key "number";
                    description
                      "port 24 hour Path performance data";
                    container sts-hour24-path-time-line-instances {
                      description
                        "port current performance data";
                      list sts-hour24-path-time-line-instance {
                        key "number";
                        description
                          "port 15-minute sts performance data";
                        leaf number {
                          type uint32 {
                            range "1";
                          }
                          description
                            "History Index number";
                        }
                        uses PM-SONET-PATH-PARAS;
                      }
                    }
                    leaf number {
                      type uint32;
                      description
                        "channel number";
                    }
                  }
                }
              }
              leaf name {
                type xr:Interface-name;
                description
                  "Port name";
              }
            }
          }
        }
        container cem-history {
          description
            "CEM controller historical performance data";
          container cem-port-histories {
            description
              "CEM controller historical performance data";
            list cem-port-history {
              key "name";
              description
                "CEM controller historical performance data";
              container cem-second30-history {
                description
                  "CEM controller 30 second historical
                   performance data";
                container second30cem-histories {
                  description
                    "CEM controller 30 second CEM layer
                     historical performance data";
                  list second30cem-history {
                    key "slot-number";
                    description
                      "CEM controller 30 second CEM layer
                       historical performance data";
                    container second30cem-time-line-instances {
                      description
                        "CEM controller 30 second CEM layer
                         historical performance data";
                      list second30cem-time-line-instance {
                        key "number";
                        description
                          "CEM controller 30 second CEM layer
                           historical performance data";
                        leaf number {
                          type uint32 {
                            range "1..30";
                          }
                          description
                            "History Index number";
                        }
                        uses PM-CEM-PARAS;
                      }
                    }
                    leaf slot-number {
                      type uint32;
                      description
                        "interval slot number";
                    }
                  }
                }
              }
              container cem-hour24-history {
                description
                  "CEM controller 24 hour historical
                   performance data";
                container cem-hour24cem-histories {
                  description
                    "CEM controller 24 hour CEM layer
                     historical performance data";
                  list cem-hour24cem-history {
                    key "number";
                    description
                      "CEM controller 24 hour CEM layer
                       historical performance data";
                    container cem-hour24cem-time-line-instances {
                      description
                        "CEM controller 24 hour CEM layer
                         historical performance data";
                      list cem-hour24cem-time-line-instance {
                        key "number";
                        description
                          "CEM controller 24 hour CEM layer
                           historical performance data";
                        leaf number {
                          type uint32 {
                            range "1";
                          }
                          description
                            "History Index number";
                        }
                        uses PM-CEM-PARAS;
                      }
                    }
                    leaf number {
                      type uint32;
                      description
                        "channel number";
                    }
                  }
                }
              }
              container cem-minute15-history {
                description
                  "CEM controller 15 minute historical
                   performance data";
                container minute15cem-histories {
                  description
                    "CEM controller 15 minute CEM layer
                     historical performance data";
                  list minute15cem-history {
                    key "slot-number";
                    description
                      "CEM controller 15 minute CEM layer
                       historical performance data";
                    container minute15cem-time-line-instances {
                      description
                        "CEM controller 15 minute CEM layer
                         historical performance data";
                      list minute15cem-time-line-instance {
                        key "number";
                        description
                          "CEM controller 15 minute CEM layer
                           historical performance data";
                        leaf number {
                          type uint32 {
                            range "1..32";
                          }
                          description
                            "History Index number";
                        }
                        uses PM-CEM-PARAS;
                      }
                    }
                    leaf slot-number {
                      type uint32;
                      description
                        "interval slot number";
                    }
                  }
                }
              }
              leaf name {
                type xr:Interface-name;
                description
                  "Port name";
              }
            }
          }
        }
        container e1-history {
          description
            "E1 controller History performance data";
          container e1-port-histories {
            description
              "Port performance data";
            list e1-port-history {
              key "name";
              description
                "Port performance data";
              container e1-hour24-history {
                description
                  "port current performance data";
                container e1-hour24e1-histories {
                  description
                    "port current performance data";
                  list e1-hour24e1-history {
                    key "number";
                    description
                      "port 24 hour e1 performance data";
                    container e1-hour24e1-time-line-instances {
                      description
                        "port current performance data";
                      list e1-hour24e1-time-line-instance {
                        key "number";
                        description
                          "port 24 hour e1 performance data";
                        leaf number {
                          type uint32;
                          description
                            "History Index number";
                        }
                        uses PM-E1-PARAS;
                      }
                    }
                    leaf number {
                      type uint32;
                      description
                        "channel number";
                    }
                  }
                }
              }
              container e1-minute15-history {
                description
                  "port current performance data";
                container e1-minute15e1-histories {
                  description
                    "port current performance data";
                  list e1-minute15e1-history {
                    key "number";
                    description
                      "port 15-minute e1 performance data";
                    container e1-minute15e1-time-line-instances {
                      description
                        "port current performance data";
                      list e1-minute15e1-time-line-instance {
                        key "number";
                        description
                          "port 15-minute e1 performance data by
                           index";
                        leaf number {
                          type uint32;
                          description
                            "History Index number";
                        }
                        uses PM-E1-PARAS;
                      }
                    }
                    leaf number {
                      type uint32;
                      description
                        "channel number";
                    }
                  }
                }
              }
              leaf name {
                type xr:Interface-name;
                description
                  "Port name";
              }
            }
          }
        }
        container ethernet-history {
          description
            "EHERNET controller History performance data";
          container ethernet-port-histories {
            description
              "Port performance data";
            list ethernet-port-history {
              key "name";
              description
                "Port performance data";
              container ethernet-second30-history {
                description
                  "port current performance data";
                container ethernet-second30prbs-histories {
                  description
                    "Ethernet controller 30 second PRBS layer
                     historical performance data";
                  list ethernet-second30prbs-history {
                    key "number";
                    description
                      "Ethernet controller 30 second PRBS layer
                       historical performance data";
                    container ethernet-second30prbs-time-line-instances {
                      description
                        "Ethernet controller 30 second PRBS layer
                         historical performance data";
                      list ethernet-second30prbs-time-line-instance {
                        key "number";
                        description
                          "Ethernet controller 30 second PRBS
                           layer historical performance data";
                        leaf number {
                          type uint32 {
                            range "1..30";
                          }
                          description
                            "History Index number";
                        }
                        uses PM-PRBS-PARAS;
                      }
                    }
                    leaf number {
                      type uint32;
                      description
                        "channel number";
                    }
                  }
                }
                container second30pcs-histories {
                  description
                    "ETHERNET port interval performance data";
                  list second30pcs-history {
                    key "slot-number";
                    description
                      "ETHERNET port 30 sec pcs performance data";
                    container second30pcs-time-line-instances {
                      description
                        "port current performance data";
                      list second30pcs-time-line-instance {
                        key "number";
                        description
                          "port 30 sec pcs performance data";
                        leaf number {
                          type uint32 {
                            range "1..30";
                          }
                          description
                            "History Index number";
                        }
                        uses PM-PCS-PARAS;
                      }
                    }
                    leaf slot-number {
                      type uint32;
                      description
                        "interval slot number";
                    }
                  }
                }
                container second30-ether-histories {
                  description
                    "ETHERNET port interval performance data";
                  list second30-ether-history {
                    key "slot-number";
                    description
                      "ETHERNET port 30 sec ether performance
                       data";
                    container second30-ether-time-line-instances {
                      description
                        "port current performance data";
                      list second30-ether-time-line-instance {
                        key "number";
                        description
                          "port 30 sec otn performance data";
                        leaf number {
                          type uint32 {
                            range "1..30";
                          }
                          description
                            "History Index number";
                        }
                        uses PM-ETHERNET-PARAS;
                      }
                    }
                    leaf slot-number {
                      type uint32;
                      description
                        "interval slot number";
                    }
                  }
                }
                container second30-fec-histories {
                  description
                    "ETHERNET port interval performance data";
                  list second30-fec-history {
                    key "slot-number";
                    description
                      "ETHERNET port 30 sec fec performance data";
                    container second30-fec-time-line-instances {
                      description
                        "port current performance data";
                      list second30-fec-time-line-instance {
                        key "number";
                        description
                          "port 30 sec fec performance data";
                        leaf number {
                          type uint32 {
                            range "1..30";
                          }
                          description
                            "History Index number";
                        }
                        uses PM-FEC-PARAS;
                      }
                    }
                    leaf slot-number {
                      type uint32;
                      description
                        "interval slot number";
                    }
                  }
                }
              }
              container ethernet-hour24-history {
                description
                  "port current performance data";
                container hour24pcs-histories {
                  description
                    "port current performance data";
                  list hour24pcs-history {
                    key "number";
                    description
                      "port 24 hour ethernet performance data";
                    container hour24pcs-time-line-instances {
                      description
                        "port current performance data";
                      list hour24pcs-time-line-instance {
                        key "number";
                        description
                          "port 24-hour ethernet performance data";
                        leaf number {
                          type uint32 {
                            range "1";
                          }
                          description
                            "History Index number";
                        }
                        uses PM-PCS-PARAS;
                      }
                    }
                    leaf number {
                      type uint32;
                      description
                        "channel number";
                    }
                  }
                }
                container ethernet-hour24fec-histories {
                  description
                    "port current performance data";
                  list ethernet-hour24fec-history {
                    key "number";
                    description
                      "port 24 hour ethernet performance data";
                    container ethernet-hour24fec-time-line-instances {
                      description
                        "port current performance data";
                      list ethernet-hour24fec-time-line-instance {
                        key "number";
                        description
                          "port 24-hour ethernet performance data";
                        leaf number {
                          type uint32 {
                            range "1";
                          }
                          description
                            "History Index number";
                        }
                        uses PM-FEC-PARAS;
                      }
                    }
                    leaf number {
                      type uint32;
                      description
                        "channel number";
                    }
                  }
                }
                container ethernet-hour24prbs-histories {
                  description
                    "Ethernet controller 24 hour PRBS layer
                     historical performance data";
                  list ethernet-hour24prbs-history {
                    key "number";
                    description
                      "Ethernet controller 24 hour PRBS layer
                       historical performance data";
                    container ethernet-hour24prbs-time-line-instances {
                      description
                        "Ethernet controller 24 hour PRBS layer
                         historical performance data";
                      list ethernet-hour24prbs-time-line-instance {
                        key "number";
                        description
                          "Ethernet controller 24 hour PRBS layer
                           historical performance data";
                        leaf number {
                          type uint32 {
                            range "1";
                          }
                          description
                            "History Index number";
                        }
                        uses PM-PRBS-PARAS;
                      }
                    }
                    leaf number {
                      type uint32;
                      description
                        "channel number";
                    }
                  }
                }
                container ethernet-hour24-ether-histories {
                  description
                    "port current performance data";
                  list ethernet-hour24-ether-history {
                    key "number";
                    description
                      "port 24 hour ethernet performance data";
                    container ethernet-hour24-ether-time-line-instances {
                      description
                        "port current performance data";
                      list ethernet-hour24-ether-time-line-instance {
                        key "number";
                        description
                          "port 15-minute otn performance data";
                        leaf number {
                          type uint32 {
                            range "1";
                          }
                          description
                            "History Index number";
                        }
                        uses PM-ETHERNET-PARAS;
                      }
                    }
                    leaf number {
                      type uint32;
                      description
                        "channel number";
                    }
                  }
                }
              }
              container ethernet-minute15-history {
                description
                  "port current performance data";
                container minute15pcs-histories {
                  description
                    "ETHERNET port interval performance data";
                  list minute15pcs-history {
                    key "slot-number";
                    description
                      "ETHERNET port 15-minute pcs performance
                       data";
                    container minute15pcs-time-line-instances {
                      description
                        "port current performance data";
                      list minute15pcs-time-line-instance {
                        key "number";
                        description
                          "port 15-minute pcs performance data";
                        leaf number {
                          type uint32 {
                            range "1..32";
                          }
                          description
                            "History Index number";
                        }
                        uses PM-PCS-PARAS;
                      }
                    }
                    leaf slot-number {
                      type uint32;
                      description
                        "interval slot number";
                    }
                  }
                }
                container minute15-ether-histories {
                  description
                    "ETHERNET port interval performance data";
                  list minute15-ether-history {
                    key "slot-number";
                    description
                      "ETHERNET port 15-minute ether performance
                       data";
                    container minute15-ether-time-line-instances {
                      description
                        "port current performance data";
                      list minute15-ether-time-line-instance {
                        key "number";
                        description
                          "port 15-minute otn performance data";
                        leaf number {
                          type uint32 {
                            range "1..32";
                          }
                          description
                            "History Index number";
                        }
                        uses PM-ETHERNET-PARAS;
                      }
                    }
                    leaf slot-number {
                      type uint32;
                      description
                        "interval slot number";
                    }
                  }
                }
                container minute15-fec-histories {
                  description
                    "ETHERNET port interval performance data";
                  list minute15-fec-history {
                    key "slot-number";
                    description
                      "ETHERNET port 15-minute fec performance
                       data";
                    container minute15-fec-time-line-instances {
                      description
                        "port current performance data";
                      list minute15-fec-time-line-instance {
                        key "number";
                        description
                          "port 15-minute fec performance data";
                        leaf number {
                          type uint32 {
                            range "1..32";
                          }
                          description
                            "History Index number";
                        }
                        uses PM-FEC-PARAS;
                      }
                    }
                    leaf slot-number {
                      type uint32;
                      description
                        "interval slot number";
                    }
                  }
                }
                container ethernet-minute15prbs-histories {
                  description
                    "Ethernet controller 15 minute PRBS layer
                     historical performance data";
                  list ethernet-minute15prbs-history {
                    key "number";
                    description
                      "Ethernet controller 15 minute PRBS layer
                       historical performance data";
                    container ethernet-minute15prbs-time-line-instances {
                      description
                        "Ethernet controller 15 minute PRBS layer
                         historical performance data";
                      list ethernet-minute15prbs-time-line-instance {
                        key "number";
                        description
                          "Ethernet controller 15 minute PRBS
                           layer historical performance data";
                        leaf number {
                          type uint32 {
                            range "1..32";
                          }
                          description
                            "History Index number";
                        }
                        uses PM-PRBS-PARAS;
                      }
                    }
                    leaf number {
                      type uint32;
                      description
                        "channel number";
                    }
                  }
                }
              }
              leaf name {
                type xr:Interface-name;
                description
                  "Port name";
              }
            }
          }
        }
        container dwdm-history {
          description
            "DWDM controller History performance data";
          container dwdm-port-histories {
            description
              "Port performance data";
            list dwdm-port-history {
              key "name";
              description
                "Port performance data";
              container dwdm-minute15-history {
                description
                  "port current performance data";
                container dwdm-minute15otn-histories {
                  description
                    "port current performance data";
                  list dwdm-minute15otn-history {
                    key "number";
                    description
                      "port 15-minute otn performance data";
                    container dwdm-minute15otn-time-line-instances {
                      description
                        "port current performance data";
                      list dwdm-minute15otn-time-line-instance {
                        key "number";
                        description
                          "port 15-minute otn performance data";
                        leaf number {
                          type uint32 {
                            range "1..32";
                          }
                          description
                            "History Index number";
                        }
                        uses PM-OTN-PARAS;
                      }
                    }
                    leaf number {
                      type uint32;
                      description
                        "channel number";
                    }
                  }
                }
                container dwdm-minute15fec-histories {
                  description
                    "port current performance data";
                  list dwdm-minute15fec-history {
                    key "number";
                    description
                      "port 15-minute fec performance data";
                    container dwdm-minute15fec-time-line-instances {
                      description
                        "port current performance data";
                      list dwdm-minute15fec-time-line-instance {
                        key "number";
                        description
                          "port 15-minute fec performance data by
                           index";
                        leaf number {
                          type uint32 {
                            range "1..32";
                          }
                          description
                            "History Index number";
                        }
                        uses PM-FEC-PARAS;
                      }
                    }
                    leaf number {
                      type uint32;
                      description
                        "channel number";
                    }
                  }
                }
                container dwdm-minute15-optics-histories {
                  description
                    "port current performance data";
                  list dwdm-minute15-optics-history {
                    key "number";
                    description
                      "port 15-minute optics performance data";
                    container dwdm-minute15-optics-time-line-instances {
                      description
                        "port current performance data";
                      list dwdm-minute15-optics-time-line-instance {
                        key "number";
                        description
                          "port 15-minute otn performance data";
                        leaf number {
                          type uint32 {
                            range "1..32";
                          }
                          description
                            "History Index number";
                        }
                        uses PM-OPTICS-PARAS;
                      }
                    }
                    leaf number {
                      type uint32;
                      description
                        "channel number";
                    }
                  }
                }
              }
              container dwdm-hour24-history {
                description
                  "port current performance data";
                container dwdm-hour24otn-histories {
                  description
                    "port 24 hour performance data";
                  list dwdm-hour24otn-history {
                    key "number";
                    description
                      "port 24 hour otn performance data";
                    container dwdm-hour24otn-time-line-instances {
                      description
                        "port current performance data";
                      list dwdm-hour24otn-time-line-instance {
                        key "number";
                        description
                          "port 15-minute otn performance data";
                        leaf number {
                          type uint32 {
                            range "1";
                          }
                          description
                            "History Index number";
                        }
                        uses PM-OTN-PARAS;
                      }
                    }
                    leaf number {
                      type uint32;
                      description
                        "channel number";
                    }
                  }
                }
                container dwdm-hour24fec-histories {
                  description
                    "port current performance data";
                  list dwdm-hour24fec-history {
                    key "number";
                    description
                      "port 24 hour fec performance data";
                    container dwdm-hour24fec-time-line-instances {
                      description
                        "port current performance data";
                      list dwdm-hour24fec-time-line-instance {
                        key "number";
                        description
                          "port 15-minute fec performance data by
                           index";
                        leaf number {
                          type uint32 {
                            range "1";
                          }
                          description
                            "History Index number";
                        }
                        uses PM-FEC-PARAS;
                      }
                    }
                    leaf number {
                      type uint32;
                      description
                        "channel number";
                    }
                  }
                }
                container dwdm-hour24-optics-histories {
                  description
                    "port 24 hour performance data";
                  list dwdm-hour24-optics-history {
                    key "number";
                    description
                      "port 24 hour optics performance data";
                    container dwdm-hour24-optics-time-line-instances {
                      description
                        "port current performance data";
                      list dwdm-hour24-optics-time-line-instance {
                        key "number";
                        description
                          "port 15-minute otn performance data";
                        leaf number {
                          type uint32 {
                            range "1";
                          }
                          description
                            "History Index number";
                        }
                        uses PM-OPTICS-PARAS;
                      }
                    }
                    leaf number {
                      type uint32;
                      description
                        "channel number";
                    }
                  }
                }
              }
              leaf name {
                type xr:Interface-name;
                description
                  "Port name";
              }
            }
          }
        }
        container stm-history {
          description
            "STM controller History performance data";
          container stm-port-histories {
            description
              "Port performance data";
            list stm-port-history {
              key "name";
              description
                "Port performance data";
              container stm-hour24-history {
                description
                  "port current performance data";
                container stm-hour24stm-histories {
                  description
                    "port current performance data";
                  list stm-hour24stm-history {
                    key "number";
                    description
                      "port 24 hour stm performance data";
                    container stm-hour24stm-time-line-instances {
                      description
                        "port current performance data";
                      list stm-hour24stm-time-line-instance {
                        key "number";
                        description
                          "port 15-minute stm performance data";
                        leaf number {
                          type uint32 {
                            range "1";
                          }
                          description
                            "History Index number";
                        }
                        uses PM-STM-PARAS;
                      }
                    }
                    leaf number {
                      type uint32;
                      description
                        "channel number";
                    }
                  }
                }
                container stm-hour24prbs-histories {
                  description
                    "STM controller 24 hour PRBS layer
                     historical performance data";
                  list stm-hour24prbs-history {
                    key "number";
                    description
                      "STM controller 24 hour PRBS layer
                       historical performance data";
                    container stm-hour24prbs-time-line-instances {
                      description
                        "STM controller 24 hour PRBS layer
                         historical performance data";
                      list stm-hour24prbs-time-line-instance {
                        key "number";
                        description
                          "STM controller 24 hour PRBS layer
                           historical performance data";
                        leaf number {
                          type uint32 {
                            range "1";
                          }
                          description
                            "History Index number";
                        }
                        uses PM-PRBS-PARAS;
                      }
                    }
                    leaf number {
                      type uint32;
                      description
                        "channel number";
                    }
                  }
                }
              }
              container stm-minute15-history {
                description
                  "port current performance data";
                container stm-minute15stm-histories {
                  description
                    "port current performance data";
                  list stm-minute15stm-history {
                    key "number";
                    description
                      "port 15-minute stm performance data";
                    container stm-minute15stm-time-line-instances {
                      description
                        "port current performance data";
                      list stm-minute15stm-time-line-instance {
                        key "number";
                        description
                          "port 15-minute stm performance data";
                        leaf number {
                          type uint32 {
                            range "1..32";
                          }
                          description
                            "History Index number";
                        }
                        uses PM-STM-PARAS;
                      }
                    }
                    leaf number {
                      type uint32;
                      description
                        "channel number";
                    }
                  }
                }
                container stm-minute15prbs-histories {
                  description
                    "STM controller 15 minute PRBS layer
                     historical performance data";
                  list stm-minute15prbs-history {
                    key "number";
                    description
                      "STM controller 15 minute PRBS layer
                       historical performance data";
                    container stm-minute15prbs-time-line-instances {
                      description
                        "STM controller 15 minute PRBS layer
                         historical performance data";
                      list stm-minute15prbs-time-line-instance {
                        key "number";
                        description
                          "STM controller 15 minute PRBS layer
                           historical performance data";
                        leaf number {
                          type uint32 {
                            range "1..32";
                          }
                          description
                            "History Index number";
                        }
                        uses PM-PRBS-PARAS;
                      }
                    }
                    leaf number {
                      type uint32;
                      description
                        "channel number";
                    }
                  }
                }
              }
              container stm-second30-history {
                description
                  "STM controller 30 second historical
                   performance data";
                container stm-second30prbs-histories {
                  description
                    "STM controller 30 second PRBS layer
                     historical performance data";
                  list stm-second30prbs-history {
                    key "number";
                    description
                      "STM controller 30 second PRBS layer
                       historical performance data";
                    container stm-second30prbs-time-line-instances {
                      description
                        "STM controller 30 second PRBS layer
                         historical performance data";
                      list stm-second30prbs-time-line-instance {
                        key "number";
                        description
                          "STM controller 30 second PRBS layer
                           historical performance data";
                        leaf number {
                          type uint32 {
                            range "1..30";
                          }
                          description
                            "History Index number";
                        }
                        uses PM-PRBS-PARAS;
                      }
                    }
                    leaf number {
                      type uint32;
                      description
                        "channel number";
                    }
                  }
                }
              }
              leaf name {
                type xr:Interface-name;
                description
                  "Port name";
              }
            }
          }
        }
        container macsec-history {
          description
            "MACSEC controller History performance data";
          container macsec-port-histories {
            description
              "Port performance data";
            list macsec-port-history {
              key "name";
              description
                "Port performance data";
              container macsec-minute15-history {
                description
                  "port current performance data";
                container macsec-minute15secyrx-histories {
                  description
                    "port current performance data";
                  list macsec-minute15secyrx-history {
                    key "number";
                    description
                      "port 15-minute secy_rx performance data";
                    container macsec-minute15secyrx-time-line-instances {
                      description
                        "port current performance data";
                      list macsec-minute15secyrx-time-line-instance {
                        key "number";
                        description
                          "port 15-minute secy_rx performance data
                           by index";
                        leaf number {
                          type uint32 {
                            range "1..32";
                          }
                          description
                            "History Index number";
                        }
                        uses PM-SECY-RX-PARAS;
                      }
                    }
                    leaf number {
                      type uint32;
                      description
                        "channel number";
                    }
                  }
                }
                container macsec-minute15-ether-histories {
                  description
                    "port current performance data";
                  list macsec-minute15-ether-history {
                    key "number";
                    description
                      "port 15-minute ether performance data";
                    container macsec-minute15-ether-time-line-instances {
                      description
                        "port current performance data";
                      list macsec-minute15-ether-time-line-instance {
                        key "number";
                        description
                          "port 15-minute ether performance data
                           by index";
                        leaf number {
                          type uint32 {
                            range "1..32";
                          }
                          description
                            "History Index number";
                        }
                        uses PM-ETHERNET-PARAS;
                      }
                    }
                    leaf number {
                      type uint32;
                      description
                        "channel number";
                    }
                  }
                }
                container macsec-minute15secytx-histories {
                  description
                    "port current performance data";
                  list macsec-minute15secytx-history {
                    key "number";
                    description
                      "port 15-minute secy_tx performance data";
                    container macsec-minute15secytx-time-line-instances {
                      description
                        "port current performance data";
                      list macsec-minute15secytx-time-line-instance {
                        key "number";
                        description
                          "port 15-minute secy_tx performance data
                           by index";
                        leaf number {
                          type uint32 {
                            range "1..32";
                          }
                          description
                            "History Index number";
                        }
                        uses PM-SECY-TX-PARAS;
                      }
                    }
                    leaf number {
                      type uint32;
                      description
                        "channel number";
                    }
                  }
                }
                container macsec-minute15secyif-histories {
                  description
                    "port current performance data";
                  list macsec-minute15secyif-history {
                    key "number";
                    description
                      "port 15-minute secy_if performance data";
                    container macsec-minute15secyif-time-line-instances {
                      description
                        "port current performance data";
                      list macsec-minute15secyif-time-line-instance {
                        key "number";
                        description
                          "port 15-minute secy_if performance data
                           by index";
                        leaf number {
                          type uint32 {
                            range "1..32";
                          }
                          description
                            "History Index number";
                        }
                        uses PM-SECY-IF-PARAS;
                      }
                    }
                    leaf number {
                      type uint32;
                      description
                        "channel number";
                    }
                  }
                }
              }
              container macsec-hour24-history {
                description
                  "port current performance data";
                container macsec-hour24-ether-histories {
                  description
                    "port current performance data";
                  list macsec-hour24-ether-history {
                    key "number";
                    description
                      "port 24 hour ether performance data";
                    container macsec-hour24-ether-time-line-instances {
                      description
                        "port current performance data";
                      list macsec-hour24-ether-time-line-instance {
                        key "number";
                        description
                          "port 24 hour ether performance data";
                        leaf number {
                          type uint32 {
                            range "1";
                          }
                          description
                            "History Index number";
                        }
                        uses PM-ETHERNET-PARAS;
                      }
                    }
                    leaf number {
                      type uint32;
                      description
                        "channel number";
                    }
                  }
                }
                container macsec-hour24secytx-histories {
                  description
                    "port current performance data";
                  list macsec-hour24secytx-history {
                    key "number";
                    description
                      "port 24 hour secy_tx performance data";
                    container macsec-hour24secytx-time-line-instances {
                      description
                        "port current performance data";
                      list macsec-hour24secytx-time-line-instance {
                        key "number";
                        description
                          "port 24 hour secy_tx performance data";
                        leaf number {
                          type uint32 {
                            range "1";
                          }
                          description
                            "History Index number";
                        }
                        uses PM-SECY-TX-PARAS;
                      }
                    }
                    leaf number {
                      type uint32;
                      description
                        "channel number";
                    }
                  }
                }
                container macsec-hour24secyif-histories {
                  description
                    "port current performance data";
                  list macsec-hour24secyif-history {
                    key "number";
                    description
                      "port 24 hour secy_if performance data";
                    container macsec-hour24secyif-time-line-instances {
                      description
                        "port current performance data";
                      list macsec-hour24secyif-time-line-instance {
                        key "number";
                        description
                          "port 24 hour secy_if performance data";
                        leaf number {
                          type uint32 {
                            range "1";
                          }
                          description
                            "History Index number";
                        }
                        uses PM-SECY-IF-PARAS;
                      }
                    }
                    leaf number {
                      type uint32;
                      description
                        "channel number";
                    }
                  }
                }
                container macsec-hour24secyrx-histories {
                  description
                    "port current performance data";
                  list macsec-hour24secyrx-history {
                    key "number";
                    description
                      "port 24 hour secy_rx performance data";
                    container macsec-hour24secyrx-time-line-instances {
                      description
                        "port current performance data";
                      list macsec-hour24secyrx-time-line-instance {
                        key "number";
                        description
                          "port 24 hour secy_rx performance data";
                        leaf number {
                          type uint32 {
                            range "1";
                          }
                          description
                            "History Index number";
                        }
                        uses PM-SECY-RX-PARAS;
                      }
                    }
                    leaf number {
                      type uint32;
                      description
                        "channel number";
                    }
                  }
                }
              }
              container macsec-second30-history {
                description
                  "port current performance data";
                container macsec-second30secyrx-histories {
                  description
                    "port current performance data";
                  list macsec-second30secyrx-history {
                    key "number";
                    description
                      "port 30-second secy_rx performance data";
                    container macsec-second30secyrx-time-line-instances {
                      description
                        "port current performance data";
                      list macsec-second30secyrx-time-line-instance {
                        key "number";
                        description
                          "port 30-second secy_rx performance data";
                        leaf number {
                          type uint32 {
                            range "1..30";
                          }
                          description
                            "History Index number";
                        }
                        uses PM-SECY-RX-PARAS;
                      }
                    }
                    leaf number {
                      type uint32;
                      description
                        "channel number";
                    }
                  }
                }
                container macsec-second30-ether-histories {
                  description
                    "port current performance data";
                  list macsec-second30-ether-history {
                    key "number";
                    description
                      "port 30-second ether performance data";
                    container macsec-second30-ether-time-line-instances {
                      description
                        "port current performance data";
                      list macsec-second30-ether-time-line-instance {
                        key "number";
                        description
                          "port 30-second ether performance data";
                        leaf number {
                          type uint32 {
                            range "1..30";
                          }
                          description
                            "History Index number";
                        }
                        uses PM-ETHERNET-PARAS;
                      }
                    }
                    leaf number {
                      type uint32;
                      description
                        "channel number";
                    }
                  }
                }
                container macsec-second30secytx-histories {
                  description
                    "port current performance data";
                  list macsec-second30secytx-history {
                    key "number";
                    description
                      "port 30-second secy_tx performance data";
                    container macsec-second30secytx-time-line-instances {
                      description
                        "port current performance data";
                      list macsec-second30secytx-time-line-instance {
                        key "number";
                        description
                          "port 30-second secy_tx performance data";
                        leaf number {
                          type uint32 {
                            range "1..30";
                          }
                          description
                            "History Index number";
                        }
                        uses PM-SECY-TX-PARAS;
                      }
                    }
                    leaf number {
                      type uint32;
                      description
                        "channel number";
                    }
                  }
                }
                container macsec-second30secyif-histories {
                  description
                    "port current performance data";
                  list macsec-second30secyif-history {
                    key "number";
                    description
                      "port 30-second secy_if performance data";
                    container macsec-second30secyif-time-line-instances {
                      description
                        "port current performance data";
                      list macsec-second30secyif-time-line-instance {
                        key "number";
                        description
                          "port 30-second secy_if performance data";
                        leaf number {
                          type uint32 {
                            range "1..30";
                          }
                          description
                            "History Index number";
                        }
                        uses PM-SECY-IF-PARAS;
                      }
                    }
                    leaf number {
                      type uint32;
                      description
                        "channel number";
                    }
                  }
                }
              }
              leaf name {
                type xr:Interface-name;
                description
                  "Port name";
              }
            }
          }
        }
        container odu-history {
          description
            "ODU controller History performance data";
          container odu-port-histories {
            description
              "Port performance data";
            list odu-port-history {
              key "name";
              description
                "Port performance data";
              container odu-hour24-history {
                description
                  "port current performance data";
                container odu-hour24gfp-histories {
                  description
                    "port 24 hour performance data";
                  list odu-hour24gfp-history {
                    key "number";
                    description
                      "port 24 hour otn performance data";
                    container odu-hour24gfp-time-line-instances {
                      description
                        "port current performance data";
                      list odu-hour24gfp-time-line-instance {
                        key "number";
                        description
                          "port 15-minute otn performance data";
                        leaf number {
                          type uint32 {
                            range "1";
                          }
                          description
                            "History Index number";
                        }
                        uses PM-GFP-PARAS;
                      }
                    }
                    leaf number {
                      type uint32;
                      description
                        "channel number";
                    }
                  }
                }
                container odu-hour24prbs-histories {
                  description
                    "port 24 hour performance data";
                  list odu-hour24prbs-history {
                    key "number";
                    description
                      "port 24 hour prbs performance data";
                    container odu-hour24prbs-time-line-instances {
                      description
                        "port current performance data";
                      list odu-hour24prbs-time-line-instance {
                        key "number";
                        description
                          "port 15-minute prbs performance data";
                        leaf number {
                          type uint32 {
                            range "1";
                          }
                          description
                            "History Index number";
                        }
                        uses PM-PRBS-PARAS;
                      }
                    }
                    leaf number {
                      type uint32;
                      description
                        "channel number";
                    }
                  }
                }
                container odu-hour24otn-histories {
                  description
                    "port 24 hour performance data";
                  list odu-hour24otn-history {
                    key "number";
                    description
                      "port 24 hour otn performance data";
                    container odu-hour24otn-time-line-instances {
                      description
                        "port current performance data";
                      list odu-hour24otn-time-line-instance {
                        key "number";
                        description
                          "port 24-hour otn performance data";
                        leaf number {
                          type uint32 {
                            range "1..7";
                          }
                          description
                            "History Index number";
                        }
                        uses PM-OTN-PARAS;
                      }
                    }
                    leaf number {
                      type uint32;
                      description
                        "channel number";
                    }
                  }
                }
              }
              container odu-second30-history {
                description
                  "port current performance data";
                container odu-second30otn-histories {
                  description
                    "port current performance data";
                  list odu-second30otn-history {
                    key "number";
                    description
                      "port 30-second otn performance data";
                    container odu-second30otn-time-line-instances {
                      description
                        "port current performance data";
                      list odu-second30otn-time-line-instance {
                        key "number";
                        description
                          "port 30-second otn performance data";
                        leaf number {
                          type uint32 {
                            range "1..30";
                          }
                          description
                            "History Index number";
                        }
                        uses PM-OTN-PARAS;
                      }
                    }
                    leaf number {
                      type uint32;
                      description
                        "channel number";
                    }
                  }
                }
                container odu-second30prbs-histories {
                  description
                    "port current performance data";
                  list odu-second30prbs-history {
                    key "number";
                    description
                      "port 30-second prbs performance data";
                    container odu-second30prbs-time-line-instances {
                      description
                        "port current performance data";
                      list odu-second30prbs-time-line-instance {
                        key "number";
                        description
                          "port 30-second prbs performance data";
                        leaf number {
                          type uint32 {
                            range "1..30";
                          }
                          description
                            "History Index number";
                        }
                        uses PM-PRBS-PARAS;
                      }
                    }
                    leaf number {
                      type uint32;
                      description
                        "channel number";
                    }
                  }
                }
                container odu-second30gfp-histories {
                  description
                    "port current performance data";
                  list odu-second30gfp-history {
                    key "number";
                    description
                      "port 30-second otn performance data";
                    container odu-second30gfp-time-line-instances {
                      description
                        "port current performance data";
                      list odu-second30gfp-time-line-instance {
                        key "number";
                        description
                          "port 30-second otn performance data";
                        leaf number {
                          type uint32 {
                            range "1..30";
                          }
                          description
                            "History Index number";
                        }
                        uses PM-GFP-PARAS;
                      }
                    }
                    leaf number {
                      type uint32;
                      description
                        "channel number";
                    }
                  }
                }
              }
              container odu-minute15-history {
                description
                  "port current performance data";
                container odu-minute15prbs-histories {
                  description
                    "port current performance data";
                  list odu-minute15prbs-history {
                    key "number";
                    description
                      "port 15-minute prbs performance data";
                    container odu-minute15prbs-time-line-instances {
                      description
                        "port current performance data";
                      list odu-minute15prbs-time-line-instance {
                        key "number";
                        description
                          "port 15-minute prbs performance data";
                        leaf number {
                          type uint32 {
                            range "1..32";
                          }
                          description
                            "History Index number";
                        }
                        uses PM-PRBS-PARAS;
                      }
                    }
                    leaf number {
                      type uint32;
                      description
                        "channel number";
                    }
                  }
                }
                container odu-minute15gfp-histories {
                  description
                    "port current performance data";
                  list odu-minute15gfp-history {
                    key "number";
                    description
                      "port 15-minute otn performance data";
                    container odu-minute15gfp-time-line-instances {
                      description
                        "port current performance data";
                      list odu-minute15gfp-time-line-instance {
                        key "number";
                        description
                          "port 15-minute otn performance data";
                        leaf number {
                          type uint32 {
                            range "1..32";
                          }
                          description
                            "History Index number";
                        }
                        uses PM-GFP-PARAS;
                      }
                    }
                    leaf number {
                      type uint32;
                      description
                        "channel number";
                    }
                  }
                }
                container odu-minute15otn-histories {
                  description
                    "port current performance data";
                  list odu-minute15otn-history {
                    key "number";
                    description
                      "port 15-minute otn performance data";
                    container odu-minute15otn-time-line-instances {
                      description
                        "port current performance data";
                      list odu-minute15otn-time-line-instance {
                        key "number";
                        description
                          "port 15-minute otn performance data";
                        leaf number {
                          type uint32 {
                            range "1..32";
                          }
                          description
                            "History Index number";
                        }
                        uses PM-OTN-PARAS;
                      }
                    }
                    leaf number {
                      type uint32;
                      description
                        "channel number";
                    }
                  }
                }
              }
              leaf name {
                type xr:Interface-name;
                description
                  "Port name";
              }
            }
          }
        }
        container otu-history {
          description
            "OTU controller History performance data";
          container otu-port-histories {
            description
              "Port performance data";
            list otu-port-history {
              key "name";
              description
                "Port performance data";
              container otu-second30-history {
                description
                  "port current performance data";
                container otu-second30fec-histories {
                  description
                    "port current performance data";
                  list otu-second30fec-history {
                    key "number";
                    description
                      "port 30-second fec performance data";
                    container otu-second30fec-time-line-instances {
                      description
                        "port current performance data";
                      list otu-second30fec-time-line-instance {
                        key "number";
                        description
                          "port 30-second fec performance data";
                        leaf number {
                          type uint32 {
                            range "1..30";
                          }
                          description
                            "History Index number";
                        }
                        uses PM-FEC-PARAS;
                      }
                    }
                    leaf number {
                      type uint32;
                      description
                        "channel number";
                    }
                  }
                }
                container otu-second30prbs-histories {
                  description
                    "prbs 30-sec performance data";
                  list otu-second30prbs-history {
                    key "number";
                    description
                      "prbs 30-sec prbs performance data";
                    container otu-second30prbs-time-line-instances {
                      description
                        "prbs 30-sec current performance data";
                      list otu-second30prbs-time-line-instance {
                        key "number";
                        description
                          "prbs 30-sec prbs performance data";
                        leaf number {
                          type uint32 {
                            range "1..30";
                          }
                          description
                            "History Index number";
                        }
                        uses PM-PRBS-PARAS;
                      }
                    }
                    leaf number {
                      type uint32;
                      description
                        "channel number";
                    }
                  }
                }
                container otu-second30otn-histories {
                  description
                    "port current performance data";
                  list otu-second30otn-history {
                    key "number";
                    description
                      "port 30-second otn performance data";
                    container otu-second30otn-time-line-instances {
                      description
                        "port current performance data";
                      list otu-second30otn-time-line-instance {
                        key "number";
                        description
                          "port 30-second otn performance data";
                        leaf number {
                          type uint32 {
                            range "1..30";
                          }
                          description
                            "History Index number";
                        }
                        uses PM-OTN-PARAS;
                      }
                    }
                    leaf number {
                      type uint32;
                      description
                        "channel number";
                    }
                  }
                }
              }
              container otu-minute15-history {
                description
                  "port current performance data";
                container otu-minute15fec-histories {
                  description
                    "port current performance data";
                  list otu-minute15fec-history {
                    key "number";
                    description
                      "port 15-minute fec performance data";
                    container otu-minute15fec-time-line-instances {
                      description
                        "port current performance data";
                      list otu-minute15fec-time-line-instance {
                        key "number";
                        description
                          "port 15-minute fec performance data";
                        leaf number {
                          type uint32 {
                            range "1..32";
                          }
                          description
                            "History Index number";
                        }
                        uses PM-FEC-PARAS;
                      }
                    }
                    leaf number {
                      type uint32;
                      description
                        "channel number";
                    }
                  }
                }
                container otu-minute15prbs-histories {
                  description
                    "port current performance data";
                  list otu-minute15prbs-history {
                    key "number";
                    description
                      "port 15-minute prbs performance data";
                    container otu-minute15prbs-time-line-instances {
                      description
                        "port current performance data";
                      list otu-minute15prbs-time-line-instance {
                        key "number";
                        description
                          "port 15-minute prbs performance data";
                        leaf number {
                          type uint32 {
                            range "1..32";
                          }
                          description
                            "History Index number";
                        }
                        uses PM-PRBS-PARAS;
                      }
                    }
                    leaf number {
                      type uint32;
                      description
                        "channel number";
                    }
                  }
                }
                container otu-minute15otn-histories {
                  description
                    "port current performance data";
                  list otu-minute15otn-history {
                    key "number";
                    description
                      "port 15-minute otn performance data";
                    container otu-minute15otn-time-line-instances {
                      description
                        "port current performance data";
                      list otu-minute15otn-time-line-instance {
                        key "number";
                        description
                          "port 15-minute otn performance data";
                        leaf number {
                          type uint32 {
                            range "1..32";
                          }
                          description
                            "History Index number";
                        }
                        uses PM-OTN-PARAS;
                      }
                    }
                    leaf number {
                      type uint32;
                      description
                        "channel number";
                    }
                  }
                }
              }
              container otu-hour24-history {
                description
                  "port current performance data";
                container otu-hour24prbs-histories {
                  description
                    "port 24 hour performance data";
                  list otu-hour24prbs-history {
                    key "number";
                    description
                      "port 24 hour prbs performance data";
                    container otu-hour24prbs-time-line-instances {
                      description
                        "port current performance data";
                      list otu-hour24prbs-time-line-instance {
                        key "number";
                        description
                          "port 15-minute prbs performance data";
                        leaf number {
                          type uint32 {
                            range "1";
                          }
                          description
                            "History Index number";
                        }
                        uses PM-PRBS-PARAS;
                      }
                    }
                    leaf number {
                      type uint32;
                      description
                        "channel number";
                    }
                  }
                }
                container otu-hour24otn-histories {
                  description
                    "port 24 hour performance data";
                  list otu-hour24otn-history {
                    key "number";
                    description
                      "port 24 hour otn performance data";
                    container otu-hour24otn-time-line-instances {
                      description
                        "port current performance data";
                      list otu-hour24otn-time-line-instance {
                        key "number";
                        description
                          "port 24-hour otn performance data";
                        leaf number {
                          type uint32 {
                            range "1..7";
                          }
                          description
                            "History Index number";
                        }
                        uses PM-OTN-PARAS;
                      }
                    }
                    leaf number {
                      type uint32;
                      description
                        "channel number";
                    }
                  }
                }
                container otu-hour24fec-histories {
                  description
                    "port current performance data";
                  list otu-hour24fec-history {
                    key "number";
                    description
                      "port 24 hour fec performance data";
                    container otu-hour24fec-time-line-instances {
                      description
                        "port current performance data";
                      list otu-hour24fec-time-line-instance {
                        key "number";
                        description
                          "port 15-minute fec performance data";
                        leaf number {
                          type uint32 {
                            range "1";
                          }
                          description
                            "History Index number";
                        }
                        uses PM-FEC-PARAS;
                      }
                    }
                    leaf number {
                      type uint32;
                      description
                        "channel number";
                    }
                  }
                }
              }
              leaf name {
                type xr:Interface-name;
                description
                  "Port name";
              }
            }
          }
        }
        container ho-vc-history {
          description
            "HO_VC controller History performance data";
          container ho-vc-port-histories {
            description
              "Port performance data";
            list ho-vc-port-history {
              key "name";
              description
                "Port performance data";
              container ho-vc-minute15-history {
                description
                  "port current performance data";
                container ho-vc-minute15-path-histories {
                  description
                    "port current performance data";
                  list ho-vc-minute15-path-history {
                    key "number";
                    description
                      "port 15-minute Path performance data";
                    container ho-vc-minute15-path-time-line-instances {
                      description
                        "port current performance data";
                      list ho-vc-minute15-path-time-line-instance {
                        key "number";
                        description
                          "port 15-minute ho_vc performance data";
                        leaf number {
                          type uint32 {
                            range "1..32";
                          }
                          description
                            "History Index number";
                        }
                        uses PM-HO-VC-PARAS;
                      }
                    }
                    leaf number {
                      type uint32;
                      description
                        "channel number";
                    }
                  }
                }
              }
              container ho-vc-hour24-history {
                description
                  "port current performance data";
                container ho-vc-hour24-path-histories {
                  description
                    "port current performance data";
                  list ho-vc-hour24-path-history {
                    key "number";
                    description
                      "port 24 hour Path performance data";
                    container ho-vc-hour24-path-time-line-instances {
                      description
                        "port current performance data";
                      list ho-vc-hour24-path-time-line-instance {
                        key "number";
                        description
                          "port 15-minute otn performance data";
                        leaf number {
                          type uint32 {
                            range "1";
                          }
                          description
                            "History Index number";
                        }
                        uses PM-HO-VC-PARAS;
                      }
                    }
                    leaf number {
                      type uint32;
                      description
                        "channel number";
                    }
                  }
                }
              }
              leaf name {
                type xr:Interface-name;
                description
                  "Port name";
              }
            }
          }
        }
        container fc-history {
          description
            "FC controller historical performance data";
          container fc-port-histories {
            description
              "FC controller historical performance data";
            list fc-port-history {
              key "name";
              description
                "FC controller historical performance data";
              container fc-minute15-history {
                description
                  "FC controller 15 minute historical
                   performance data";
                container fc-minute15fec-histories {
                  description
                    "FC controller 15 minute FEC layer
                     historical performance data";
                  list fc-minute15fec-history {
                    key "slot-number";
                    description
                      "FC controller 15 minute FEC layer
                       historical performance data";
                    container fc-minute15fec-time-line-instances {
                      description
                        "FC controller 15 minute FEC layer
                         historical performance data";
                      list fc-minute15fec-time-line-instance {
                        key "number";
                        description
                          "FC controller 15 minute FEC layer
                           historical performance data";
                        leaf number {
                          type uint32 {
                            range "1..32";
                          }
                          description
                            "History Index number";
                        }
                        uses PM-FEC-PARAS;
                      }
                    }
                    leaf slot-number {
                      type uint32;
                      description
                        "interval slot number";
                    }
                  }
                }
                container fc-minute15prbs-histories {
                  description
                    "FC controller 15 minute PRBS layer
                     historical performance data";
                  list fc-minute15prbs-history {
                    key "number";
                    description
                      "FC controller 15 minute PRBS layer
                       historical performance data";
                    container fc-minute15prbs-time-line-instances {
                      description
                        "FC controller 15 minute PRBS layer
                         historical performance data";
                      list fc-minute15prbs-time-line-instance {
                        key "number";
                        description
                          "FC controller 15 minute PRBS layer
                           historical performance data";
                        leaf number {
                          type uint32 {
                            range "1..32";
                          }
                          description
                            "History Index number";
                        }
                        uses PM-PRBS-PARAS;
                      }
                    }
                    leaf number {
                      type uint32;
                      description
                        "channel number";
                    }
                  }
                }
                container minute15fc-histories {
                  description
                    "FC controller 15 minute FC layer
                     historical performance data";
                  list minute15fc-history {
                    key "slot-number";
                    description
                      "FC controller 15 minute FC layer
                       historical performance data";
                    container minute15fc-time-line-instances {
                      description
                        "FC controller 15 minute FC layer
                         historical performance data";
                      list minute15fc-time-line-instance {
                        key "number";
                        description
                          "FC controller 15 minute FC layer
                           historical performance data";
                        leaf number {
                          type uint32 {
                            range "1..32";
                          }
                          description
                            "History Index number";
                        }
                        uses PM-FC-PARAS;
                      }
                    }
                    leaf slot-number {
                      type uint32;
                      description
                        "interval slot number";
                    }
                  }
                }
                container fc-minute15pcs-histories {
                  description
                    "FC controller 15 minute PCS layer
                     historical performance data";
                  list fc-minute15pcs-history {
                    key "slot-number";
                    description
                      "FC controller 15 minute PCS layer
                       historical performance data";
                    container fc-minute15pcs-time-line-instances {
                      description
                        "FC controller 15 minute PCS layer
                         historical performance data";
                      list fc-minute15pcs-time-line-instance {
                        key "number";
                        description
                          "FC controller 15 minute PCS layer
                           historical performance data";
                        leaf number {
                          type uint32 {
                            range "1..32";
                          }
                          description
                            "History Index number";
                        }
                        uses PM-PCS-PARAS;
                      }
                    }
                    leaf slot-number {
                      type uint32;
                      description
                        "interval slot number";
                    }
                  }
                }
              }
              container fc-second30-history {
                description
                  "FC controller 30 second historical
                   performance data";
                container fc-second30fec-histories {
                  description
                    "FC controller 30 second FEC layer
                     historical performance data";
                  list fc-second30fec-history {
                    key "slot-number";
                    description
                      "FC controller 30 second FEC layer
                       historical performance data";
                    container fc-second30fec-time-line-instances {
                      description
                        "FC controller 30 second FEC layer
                         historical performance data";
                      list fc-second30fec-time-line-instance {
                        key "number";
                        description
                          "FC controller 30 second FEC layer
                           historical performance data";
                        leaf number {
                          type uint32 {
                            range "1..30";
                          }
                          description
                            "History Index number";
                        }
                        uses PM-FC-PARAS;
                      }
                    }
                    leaf slot-number {
                      type uint32;
                      description
                        "interval slot number";
                    }
                  }
                }
                container fc-second30prbs-histories {
                  description
                    "FC controller 30 second PRBS layer
                     historical performance data";
                  list fc-second30prbs-history {
                    key "number";
                    description
                      "FC controller 30 second PRBS layer
                       historical performance data";
                    container fc-second30prbs-time-line-instances {
                      description
                        "FC controller 30 second PRBS layer
                         historical performance data";
                      list fc-second30prbs-time-line-instance {
                        key "number";
                        description
                          "FC controller 30 second PRBS layer
                           historical performance data";
                        leaf number {
                          type uint32 {
                            range "1..30";
                          }
                          description
                            "History Index number";
                        }
                        uses PM-PRBS-PARAS;
                      }
                    }
                    leaf number {
                      type uint32;
                      description
                        "channel number";
                    }
                  }
                }
                container fc-second30pcs-histories {
                  description
                    "FC controller 30 second PCS layer
                     historical performance data";
                  list fc-second30pcs-history {
                    key "slot-number";
                    description
                      "FC controller 30 second PCS layer
                       historical performance data";
                    container fc-second30pcs-time-line-instances {
                      description
                        "FC controller 30 second PCS layer
                         historical performance data";
                      list fc-second30pcs-time-line-instance {
                        key "number";
                        description
                          "FC controller 30 second PCS layer
                           historical performance data";
                        leaf number {
                          type uint32 {
                            range "1..30";
                          }
                          description
                            "History Index number";
                        }
                        uses PM-FC-PARAS;
                      }
                    }
                    leaf slot-number {
                      type uint32;
                      description
                        "interval slot number";
                    }
                  }
                }
                container second30fc-histories {
                  description
                    "FC controller 30 second FC layer
                     historical performance data";
                  list second30fc-history {
                    key "slot-number";
                    description
                      "FC controller 30 second FC layer
                       historical performance data";
                    container second30fc-time-line-instances {
                      description
                        "FC controller 30 second FC layer
                         historical performance data";
                      list second30fc-time-line-instance {
                        key "number";
                        description
                          "FC controller 30 second FC layer
                           historical performance data";
                        leaf number {
                          type uint32 {
                            range "1..30";
                          }
                          description
                            "History Index number";
                        }
                        uses PM-FC-PARAS;
                      }
                    }
                    leaf slot-number {
                      type uint32;
                      description
                        "interval slot number";
                    }
                  }
                }
              }
              container fc-hour24-history {
                description
                  "FC controller 24 hour historical
                   performance data";
                container fc-hour24pcs-histories {
                  description
                    "FC controller 24 hour PCS layer historical
                     performance data";
                  list fc-hour24pcs-history {
                    key "number";
                    description
                      "FC controller 24 hour PCS layer
                       historical performance data";
                    container fc-hour24pcs-time-line-instances {
                      description
                        "FC controller 24 hour PCS layer
                         historical performance data";
                      list fc-hour24pcs-time-line-instance {
                        key "number";
                        description
                          "FC controller 24 hour PCS layer
                           historical performance data";
                        leaf number {
                          type uint32 {
                            range "1";
                          }
                          description
                            "History Index number";
                        }
                        uses PM-PCS-PARAS;
                      }
                    }
                    leaf number {
                      type uint32;
                      description
                        "channel number";
                    }
                  }
                }
                container fc-hour24fec-histories {
                  description
                    "FC controller 24 hour FEC layer historical
                     performance data";
                  list fc-hour24fec-history {
                    key "number";
                    description
                      "FC controller 24 hour FEC layer
                       historical performance data";
                    container fc-hour24fec-time-line-instances {
                      description
                        "FC controller 24 hour FEC layer
                         historical performance data";
                      list fc-hour24fec-time-line-instance {
                        key "number";
                        description
                          "FC controller 24 hour FEC layer
                           historical performance data";
                        leaf number {
                          type uint32 {
                            range "1";
                          }
                          description
                            "History Index number";
                        }
                        uses PM-FEC-PARAS;
                      }
                    }
                    leaf number {
                      type uint32;
                      description
                        "channel number";
                    }
                  }
                }
                container fc-hour24fc-histories {
                  description
                    "FC controller 24 hour FC layer historical
                     performance data";
                  list fc-hour24fc-history {
                    key "number";
                    description
                      "FC controller 24 hour FC layer historical
                       performance data";
                    container fc-hour24fc-time-line-instances {
                      description
                        "FC controller 24 hour FC layer
                         historical performance data";
                      list fc-hour24fc-time-line-instance {
                        key "number";
                        description
                          "FC controller 24 hour FC layer
                           historical performance data";
                        leaf number {
                          type uint32 {
                            range "1";
                          }
                          description
                            "History Index number";
                        }
                        uses PM-FC-PARAS;
                      }
                    }
                    leaf number {
                      type uint32;
                      description
                        "channel number";
                    }
                  }
                }
                container fc-hour24prbs-histories {
                  description
                    "FC controller 24 hour PRBS layer
                     historical performance data";
                  list fc-hour24prbs-history {
                    key "number";
                    description
                      "FC controller 24 hour PRBS layer
                       historical performance data";
                    container fc-hour24prbs-time-line-instances {
                      description
                        "FC controller 24 hour PRBS layer
                         historical performance data";
                      list fc-hour24prbs-time-line-instance {
                        key "number";
                        description
                          "FC controller 24 hour PRBS layer
                           historical performance data";
                        leaf number {
                          type uint32 {
                            range "1";
                          }
                          description
                            "History Index number";
                        }
                        uses PM-PRBS-PARAS;
                      }
                    }
                    leaf number {
                      type uint32;
                      description
                        "channel number";
                    }
                  }
                }
              }
              leaf name {
                type xr:Interface-name;
                description
                  "Port name";
              }
            }
          }
        }
        container optics-history {
          description
            "OPTICS controller History performance data";
          container optics-port-histories {
            description
              "Port performance data";
            list optics-port-history {
              key "name";
              description
                "Port performance data";
              container optics-hour24-history {
                description
                  "port current performance data";
                container optics-hour24-optics-histories {
                  description
                    "port 24 hour performance data";
                  list optics-hour24-optics-history {
                    key "number";
                    description
                      "port 24 hour optics performance data";
                    container optics-hour24-optics-time-line-instances {
                      description
                        "port current performance data";
                      list optics-hour24-optics-time-line-instance {
                        key "number";
                        description
                          "port 24-hour optics performance data";
                        leaf number {
                          type uint32 {
                            range "1..7";
                          }
                          description
                            "History Index number";
                        }
                        uses PM-OPTICS-PARAS;
                      }
                    }
                    leaf number {
                      type uint32;
                      description
                        "channel number";
                    }
                  }
                }
                container optics-hour24fec-histories {
                  description
                    "port current performance data";
                  list optics-hour24fec-history {
                    key "number";
                    description
                      "port 24 hour fec performance data";
                    container optics-hour24fec-time-line-instances {
                      description
                        "port current performance data";
                      list optics-hour24fec-time-line-instance {
                        key "number";
                        description
                          "port 15-minute fec performance data";
                        leaf number {
                          type uint32 {
                            range "1";
                          }
                          description
                            "History Index number";
                        }
                        uses PM-FEC-PARAS;
                      }
                    }
                    leaf number {
                      type uint32;
                      description
                        "channel number";
                    }
                  }
                }
              }
              container optics-second30-history {
                description
                  "port current performance data";
                container optics-second30-optics-histories {
                  description
                    "port current performance data";
                  list optics-second30-optics-history {
                    key "number";
                    description
                      "port 30-second optics performance data";
                    container optics-second30-optics-time-line-instances {
                      description
                        "port current performance data";
                      list optics-second30-optics-time-line-instance {
                        key "number";
                        description
                          "port 30 second otn performance data";
                        leaf number {
                          type uint32 {
                            range "1..30";
                          }
                          description
                            "History Index number";
                        }
                        uses PM-OPTICS-PARAS;
                      }
                    }
                    leaf number {
                      type uint32;
                      description
                        "channel number";
                    }
                  }
                }
                container optics-second30fec-histories {
                  description
                    "port current performance data";
                  list optics-second30fec-history {
                    key "number";
                    description
                      "port 30-second fec performance data";
                    container optics-second30fec-time-line-instances {
                      description
                        "port current performance data";
                      list optics-second30fec-time-line-instance {
                        key "number";
                        description
                          "port sec-30 fec performance data";
                        leaf number {
                          type uint32 {
                            range "1..30";
                          }
                          description
                            "History Index number";
                        }
                        uses PM-FEC-PARAS;
                      }
                    }
                    leaf number {
                      type uint32;
                      description
                        "channel number";
                    }
                  }
                }
              }
              container optics-minute15-history {
                description
                  "port current performance data";
                container optics-minute15-optics-histories {
                  description
                    "port current performance data";
                  list optics-minute15-optics-history {
                    key "number";
                    description
                      "port 15-minute optics performance data";
                    container optics-minute15-optics-time-line-instances {
                      description
                        "port current performance data";
                      list optics-minute15-optics-time-line-instance {
                        key "number";
                        description
                          "port 15-minute otn performance data";
                        leaf number {
                          type uint32 {
                            range "1..32";
                          }
                          description
                            "History Index number";
                        }
                        uses PM-OPTICS-PARAS;
                      }
                    }
                    leaf number {
                      type uint32;
                      description
                        "channel number";
                    }
                  }
                }
                container optics-minute15fec-histories {
                  description
                    "port current performance data";
                  list optics-minute15fec-history {
                    key "number";
                    description
                      "port 15-minute fec performance data";
                    container optics-minute15fec-time-line-instances {
                      description
                        "port current performance data";
                      list optics-minute15fec-time-line-instance {
                        key "number";
                        description
                          "port 15-minute fec performance data";
                        leaf number {
                          type uint32 {
                            range "1..32";
                          }
                          description
                            "History Index number";
                        }
                        uses PM-FEC-PARAS;
                      }
                    }
                    leaf number {
                      type uint32;
                      description
                        "channel number";
                    }
                  }
                }
              }
              leaf name {
                type xr:Interface-name;
                description
                  "Port name";
              }
            }
          }
        }
        container oc-history {
          description
            "OC controller History performance data";
          container oc-port-histories {
            description
              "Port performance data";
            list oc-port-history {
              key "name";
              description
                "Port performance data";
              container oc-second30-history {
                description
                  "OC controller 30 second historical
                   performance data";
                container oc-second30prbs-histories {
                  description
                    "OC controller 30 second PRBS layer
                     historical performance data";
                  list oc-second30prbs-history {
                    key "number";
                    description
                      "OC controller 30 second PRBS layer
                       historical performance data";
                    container oc-second30prbs-time-line-instances {
                      description
                        "OC controller 30 second PRBS layer
                         historical performance data";
                      list oc-second30prbs-time-line-instance {
                        key "number";
                        description
                          "OC controller 30 second PRBS layer
                           historical performance data";
                        leaf number {
                          type uint32 {
                            range "1..30";
                          }
                          description
                            "History Index number";
                        }
                        uses PM-PRBS-PARAS;
                      }
                    }
                    leaf number {
                      type uint32;
                      description
                        "channel number";
                    }
                  }
                }
              }
              container oc-hour24-history {
                description
                  "port current performance data";
                container oc-hour24prbs-histories {
                  description
                    "OC controller 24 hour PRBS layer
                     historical performance data";
                  list oc-hour24prbs-history {
                    key "number";
                    description
                      "OC controller 24 hour PRBS layer
                       historical performance data";
                    container oc-hour24prbs-time-line-instances {
                      description
                        "OC controller 24 hour PRBS layer
                         historical performance data";
                      list oc-hour24prbs-time-line-instance {
                        key "number";
                        description
                          "OC controller 24 hour PRBS layer
                           historical performance data";
                        leaf number {
                          type uint32 {
                            range "1";
                          }
                          description
                            "History Index number";
                        }
                        uses PM-PRBS-PARAS;
                      }
                    }
                    leaf number {
                      type uint32;
                      description
                        "channel number";
                    }
                  }
                }
                container oc-hour24ocn-histories {
                  description
                    "port current performance data";
                  list oc-hour24ocn-history {
                    key "number";
                    description
                      "port 24 hour ocn performance data";
                    container oc-hour24ocn-time-line-instances {
                      description
                        "port current performance data";
                      list oc-hour24ocn-time-line-instance {
                        key "number";
                        description
                          "port 15-minute otn performance data";
                        leaf number {
                          type uint32 {
                            range "1";
                          }
                          description
                            "History Index number";
                        }
                        uses PM-SONET-PARAS;
                      }
                    }
                    leaf number {
                      type uint32;
                      description
                        "channel number";
                    }
                  }
                }
              }
              container oc-minute15-history {
                description
                  "port current performance data";
                container oc-minute15ocn-histories {
                  description
                    "port current performance data";
                  list oc-minute15ocn-history {
                    key "number";
                    description
                      "port 15-minute ocn performance data";
                    container oc-minute15ocn-time-line-instances {
                      description
                        "port current performance data";
                      list oc-minute15ocn-time-line-instance {
                        key "number";
                        description
                          "port 15-minute ocn performance data";
                        leaf number {
                          type uint32 {
                            range "1..32";
                          }
                          description
                            "History Index number";
                        }
                        uses PM-SONET-PARAS;
                      }
                    }
                    leaf number {
                      type uint32;
                      description
                        "channel number";
                    }
                  }
                }
                container oc-minute15prbs-histories {
                  description
                    "OC controller 15 minute PRBS layer
                     historical performance data";
                  list oc-minute15prbs-history {
                    key "number";
                    description
                      "OC controller 15 minute PRBS layer
                       historical performance data";
                    container oc-minute15prbs-time-line-instances {
                      description
                        "OC controller 15 minute PRBS layer
                         historical performance data";
                      list oc-minute15prbs-time-line-instance {
                        key "number";
                        description
                          "OC controller 15 minute PRBS layer
                           historical performance data";
                        leaf number {
                          type uint32 {
                            range "1..32";
                          }
                          description
                            "History Index number";
                        }
                        uses PM-PRBS-PARAS;
                      }
                    }
                    leaf number {
                      type uint32;
                      description
                        "channel number";
                    }
                  }
                }
              }
              leaf name {
                type xr:Interface-name;
                description
                  "Port name";
              }
            }
          }
        }
      }
    }
  }
}
