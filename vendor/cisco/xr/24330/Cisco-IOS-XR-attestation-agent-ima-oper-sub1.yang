submodule Cisco-IOS-XR-attestation-agent-ima-oper-sub1 {
  belongs-to Cisco-IOS-XR-attestation-agent-ima-oper {
    prefix Cisco-IOS-XR-attestation-agent-ima-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR attestation-agent-ima package operational data.
     
     Copyright (c) 2013-2022 by Cisco Systems, Inc.
     All rights reserved.";

  revision 2022-07-29 {
    description
      "Changed a few entries in bag from character array to string.";
    semver:module-version "1.1.0";
  }
  revision 2021-07-19 {
    description
      "Added total_count under cron job stat bag.";
    semver:module-version "1.1.0";
  }
  revision 2020-09-21 {
    description
      "Fixed bag mismatch issue for dossier stat.";
    semver:module-version "1.0.0";
  }
  revision 2020-09-15 {
    description
      "Added task for netconf support.";
  }
  revision 2019-04-05 {
    description
      "Establish semantic version baseline.";
  }
  revision 2015-11-09 {
    description
      "IOS XR 6.0 revision.";
  }

  grouping CACHE-BLOCK-SUMMARY {
    description
      "CACHE BLOCK SUMMARY";
    leaf block-start {
      type uint32;
      description
        "block start event number";
    }
    leaf block-end {
      type uint32;
      description
        "block end event number";
    }
    leaf block-size {
      type uint32;
      description
        "block size in MB";
    }
    leaf duplicate-events {
      type uint32;
      description
        "total no. of duplicate events in block";
    }
    leaf unique-events {
      type uint32;
      description
        "total no. of unique events in block";
    }
    leaf block-name {
      type string;
      description
        "block name";
    }
    leaf timestamp {
      type string;
      description
        "last modified";
    }
    leaf create-time {
      type string;
      description
        "timestamp when block was created";
    }
    leaf block-exists {
      type string;
      description
        "TRUE if block is present FALSE if block is
         deleted";
    }
  }

  grouping NODE-BLOCK-SUMMARY {
    description
      "NODE BLOCK SUMMARY";
    leaf node-name {
      type string;
      description
        "node name";
    }
    list block {
      description
        "list of blocks for this node";
      uses CACHE-BLOCK-SUMMARY;
    }
  }

  grouping BLOCK-DET {
    description
      "BLOCK DET";
    list node-block {
      description
        "node block";
      uses NODE-BLOCK-SUMMARY;
    }
  }

  grouping CACHE-SUMMARY {
    description
      "CACHE SUMMARY";
    leaf total-blocks {
      type uint32;
      description
        "total blocks in cache";
    }
    leaf cache-size {
      type uint32;
      description
        "total cache size in MB";
    }
    leaf total-events {
      type uint32;
      description
        "total no. of events in cache";
    }
    leaf duplicate-events {
      type uint32;
      description
        "total no. of duplicate events in cache";
    }
    leaf unique-events {
      type uint32;
      description
        "total no. of unique events in cache";
    }
    leaf node-name {
      type string;
      description
        "node name";
    }
    leaf timestamp {
      type string;
      description
        "last modified";
    }
  }

  grouping CACHE-DET {
    description
      "CACHE DET";
    list cache {
      description
        "cache";
      uses CACHE-SUMMARY;
    }
  }

  grouping CRON-STAT {
    description
      "CRON STAT";
    leaf run-time {
      type uint32;
      units "second";
      description
        "average run time in secs";
    }
    leaf averag-blocks-read {
      type uint32;
      description
        "average no of IMA signed blocks read";
    }
    leaf success-count {
      type uint32;
      description
        "successful run count";
    }
    leaf failure-count {
      type uint32;
      description
        "failure count";
    }
    leaf periodicity {
      type uint32;
      description
        "Periodicity of cron job";
    }
    leaf no-update-count {
      type uint32;
      description
        "No. of times cron-job ran without reading any
         data";
    }
    leaf timestamp {
      type string;
      description
        "last instant ran";
    }
    leaf node-name {
      type string;
      description
        "node name";
    }
    leaf total-count {
      type uint32;
      description
        "Total run count";
    }
  }

  grouping CRON-DET {
    description
      "CRON DET";
    list cron {
      description
        "cron";
      uses CRON-STAT;
    }
  }

  grouping DOSSIER-STAT {
    description
      "DOSSIER STAT";
    leaf success-count {
      type uint32;
      description
        "dossier successfull execution count";
    }
    leaf fail-count {
      type uint32;
      description
        "dossier failure count";
    }
    leaf avg-time {
      type uint32;
      description
        "avg time taken for dossier execution";
    }
  }

  grouping BLOCK-VALIDITY {
    description
      "BLOCK VALIDITY";
    leaf chunk-start-event {
      type uint32;
      description
        "Corrupted chunk start number";
    }
    leaf chunk-end-event {
      type uint32;
      description
        "Corrupted chunk end event";
    }
  }

  grouping BLOCK-VALIDITY-SUMMARY {
    description
      "BLOCK VALIDITY SUMMARY";
    leaf node-name {
      type string;
      description
        "node name";
    }
    list chunk {
      description
        "list of starting event of corrupted chunk";
      uses BLOCK-VALIDITY;
    }
  }

  grouping BLOCK-VALID-DET {
    description
      "BLOCK VALID DET";
    list node {
      description
        "node";
      uses BLOCK-VALIDITY-SUMMARY;
    }
  }
}
