module Cisco-IOS-XR-ip-rsvp-cfg {
  namespace "http://cisco.com/ns/yang/Cisco-IOS-XR-ip-rsvp-cfg";
  prefix ip-rsvp-cfg;

  import ietf-inet-types {
    prefix inet;
  }
  import Cisco-IOS-XR-types {
    prefix xr;
  }
  import cisco-semver {
    prefix semver;
  }
  import Cisco-IOS-XR-snmp-agent-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ip-rsvp package configuration.
     
     This model is deprecated and is replaced by
     Cisco-IOS-XR-um-rsvp-cfg.yang which will provide the
     compatible functionalities.
     
     This module contains definitions
     for the following management objects:
       rsvp: Global RSVP configuration commands
     
     This YANG module augments the
       Cisco-IOS-XR-snmp-agent-cfg
     module with configuration data.
     
     Copyright (c) 2013-2023 by Cisco Systems, Inc.
     All rights reserved.";

  revision 2023-10-10 {
    description
      "Added container global-retransmit-timer and type Rsvp-gbl-rr-timer-cfg to support RSVP Global retransmit timer CLI
       2023-06-16
         Added enable-rsvp leaf.
       2023-02-22
         Added global-refresh-reduction disable and global-authentication disable.
       2022-04-25
         Added ReliableRetransmitQueueDepth under RefreshReduction as the result of unhidding the CLI.";
    semver:module-version "1.2.0";
  }
  revision 2019-09-20 {
    description
      "missing some containers under rsvp.signalling.graceful-restart in the RSVP UM cfg model";
    semver:module-version "1.1.0";
  }
  revision 2019-04-05 {
    description
      "Establish semantic version baseline.";
    semver:module-version "1.0.0";
  }
  revision 2017-05-01 {
    description
      "Fixing backward compatibility error in module.";
  }
  revision 2015-11-09 {
    description
      "IOS XR 6.0 revision.";
  }

  typedef Rsvp-rdm {
    type enumeration {
      enum "rdm" {
        value 1;
        description
          "RDM Keyword Specified";
      }
      enum "not-specified" {
        value 2;
        description
          "RDM Keyword Not Specified";
      }
      enum "use-default-bandwidth" {
        value 3;
        description
          "Use Default Bandwidth - 75% Link Bandwidth";
      }
    }
    description
      "Rsvp rdm";
  }

  typedef Rsvp-bc0 {
    type enumeration {
      enum "bc0" {
        value 1;
        description
          "Keyword is bc0";
      }
      enum "global-pool" {
        value 2;
        description
          "Keyword is global-pool";
      }
      enum "not-specified" {
        value 3;
        description
          "Keyword is not specified";
      }
    }
    description
      "Rsvp bc0";
  }

  typedef Rsvp-gbl-rr-timer-cfg {
    type enumeration {
      enum "all-option" {
        value 1;
        description
          "All Configuration for global retransmit timer";
      }
      enum "backup-option" {
        value 2;
        description
          "Backup Configuration for backup-only retransmit
           timers";
      }
    }
    description
      "Rsvp gbl rr timer cfg";
  }

  typedef Rsvp-bw-cfg {
    type enumeration {
      enum "absolute" {
        value 0;
        description
          "Configuration is in absolute bandwidth values";
      }
      enum "percentage" {
        value 1;
        description
          "Configuration is in percentage of physical
           bandwidth values";
      }
    }
    description
      "Rsvp bw cfg";
  }

  typedef Rsvp-bc1 {
    type enumeration {
      enum "bc1" {
        value 1;
        description
          "Keyword is bc1";
      }
      enum "sub-pool" {
        value 2;
        description
          "Keyword is sub-pool";
      }
    }
    description
      "Rsvp bc1";
  }

  grouping AUTHENTICATION {
    description
      "Common node of rsvp, interface, neighbor";
    container authentication {
      description
        "Configure RSVP authentication";
      leaf life-time {
        type uint32 {
          range "30..86400";
        }
        units "second";
        description
          "Life time (in seconds) for each security
           association";
      }
      leaf enable {
        type boolean;
        description
          "Enable or disable RSVP authentication";
      }
      leaf window-size {
        type uint32 {
          range "1..64";
        }
        description
          "Window-size to limit number of out-of-order
           messages";
      }
      leaf key-chain {
        type xr:Cisco-ios-xr-string {
          length "1..32";
        }
        description
          "Key chain to authenticate RSVP signalling
           messages";
      }
      leaf disable {
        type boolean;
        description
          "Disable RSVP authentication";
      }
    }
  }

  grouping OUT-OF-BAND {
    description
      "Common node of cntl-signalling, if-signalling";
    container out-of-band {
      description
        "Configure RSVP out-of-band signalling parameters";
      leaf missed-messages {
        type uint32 {
          range "1..110000";
        }
        default "38000";
        description
          "Configure max number of consecutive missed
           messages for state expiry for out-of-band
           tunnels";
      }
      leaf refresh-interval {
        type uint32 {
          range "180..86400";
        }
        units "second";
        description
          "Configure interval between successive refreshes
           for out-of-band tunnels";
      }
    }
  }

  augment "/a1:snmp/a1:notification" {
    description
      "This augment extends the configuration data of
       'Cisco-IOS-XR-snmp-agent-cfg'";
    container rsvp {
      status deprecated;
      description
        "This model is deprecated and is replaced by
         Cisco-IOS-XR-um-rsvp-cfg.yang which will provide
         the compatible functionalities.  Enable RSVP-MIB
         notifications";
      leaf lost-flow {
        type empty;
        description
          "Enable lostFlow notification";
      }
      leaf new-flow {
        type empty;
        description
          "Enable newFlow notification";
      }
      leaf enable {
        type empty;
        description
          "Enable all RSVP notifications";
      }
    }
  }
  container rsvp {
    status deprecated;
    description
      "This model is deprecated and is replaced by
       Cisco-IOS-XR-um-rsvp-cfg.yang which will provide
       the compatible functionalities.  Global RSVP
       configuration commands";
    container neighbors {
      description
        "RSVP Neighbor Table";
      list neighbor {
        key "neighbor";
        description
          "RSVP neighbor configuration";
        leaf neighbor {
          type inet:ipv4-address-no-zone;
          description
            "Neighbor IP address";
        }
        uses AUTHENTICATION;
      }
    }
    container controllers {
      description
        "Controller table";
      list controller {
        key "controller-name";
        description
          "Controller configuration";
        container cntl-signalling {
          description
            "Configure RSVP signalling parameters";
          uses OUT-OF-BAND;
        }
        leaf enable {
          type empty;
          description
            "Enable RSVP on an interface";
        }
        leaf controller-name {
          type xr:Interface-name;
          description
            "Name of controller";
        }
      }
    }
    container global-logging {
      description
        "Global Logging";
      leaf log-nsr-status {
        type empty;
        description
          "Enable NSR Status Logging";
      }
      leaf log-issu-status {
        type empty;
        description
          "Enable ISSU Status Logging";
      }
    }
    container global-bandwidth {
      description
        "Configure Global Bandwidth Parameters";
      container default-interface-percent {
        description
          "Configure Global RSVP signalling parameters";
        container mam {
          description
            "Configure global default MAM I/F percent
             bandwidth parameters";
          leaf max-res-percent {
            type uint32 {
              range "0..10000";
            }
            description
              "Default maximum reservable I/F % B/W ";
          }
          leaf bc0-percent {
            type uint32 {
              range "0..10000";
            }
            description
              "Default BC0 pool I/F % B/W ";
          }
          leaf bc1-percent {
            type uint32 {
              range "0..10000";
            }
            description
              "Default BC1 pool I/F % B/W ";
          }
        }
        container rdm {
          description
            "Configure global default RDM I/F percent
             bandwidth parameters";
          leaf bc0-percent {
            type uint32 {
              range "0..10000";
            }
            description
              "Default BC0 pool I/F % B/W ";
          }
          leaf bc1-percent {
            type uint32 {
              range "0..10000";
            }
            description
              "Default BC1 pool I/F % B/W ";
          }
        }
      }
    }
    container interfaces {
      description
        "Interface table";
      list interface {
        key "name";
        description
          "Interface configuration";
        container if-signalling {
          description
            "Configure RSVP signalling parameters";
          container refresh-reduction {
            description
              "Configure RSVP Refresh Reduction parameters";
            leaf disable {
              type empty;
              description
                "Disable refresh reduction";
            }
            leaf reliable-ack-max-size {
              type uint32 {
                range "20..65000";
              }
              units "byte";
              default "4096";
              description
                "Configure max size of a single RSVP ACK
                 message";
            }
            leaf reliable-ack-hold-time {
              type uint32 {
                range "100..5000";
              }
              units "millisecond";
              default "400";
              description
                "Configure hold time for sending RSVP ACK
                 message(s)";
            }
            leaf reliable-retransmit-time {
              type uint32 {
                range "100..10000";
              }
              units "millisecond";
              default "2100";
              description
                "Configure min delay to wait for an ACK
                 before a retransmit";
            }
            leaf reliable-s-refresh {
              type empty;
              description
                "Configure use of reliable messaging for
                 summary refresh";
            }
            leaf summary-max-size {
              type uint32 {
                range "20..65000";
              }
              units "byte";
              default "4096";
              description
                "Configure max size of a single RSVP summary
                 refresh message";
            }
            leaf reliable-retransmit-queue-depth {
              type uint32 {
                range "0..200000";
              }
              description
                "Retransmit queue depth (# sub-msg's)";
            }
            leaf bundle-message-max-size {
              type uint32 {
                range "512..65000";
              }
              units "byte";
              default "4096";
              description
                "Configure maximum size of a single RSVP
                 Bundle message";
            }
          }
          container interval-rate {
            description
              "Configure number of messages to be sent per
               interval";
            leaf messages-per-interval {
              type uint32 {
                range "1..500";
              }
              default "100";
              description
                "Number of messages to be sent per interval";
            }
            leaf interval-size {
              type uint32 {
                range "250..2000";
              }
              units "millisecond";
              default "1000";
              description
                "Size of an interval (milliseconds)";
            }
          }
          leaf dscp {
            type uint32 {
              range "0..63";
            }
            description
              "Differentiated Services Code Point (DSCP)";
          }
          leaf missed-messages {
            type uint32 {
              range "1..8";
            }
            default "4";
            description
              "Configure max number of consecutive missed
               messages for state expiry";
          }
          leaf hello-graceful-restart-if-based {
            type empty;
            description
              "Enable IF-based Hello adjacency on a RSVP
               interface";
          }
          leaf pacing {
            type empty;
            description
              "Enable rate-limiting on the interface";
          }
          leaf refresh-interval {
            type uint32 {
              range "10..180";
            }
            units "second";
            default "45";
            description
              "Configure interval between successive
               refreshes";
          }
          uses OUT-OF-BAND;
        }
        container bandwidth {
          description
            "Configure Bandwidth";
          container mam {
            description
              "Configure MAM bandwidth parameters";
            leaf max-resv-bandwidth {
              type uint32 {
                range "0..4294967295";
              }
              description
                "Maximum reservable bandwidth (Kbps or
                 percent of physical bandwidth)";
            }
            leaf max-resv-flow {
              type uint32 {
                range "0..4294967295";
              }
              description
                "Largest reservable flow (Kbps or percent of
                 physical bandwidth)";
            }
            leaf bc0-bandwidth {
              type uint32 {
                range "0..4294967295";
              }
              description
                "Reservable bandwidth in BC0 (Kbps or percent
                 of physical bandwidth)";
            }
            leaf bc1-bandwidth {
              type uint32 {
                range "0..4294967295";
              }
              description
                "Reservable bandwidth in BC1 (Kbps or percent
                 of physical bandwidth)";
            }
            leaf bandwidth-mode {
              type Rsvp-bw-cfg;
              units "percentage";
              description
                "Absolute or Percentage bandwidth mode";
            }
          }
          container rdm {
            description
              "Configure RDM bandwidth parameters";
            leaf max-resv-flow {
              when "../rdm-keyword = 'rdm' or ../rdm-keyword = 'not-specified'" {
                description
                  "../RDMKeyword = RDM or ../RDMKeyword =
                   NotSpecified";
              }
              type uint32 {
                range "0..4294967295";
              }
              description
                "Largest reservable flow (Kbps or percent of
                 physical bandwidth)";
            }
            leaf bc0-bandwidth {
              when "../rdm-keyword = 'rdm' or ../rdm-keyword = 'not-specified'" {
                description
                  "../RDMKeyword = RDM or ../RDMKeyword =
                   NotSpecified";
              }
              type uint32 {
                range "0..4294967295";
              }
              description
                "Reservable bandwidth in BC0 (Kbps or percent
                 of physical bandwidth)";
            }
            leaf bc1-bandwidth {
              when "../rdm-keyword = 'rdm' or ../rdm-keyword = 'not-specified'" {
                description
                  "../RDMKeyword = RDM or ../RDMKeyword =
                   NotSpecified";
              }
              type uint32 {
                range "0..4294967295";
              }
              description
                "Reservable bandwidth in BC1 (Kbps or percent
                 of physical bandwidth)";
            }
            leaf rdm-keyword {
              type Rsvp-rdm;
              description
                "Set requests should always use RDM";
            }
            leaf bc0-keyword {
              when "../rdm-keyword = 'rdm' or ../rdm-keyword = 'not-specified'" {
                description
                  "../RDMKeyword = RDM or ../RDMKeyword =
                   NotSpecified";
              }
              type Rsvp-bc0;
              description
                "Set requests should always use BC0";
            }
            leaf bc1-keyword {
              when "../rdm-keyword = 'rdm' or ../rdm-keyword = 'not-specified'" {
                description
                  "../RDMKeyword = RDM or ../RDMKeyword =
                   NotSpecified";
              }
              type Rsvp-bc1;
              description
                "Set requests should always use BC1";
            }
            leaf bandwidth-mode {
              when "../rdm-keyword = 'rdm' or ../rdm-keyword = 'not-specified'" {
                description
                  "../RDMKeyword = RDM or ../RDMKeyword =
                   NotSpecified";
              }
              type Rsvp-bw-cfg;
              units "percentage";
              description
                "Absolute or Percentage bandwidth mode";
            }
          }
        }
        leaf name {
          type xr:Interface-name;
          description
            "Name of interface";
        }
        uses AUTHENTICATION;
      }
    }
    container signalling {
      description
        "Configure Global RSVP signalling parameters";
      container global-out-of-band {
        description
          "Configure out-of-band signalling parameters";
        leaf vrf {
          type xr:Cisco-ios-xr-string {
            length "1..32";
          }
          description
            "VRF used for out-of-band control signalling";
        }
      }
      container global-refresh-reduction {
        description
          "Configure RSVP Refresh Reduction parameters";
        container global-retransmit-timer {
          description
            "Global retransmit timer";
          leaf global-retransmit-timer-option {
            type Rsvp-gbl-rr-timer-cfg;
            description
              "global retransmit timer option";
          }
          leaf retransmit-time {
            type uint32 {
              range "100..10000";
            }
            units "millisecond";
            description
              "Min time before RSVP messages retransmit
               (milliseconds)";
          }
        }
        leaf disable {
          type empty;
          description
            "Disable refresh reduction";
        }
      }
      container graceful-restart {
        description
          "Configure RSVP Graceful-Restart parameters";
        container lsp-class-type {
          description
            "Send LSP's ctype for recovery and suggested
             label";
          leaf enable {
            type boolean;
            description
              "Send LSP's ctype for recovery and suggested
               label";
          }
        }
        leaf enable {
          type boolean;
          description
            "Enable RSVP graceful restart";
        }
        leaf restart-time {
          type uint32 {
            range "60..3600";
          }
          units "second";
          default "120";
          description
            "Graceful restart time (seconds)";
        }
        leaf recovery-time {
          type uint32 {
            range "0..3600";
          }
          units "second";
          default "120";
          description
            "Graceful restart recovery time (seconds)";
        }
      }
      container prefix-filtering {
        description
          "Configure prefix filtering parameters";
        container default-deny-action {
          description
            "Configure RSVP behaviour for scenarios where
             ACL match yields a default (implicit) deny";
          leaf drop {
            type empty;
            description
              "Configure RSVP to drop packets when ACL match
               yields a default (implicit) deny";
          }
        }
        leaf acl {
          type string {
            length "1..65";
          }
          description
            "Configure an ACL to perform prefix filtering
             of RSVP Router Alert messages";
        }
      }
      container pesr {
        description
          "Sending Path Error with State-Removal flag";
        leaf disable {
          type empty;
          description
            "Disable RSVP PESR";
        }
      }
      container checksum {
        description
          "RSVP message checksum computation";
        leaf disable {
          type empty;
          description
            "Disable RSVP message checksum computation";
        }
      }
      leaf hello-graceful-restart-misses {
        type uint32 {
          range "1..10";
        }
        default "3";
        description
          "Configure max number of consecutive missed
           Hello messages";
      }
      leaf hello-graceful-restart-interval {
        type uint32 {
          range "3000..30000";
        }
        units "millisecond";
        default "5000";
        description
          "Configure interval between successive Hello
           messages";
      }
    }
    leaf enable-rsvp {
      type empty;
      description
        "Always set to true";
    }
    uses AUTHENTICATION;
  }
}
