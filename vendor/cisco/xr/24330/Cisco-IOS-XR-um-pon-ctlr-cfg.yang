module Cisco-IOS-XR-um-pon-ctlr-cfg {
  namespace "http://cisco.com/ns/yang/Cisco-IOS-XR-um-pon-ctlr-cfg";
  prefix um-pon-ctlr-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR pon-ctlr package configuration.
     
     This YANG module augments the
     modules with configuration data.
     
     Copyright (c) 2024 by Cisco Systems, Inc.
     All rights reserved.";

  revision 2024-01-30 {
    description
      "Initial release";
    semver:module-version "1.0.0";
  }

  container pon-ctlr {
    description
      "pon-ctlr configurations";
    leaf cfg-file {
      type string {
        length "1..1024" {
          description
            "Enter PON Controller configuration file name
             Example:
             tftp://ip-address/path_to_file
             /harddisk:/path_to_file";
        }
      }
      description
        "configuration file for PON Controller";
    }
    leaf vrf {
      type xr:Cisco-ios-xr-string {
        length "1..64" {
          description
            "Name of VRF";
        }
      }
      description
        "VRF Name";
    }
    leaf tls-pem {
      type string {
        length "1..1024" {
          description
            "Enter PON Controller configuration file name
             Example:
             tftp://ip-address/path_to_file
             /harddisk:/path_to_file";
        }
      }
      description
        "TLS Certificate PEM file for PON Controller";
    }
  }
}
