//*************  DO-NOT EDIT  **************
//*********** Auto-generated file ********** 

 module cisco-xr-openconfig-system-grpc-deviations {

  namespace "http://cisco.com/ns/yang/cisco-xr-openconfig-system-grpc-deviations";
  prefix  "oc-sys-grpcdevs";

  import openconfig-system-grpc { prefix oc-sys-grpc; }
  import openconfig-system { prefix oc-sys; }

  organization "Cisco Systems, Inc.";

  contact
    "Cisco Systems, Inc.
     Customer Service

     Postal: 170 West Tasman Drive
     San Jose, CA 95134

     Tel: +1 800 553-NETS

     E-mail: cs-yang@cisco.com";

  description
    "This module contains a set of deviations for 
 
     openconfig-system-grpc.yang@2022-04-19 

     on Cisco IOS-XR devices.

     Copyright (c) 2017, 2022, 2024 by Cisco Systems, Inc.
     All rights reserved.";

  revision "2022-12-18" {
    description
      "Add deviation for oc-sys-grpc:listen-addresses";
  }
  revision "2022-07-05" {
    description
      "Initial revision applicable to IOS-XR 6.4.1";
  }


  deviation /oc-sys:system/oc-sys-grpc:grpc-servers/oc-sys-grpc:grpc-server/oc-sys-grpc:config/oc-sys-grpc:services {
    deviate not-supported;
  }
  deviation /oc-sys:system/oc-sys-grpc:grpc-servers/oc-sys-grpc:grpc-server/oc-sys-grpc:state/oc-sys-grpc:services {
    deviate not-supported;
  }
  deviation /oc-sys:system/oc-sys-grpc:grpc-servers/oc-sys-grpc:grpc-server/oc-sys-grpc:config/oc-sys-grpc:metadata-authentication {
    deviate not-supported;
  }
  deviation /oc-sys:system/oc-sys-grpc:grpc-servers/oc-sys-grpc:grpc-server {
    deviate add {
      max-elements "1";
    }
  }
  deviation /oc-sys:system/oc-sys-grpc:grpc-servers/oc-sys-grpc:grpc-server/oc-sys-grpc:config/oc-sys-grpc:listen-addresses {
    deviate add {
      default "ANY"; 
    }
  }
  deviation /oc-sys:system/oc-sys-grpc:grpc-servers/oc-sys-grpc:grpc-server/oc-sys-grpc:state/oc-sys-grpc:metadata-authentication {
    deviate not-supported;
  }
  deviation /oc-sys:system/oc-sys-grpc:grpc-servers/oc-sys-grpc:grpc-server/oc-sys-grpc:config/oc-sys-grpc:network-instance {
    deviate not-supported;
  }
  deviation /oc-sys:system/oc-sys-grpc:grpc-servers/oc-sys-grpc:grpc-server/oc-sys-grpc:state/oc-sys-grpc:network-instance {
    deviate not-supported;
  }

}
//total deviations:8
