module Cisco-IOS-XR-um-lacp-cfg {
  namespace "http://cisco.com/ns/yang/Cisco-IOS-XR-um-lacp-cfg";
  prefix um-lacp-cfg;

  import cisco-semver {
    prefix semver;
  }
  import ietf-yang-types {
    prefix yang;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR if-bundle package configuration.
     
     This YANG module augments the
     modules with configuration data.
     
     Copyright (c) 2019, 2022 by Cisco Systems, Inc.
     All rights reserved.";

  revision 2019-06-10 {
    description
      "Establish semantic version baseline.";
    semver:module-version "1.0.1";
  }
  revision 2019-03-29 {
    description
      "Initial version";
  }

  container lacp {
    description
      "Link Aggregation Control Protocol commands";
    container system {
      description
        "Set the default system parameters for LACP bundles";
      leaf priority {
        type uint32 {
          range "1..65535" {
            description
              "Priority for this system. Lower value is higher priority.";
          }
        }
        description
          "The system priority to use in LACP negotiations.";
      }
      leaf mac {
        type yang:mac-address;
        description
          "The system ID to use in LACP negotiations.";
      }
    }
  }
}
