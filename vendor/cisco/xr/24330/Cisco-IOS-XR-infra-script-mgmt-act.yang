module Cisco-IOS-XR-infra-script-mgmt-act {
  namespace "http://cisco.com/ns/yang/Cisco-IOS-XR-infra-script-mgmt-act";
  prefix script-mgmt-act;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR action package configuration.
     
     Copyright (c) 2021-2022 by Cisco Systems, Inc.
     All rights reserved.";

  revision 2021-10-23 {
    description
      "Added checksum-type to add-checksum and run. Removed 'URL' from script run";
    semver:module-version "3.0.0";
  }
  revision 2020-10-12 {
    description
      "Added container for filenames";
    semver:module-version "1.0.0";
  }
  revision 2020-10-09 {
    description
      "Added grouping for checksum";
  }
  revision 2020-10-09 {
    description
      "Added grouping for file list";
  }
  revision 2020-10-09 {
    description
      "Separated leaf-list into individual leafs";
  }
  revision 2020-10-08 {
    description
      "Initial version";
  }

  typedef SCRIPT-TYPE {
    type enumeration {
      enum "exec" {
        value 0;
        description
          "Exec script type";
      }
      enum "eem" {
        value 1;
        description
          "EEM script type";
      }
      enum "process" {
        value 2;
        description
          "Process script type";
      }
      enum "config" {
        value 3;
        description
          "Config script type";
      }
      enum "snmp" {
        value 4;
        description
          "SNMP script type";
      }
      enum "precommit" {
        value 5;
        description
          "Precommit script type";
      }
    }
    description
      "Script type";
  }

  typedef SCRIPT-TYPE-ALL {
    type enumeration {
      enum "exec" {
        value 0;
        description
          "Exec script type";
      }
      enum "eem" {
        value 1;
        description
          "EEM script type";
      }
      enum "process" {
        value 2;
        description
          "Process script type";
      }
      enum "config" {
        value 3;
        description
          "Config script type";
      }
      enum "snmp" {
        value 4;
        description
          "SNMP script type";
      }
      enum "precommit" {
        value 5;
        description
          "Precommit script type";
      }
      enum "all" {
        value 6;
        description
          "All scripts";
      }
    }
    description
      "Script type";
  }

  typedef LOG-LEVEL {
    type enumeration {
      enum "CRITICAL" {
        value 0;
        description
          "Log messages with severity CRITICAL";
      }
      enum "DEBUG" {
        value 1;
        description
          "Log messages with severity DEBUG";
      }
      enum "ERROR" {
        value 2;
        description
          "Log messages with severity ERROR";
      }
      enum "INFO" {
        value 3;
        description
          "Log messages with severity INFO";
      }
      enum "WARNING" {
        value 4;
        description
          "Log messages with severity WARNING";
      }
    }
    description
      "LOG-LEVEL";
  }

  typedef CHECKSUM-TYPE {
    type enumeration {
      enum "SHA256" {
        value 1;
        description
          "Specify an SHA256 checksum";
      }
    }
  }

  typedef update-condition {
    type enumeration {
      enum "manual" {
        value 0;
        description
          "update scripts configured for manual update";
      }
    }
    description
      "script update condition";
  }

  grouping SCRIPT-LIST {
    description
      "Scripts to add/remove";
    leaf-list script-name {
      type string {
        length "1..256";
      }
      min-elements 1;
      max-elements "10";
      description
        "Script File name to add/remove";
    }
  }

  grouping SCRIPT-CHECKSUM-LIST {
    description
      "Scripts and checksums to add";
    list script-checksums {
      key "script-name";
      min-elements 1;
      max-elements "10";
      description
        "List of script and checksum pairs to add; max 10 script/checksum pairs can be added";
      leaf script-name {
        type string {
          length "1..256";
        }
        mandatory true;
        description
          "Script File name to add";
      }
      leaf checksum-type {
        type CHECKSUM-TYPE;
        mandatory true;
        description
          "Specify a checksum for the script";
      }
      leaf checksum {
        type string {
          length "64";
        }
        mandatory true;
        description
          "SHA256 checksum value of script";
      }
    }
  }

  grouping SCRIPT-ADD-REMOVE-OUTPUT {
    description
      "Output/Response for Script Add/Remove";
    list responses {
      key "script-name";
      description
        "List of Success or error messages for the script operations";
      leaf script-name {
        type string;
        mandatory true;
        description
          "Name of script executed";
      }
      leaf response {
        type string;
        mandatory true;
        description
          "Success or error message for the operation";
      }
      leaf status {
        type string;
        mandatory true;
        description
          "success or fail";
      }
    }
  }

  rpc add {
    description
      "Add script to script repository";
    input {
      leaf script-type {
        type SCRIPT-TYPE;
        mandatory true;
        description
          "Type of script to add";
      }
      leaf vrf {
        type string {
          length "1..32";
        }
        description
          "Specify the VRF for the network file system";
      }
      leaf source {
        type string {
          length "1..1024";
        }
        mandatory true;
        description
          "Enter source directory for the script(s)
           Example:
           http://[user:password@]server[:port]/directory/
           https://[user:password@]server[:port]/directory/
           ftp://[user:password@]server[:port]/directory/
           tftp://[user:password@]server[:port]/directory/
           scp://[user@]server:/directory/
           /directory/";
      }
      leaf location {
        type string {
          length "1..20";
        }
        description
          "Fully Qualified RP location";
      }
      uses SCRIPT-LIST;
    }
    output {
      container script-add-response {
        description
          "Script Add Response";
        uses SCRIPT-ADD-REMOVE-OUTPUT;
      }
    }
  }
  rpc add-checksum {
    description
      "Add script to script repository";
    input {
      leaf script-type {
        type SCRIPT-TYPE;
        mandatory true;
        description
          "Type of script to add";
      }
      leaf vrf {
        type string {
          length "1..32";
        }
        description
          "Specify the VRF for the network file system";
      }
      leaf source {
        type string {
          length "1..1024";
        }
        mandatory true;
        description
          "Enter source directory for the script(s)
           Example:
           http://[user:password@]server[:port]/directory/
           https://[user:password@]server[:port]/directory/
           ftp://[user:password@]server[:port]/directory/
           tftp://[user:password@]server[:port]/directory/
           scp://[user@]server:/directory/
           /directory/";
      }
      leaf location {
        type string {
          length "1..20";
        }
        description
          "Fully Qualified RP location";
      }
      uses SCRIPT-CHECKSUM-LIST;
    }
    output {
      container script-add-checksum-response {
        description
          "Script Add-Checksum Response";
        uses SCRIPT-ADD-REMOVE-OUTPUT;
      }
    }
  }
  rpc remove {
    description
      "Remove script from script repository";
    input {
      leaf script-type {
        type SCRIPT-TYPE;
        mandatory true;
        description
          "Type of script to remove";
      }
      uses SCRIPT-LIST;
    }
    output {
      container script-remove-response {
        description
          "Script Remove Response";
        uses SCRIPT-ADD-REMOVE-OUTPUT;
      }
    }
  }
  rpc stop {
    description
      "Stop OP script";
    input {
      leaf request-id {
        type uint32;
        mandatory true;
        description
          "Request ID of job in queue";
      }
      leaf description {
        type string {
          length "1..512";
        }
        description
          "Reason why user wants to stop script execution";
      }
    }
    output {
      container script-stop-response {
        description
          "Script Stop Response";
        leaf response {
          type string;
          mandatory true;
          description
            "Success or error message for the operation";
        }
        leaf status {
          type string;
          mandatory true;
          description
            "success or fail";
        }
      }
    }
  }
  rpc run {
    description
      "Run Exec script from script repository";
    input {
      leaf script-name {
        type string {
          length "1..1024";
        }
        mandatory true;
        description
          "Name of Exec script to run (OR) Enter URL source. Example: [protocol]://[user:password@]server[:port]/directory/file_name";
      }
      leaf checksum-type {
        type CHECKSUM-TYPE;
        description
          "Specify a checksum for the script";
      }
      leaf checksum {
        type string {
          length "64";
        }
        description
          "Specify SHA256 checksum value of source file";
      }
      leaf vrf {
        type string {
          length "1..32";
        }
        description
          "Specify the VRF for the network file system";
      }
      leaf argument-list {
        type string {
          length "1..1024";
        }
        description
          "Script command line argument(s). FORMAT: Strings in single quotes.Escape double quotes inside string arguments(if any)";
      }
      leaf description {
        type string {
          length "1..512";
        }
        description
          "Description of script run";
      }
      leaf log-level {
        type LOG-LEVEL;
        description
          "Script logging level. Default is INFO";
      }
      leaf log-path {
        type string {
          length "1..512";
        }
        description
          "Location to store script logs";
      }
      leaf max-runtime {
        type uint16 {
          range "1..3600";
        }
        description
          "max runtime in seconds";
      }
    }
    output {
      container script-run-response {
        description
          "Script Run Response";
        leaf response {
          type string;
          mandatory true;
          description
            "Success or error message for the operation";
        }
        leaf request-id {
          type string;
          description
            "Request id of the script execution";
        }
        leaf status {
          type string;
          mandatory true;
          description
            "success or fail";
        }
      }
    }
  }
  rpc update {
    description
      "update scripts in repository";
    input {
      leaf condition {
        type update-condition;
        mandatory true;
        description
          "script update condition";
      }
      leaf script-type {
        type SCRIPT-TYPE-ALL;
        mandatory true;
        description
          "config-script|eem-script|exec-script|process-script|snmp-script|precommit-script|all";
      }
      leaf script-name {
        type string {
          length "1..256";
        }
        description
          "Script name/Update all scripts in config";
      }
    }
    output {
      container script-update-response {
        description
          "Script Update Response";
        list responses {
          key "script-name script-type";
          description
            "List of Success or error messages for the script operations";
          leaf script-name {
            type string;
            mandatory true;
            description
              "Name of script executed";
          }
          leaf script-type {
            type string;
            mandatory true;
            description
              "script type: exec|eem|config|process|snmp|precommit";
          }
          leaf response {
            type string;
            mandatory true;
            description
              "Success or error message for the operation";
          }
          leaf status {
            type string;
            mandatory true;
            description
              "success or fail";
          }
        }
      }
    }
  }
}
