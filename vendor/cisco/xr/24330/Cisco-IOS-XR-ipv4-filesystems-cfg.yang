module Cisco-IOS-XR-ipv4-filesystems-cfg {
  namespace "http://cisco.com/ns/yang/Cisco-IOS-XR-ipv4-filesystems-cfg";
  prefix ipv4-filesystems-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ipv4-filesystems package configuration.
     
     This module contains definitions
     for the following management objects:
       rcp: RCP configuration
       ftp: FTP configuration
       tftp: TFTP configuration
     
     Copyright (c) 2013-2019 by Cisco Systems, Inc.
     All rights reserved.";

  revision 2019-04-05 {
    description
      "Establish semantic version baseline.";
    semver:module-version "1.0.1";
  }
  revision 2017-11-28 {
    description
      "IOS XR 6.4.1 revision.";
  }
  revision 2015-11-09 {
    description
      "IOS XR 6.0 revision.";
  }

  grouping USERNAME {
    description
      "Common node of ftp-client, rcp-client";
    leaf username {
      type string;
      description
        "Specify username for connections";
    }
  }

  grouping SOURCE-INTERFACE {
    description
      "Common node of ftp-client, tftp-client,
       rcp-client";
    leaf source-interface {
      type xr:Interface-name;
      description
        "Specify interface for source address in
         connections";
    }
  }

  container rcp {
    description
      "RCP configuration";
    container rcp-client {
      description
        "RCP client configuration";
      uses USERNAME;
      uses SOURCE-INTERFACE;
    }
  }
  container ftp {
    description
      "FTP configuration";
    container ftp-client {
      description
        "FTP client configuration";
      container vrfs {
        description
          "VRF table";
        list vrf {
          key "vrf-name";
          description
            "VRF specific data";
          leaf source-interface {
            type xr:Interface-name;
            description
              "Specify interface for source address in
               connections";
          }
          leaf username {
            type string;
            description
              "Specify username for connections";
          }
          leaf anonymous-password {
            type string;
            description
              "Password for anonymous user (ftp server
               dependent)";
          }
          leaf password {
            type xr:Proprietary-password;
            description
              "Specify password for ftp connnection";
          }
          leaf passive {
            type empty;
            description
              "Enable connect using passive mode";
          }
          leaf vrf-name {
            type xr:Cisco-ios-xr-string;
            description
              "Name of the VRF instance";
          }
        }
      }
      leaf passive {
        type empty;
        description
          "Enable connect using passive mode";
      }
      leaf password {
        type xr:Proprietary-password;
        description
          "Specify password for ftp connnection";
      }
      leaf anonymous-password {
        type string;
        description
          "Password for anonymous user (ftp server
           dependent)";
      }
      uses USERNAME;
      uses SOURCE-INTERFACE;
    }
  }
  container tftp {
    description
      "TFTP configuration";
    container tftp-client {
      description
        "TFTP client configuration";
      container vrfs {
        description
          "VRF table";
        list vrf {
          key "vrf-name";
          description
            "VRF specific data";
          leaf source-interface {
            type xr:Interface-name;
            description
              "Specify interface for source address in
               connections";
          }
          leaf retry {
            type uint32 {
              range "0..256";
            }
            description
              "Specify the number of retries when client
               requests TFTP connections";
          }
          leaf timeout {
            type uint32 {
              range "0..256";
            }
            units "second";
            description
              "Specify the timeout for every TFTP connection
               in seconds";
          }
          leaf vrf-name {
            type xr:Cisco-ios-xr-string;
            description
              "Name of the VRF instance";
          }
        }
      }
      leaf retry {
        type uint32 {
          range "0..256";
        }
        description
          "Specify the number of retries when client
           requests TFTP connections";
      }
      leaf timeout {
        type uint32 {
          range "0..256";
        }
        units "second";
        description
          "Specify the timeout for every TFTP connection
           in seconds";
      }
      uses SOURCE-INTERFACE;
    }
  }
}
