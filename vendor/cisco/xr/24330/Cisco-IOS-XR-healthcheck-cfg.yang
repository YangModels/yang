module Cisco-IOS-XR-healthcheck-cfg {
  namespace "http://cisco.com/ns/yang/Cisco-IOS-XR-healthcheck-cfg";
  prefix healthcheck-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR healthcheck package configuration.
     
     This module contains definitions
     for the following management objects:
       health-check: System Health Check operational data space
     
     Copyright (c) 2013-2024 by Cisco Systems, Inc.
     All rights reserved.";

  revision 2024-01-18 {
    description
      "Removed Drop-Tolerance leaf from packet-drop
       2023-10-03
         Added tolerance container and window leaf in packet-drop
       2023-07-19
         Removed default cadence
       2023-01-18
         Updated Metric Threshold Ranges";
    semver:module-version "2.0.0";
  }
  revision 2022-05-25 {
    description
      "Changed the counter-size start value";
  }
  revision 2022-04-07 {
    description
      "Migrate NBC and rev build control to mgbl-yangref component";
  }
  revision 2020-07-14 {
    description
      "Platform Stats metrics and Custom Metrics configurations added";
    semver:module-version "1.0.0";
  }
  revision 2019-04-05 {
    description
      "Establish semantic version baseline.";
  }
  revision 2015-11-09 {
    description
      "IOS XR 6.0 revision.";
  }

  typedef Hcmgr-avgutil-enum {
    type enumeration {
      enum "minute1" {
        value 1;
        description
          "1 minute utilization";
      }
      enum "minute5" {
        value 5;
        description
          "5 minutes utilization";
      }
      enum "minute15" {
        value 15;
        description
          "15 minutes utilization";
      }
    }
    description
      "Hcmgr avgutil enum";
  }

  container health-check {
    description
      "System Health Check operational data space";
    container ord-z {
      description
        "Healthcheck config";
      leaf enable {
        type empty;
        description
          "Enable or disable health check";
      }
    }
    container use-case {
      description
        "Use case to monitor";
      container asic-reset {
        description
          "Use case Asic reset";
        leaf disable {
          type empty;
          description
            "Enable or disable Asic reset use case
             monitoring";
        }
        leaf drop-tolerance {
          type uint32 {
            range "0..100";
          }
          units "percentage";
          default "10";
          description
            "Drop tolerance as a percentage of total
             incoming bytes/packets";
        }
      }
      container packet-drop {
        description
          "Use case Packet drop";
        container tolerance {
          description
            "Use case Packet drop";
          leaf tolerance-level-low {
            type uint32 {
              range "0..1000000";
            }
            default "100";
            description
              "Drop tolerance as traps per second for low
               classified traps";
          }
          leaf tolerance-level-medium {
            type uint32 {
              range "0..1000000";
            }
            default "1000";
            description
              "Drop tolerance as traps per second for medium
               classified traps";
          }
          leaf tolerance-level-high {
            type uint32 {
              range "0..1000000";
            }
            default "10000";
            description
              "Drop tolerance as traps per second for high
               classified traps";
          }
        }
        leaf disable {
          type empty;
          description
            "Enable or disable Packet drop use case
             monitoring";
        }
        leaf drop-window {
          type uint32 {
            range "5..20";
          }
          default "10";
          description
            "Drop window is the number of cadence intervals
             to detect traffic failure";
        }
      }
    }
    container ord-a {
      description
        "Healthcheck config";
      leaf cadence {
        type uint32 {
          range "30..1800";
        }
        description
          "health check cadence";
      }
    }
    container ord-b {
      description
        "Healthcheck config";
      container metric {
        description
          "System metric to monitor";
        container fabric-health {
          description
            "Metric Fabric Health";
          leaf disable {
            type empty;
            description
              "Enable or disable Fabric health monitoring";
          }
        }
        container system-clock {
          description
            "Systemclock timezone";
          leaf disable {
            type empty;
            description
              "Disable Systemclock monitoring";
          }
        }
        container lc-monitoring {
          description
            "LC monitoring";
          leaf disable {
            type empty;
            description
              "Disable LC monitoring";
          }
        }
        container cpu {
          description
            "Metric CPU";
          container threshold {
            presence "Indicates a threshold node is configured.";
            description
              "CPU thresholds";
            leaf minor {
              type uint32 {
                range "1..98";
              }
              mandatory true;
              description
                "Minor threshold, Range(1, 98)";
            }
            leaf severe {
              type uint32 {
                range "1..99";
              }
              mandatory true;
              description
                "Severe threshold, Range(minor, 99)";
            }
            leaf critical {
              type uint32 {
                range "1..100";
              }
              mandatory true;
              description
                "Critical threshold, Range(severe, 100)";
            }
          }
          leaf avg-util {
            type Hcmgr-avgutil-enum;
            default "minute15";
            description
              "Average CPU utilization";
          }
          leaf disable {
            type empty;
            description
              "Enable or disable CPU monitoring";
          }
        }
        container config-inconsistency {
          description
            "Config Inconsistency monitoring";
          leaf disable {
            type empty;
            description
              "Disable Config Inconsistency monitoring";
          }
        }
        container intf-counters {
          description
            "Metric Interface counters";
          container interfaces {
            description
              "List of interface to monitor";
            leaf-list interface {
              type string;
              max-elements "32";
              description
                "Interface Name";
            }
          }
          leaf counter-size {
            type uint32 {
              range "2..15";
            }
            default "5";
            description
              "Number of runs for Interface counters
               monitoring";
          }
          leaf disable {
            type empty;
            description
              "Enable or disable Interface counters
               monitoring";
          }
        }
        container pci-monitoring {
          description
            "PCI Monitoring";
          leaf disable {
            type empty;
            description
              "Disable PCI tree monitoring";
          }
        }
        container hw-monitoring {
          description
            "Hardware monitoring";
          leaf disable {
            type empty;
            description
              "Disable Hardware monitoring";
          }
        }
        container process-resource {
          description
            "Process rlimit value monitoring";
          leaf disable {
            type empty;
            description
              "Disable Process Resource monitoring";
          }
        }
        container communication-timeout {
          description
            "Process communication timeout";
          leaf disable {
            type empty;
            description
              "Disable Process communication timeout";
          }
        }
        container redundancy {
          description
            "Metric Redundancy";
          leaf disable {
            type empty;
            description
              "Enable or disable Redundancy monitoring";
          }
        }
        container free-memory {
          description
            "Metric Free Memory";
          container threshold {
            presence "Indicates a threshold node is configured.";
            description
              "Free Memory thresholds";
            leaf minor {
              type uint32 {
                range "3..100";
              }
              mandatory true;
              description
                "Minor threshold, Range(3, 100)";
            }
            leaf severe {
              type uint32 {
                range "2..100";
              }
              mandatory true;
              description
                "Severe threshold, Range(2, minor)";
            }
            leaf critical {
              type uint32 {
                range "1..100";
              }
              mandatory true;
              description
                "Critical threshold, Range(1, severe)";
            }
          }
          leaf disable {
            type empty;
            description
              "Enable or disable Free Memory monitoring";
          }
        }
        container platform {
          description
            "Metric Platform";
          leaf disable {
            type empty;
            description
              "Enable or disable Platform monitoring";
          }
        }
        container custom-metrics {
          description
            "List of custom metrics to monitor";
          leaf-list custom-metric {
            type string {
              length "1..64";
            }
            max-elements "10";
            description
              "Custom Metric Name";
          }
        }
        container fabric-stats {
          description
            "Metric Fabric stats";
          leaf counter-size {
            type uint32 {
              range "2..15";
            }
            default "5";
            description
              "Number of runs for Fabric stats monitoring";
          }
          leaf disable {
            type empty;
            description
              "Enable or disable Fabric stats monitoring";
          }
        }
        container wd-monitoring {
          description
            "Watchdog monitoring";
          leaf disable {
            type empty;
            description
              "Disable Watchdog monitoring";
          }
        }
        container fpd {
          description
            "Metric FPD";
          leaf disable {
            type empty;
            description
              "Enable or disable FPD monitoring";
          }
        }
        container asic-errors {
          description
            "Metric Asic errors";
          leaf counter-size {
            type uint32 {
              range "2..15";
            }
            default "5";
            description
              "Number of runs for Asic errors monitoring";
          }
          leaf disable {
            type empty;
            description
              "Enable or disable Asic errors monitoring";
          }
        }
        container filesystem {
          description
            "Metric Filesystem Usage";
          container threshold {
            presence "Indicates a threshold node is configured.";
            description
              "Filesystem Usage thresholds";
            leaf minor {
              type uint32 {
                range "1..98";
              }
              mandatory true;
              description
                "Minor threshold, Range(1, 98)";
            }
            leaf severe {
              type uint32 {
                range "1..99";
              }
              mandatory true;
              description
                "Severe threshold, Range(minor, 99)";
            }
            leaf critical {
              type uint32 {
                range "1..100";
              }
              mandatory true;
              description
                "Critical threshold, Range(severe, 100)";
            }
          }
          leaf disable {
            type empty;
            description
              "Enable or disable Filesystem Usage monitoring";
          }
        }
        container process-state {
          description
            "Process state monitoring";
          leaf disable {
            type empty;
            description
              "Disable Process State monitoring";
          }
        }
        container shared-memory {
          description
            "Metric Shared Memory";
          container threshold {
            presence "Indicates a threshold node is configured.";
            description
              "Shared Memory thresholds";
            leaf minor {
              type uint32 {
                range "1..98";
              }
              mandatory true;
              description
                "Minor threshold, Range(1, 98)";
            }
            leaf severe {
              type uint32 {
                range "1..99";
              }
              mandatory true;
              description
                "Severe threshold, Range(minor, 99)";
            }
            leaf critical {
              type uint32 {
                range "1..100";
              }
              mandatory true;
              description
                "Critical threshold, Range(severe, 100)";
            }
          }
          leaf disable {
            type empty;
            description
              "Enable or disable Shared Memory monitoring";
          }
        }
      }
    }
  }
}
