submodule Cisco-IOS-XR-ipv4-arp-oper-sub2 {
  belongs-to Cisco-IOS-XR-ipv4-arp-oper {
    prefix Cisco-IOS-XR-ipv4-arp-oper;
  }

  import ietf-inet-types {
    prefix inet;
  }
  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR ipv4-arp package operational data.
     
     Copyright (c) 2013-2024 by Cisco Systems, Inc.
     All rights reserved.";

  revision 2024-01-18 {
    description
      "Statistics for ARP EVPN Proxy responses
       2024-01-08
         Updated ARP state enum / ARP ext-flag enum for EVPN-Remote entry + Immutable flag
       2023-10-03
         Increase in interface name length
       2023-10-01
         Adding support for ARP Host tracking entries
       2022-06-10
         Adding support for displaying counters related to ARP Cache Limit
       2022-06-09
         Adding support for ARP Policer";
    semver:module-version "3.0.0";
  }
  revision 2021-08-17 {
    description
      "Adding support for displaying Last pulse time for Punt and input queue from XIPC";
    semver:module-version "2.1.0";
  }
  revision 2021-02-11 {
    description
      "IOS XR 6.2.3 revision.
       2021-02-04
           IOS XR 6.2.2 revision.
       2020-12-03
           Adding support for displaying client resync time
       2020-04-22
           adding oper schema support, clinet stats update with cnbng.";
    semver:module-version "2.0.0";
  }
  revision 2019-12-11 {
    description
      "adding oper schema support.";
    semver:module-version "1.1.0";
  }
  revision 2019-04-05 {
    description
      "Establish semantic version baseline.";
    semver:module-version "1.0.1";
  }
  revision 2018-11-21 {
    description
      "Fixing backward compatibility error in module.";
  }
  revision 2017-05-01 {
    description
      "Fixing backward compatibility error in module.";
  }
  revision 2016-12-19 {
    description
      "IOS XR 6.2.1 revision.";
  }
  revision 2015-11-09 {
    description
      "IOS XR 6.0 revision.";
  }

  grouping DAGR-GROUP-INFO {
    description
      "DAGR Group information";
    leaf ifhandle {
      type xr:Interface-name;
      description
        "Interface";
    }
    leaf vip {
      type inet:ipv4-address;
      description
        "Virtual IPv4 address";
    }
    leaf state {
      type xr:Node-id;
      description
        "State";
    }
    leaf query-period {
      type uint32;
      description
        "Query Period for dagr group";
    }
    leaf dist {
      type uint32;
      description
        "DAGR Route distance";
    }
    leaf metric {
      type uint32;
      description
        "DAGR Route Metric";
    }
  }
}
