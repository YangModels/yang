module Cisco-IOS-XR-prm-hwmod-loadbalance-cfg {

  /*** NAMESPACE / PREFIX DEFINITION ***/

  namespace "http://cisco.com/ns/yang"+
    "/Cisco-IOS-XR-prm-hwmod-loadbalance-cfg";


  prefix "prm-hwmod-loadbalance-cfg";

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR prm-hwmod-loadbalance package configuration.

     This module contains definitions
     for the following management objects:
       hardware-module: HardwareModule

     Copyright (c) 2013-2017 by Cisco Systems, Inc.
     All rights reserved.";

  revision "2017-04-12" {
    description
      "Implementing Conf Yang Model for BGP LU HW ECMP";
  }

  revision "2015-11-09" {
    description
      "IOS XR 6.0 revision.";
  }


  container hardware-module {
    description "HardwareModule";

    container loadbalancing {
      description "Loadbalance option";

      container bgp3107 {
        description "BGP LU";

        container ecmp {
          description "ECMP ";
          leaf enable {
            type empty;
            description "Enable Option";
          }
        }
      }
    }
  }
}
