submodule Cisco-IOS-XR-infra-dumper-oper-sub1 {

  belongs-to Cisco-IOS-XR-infra-dumper-oper {
    prefix Cisco-IOS-XR-infra-dumper-oper;
  }

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR infra-dumper package operational data.

     Copyright (c) 2013-2017 by Cisco Systems, Inc.
     All rights reserved.";

  revision "2017-05-05" {
    description
      "Fix comp-mdata.pl for adding sub1 yang file to /pkg/yang";
  }

  revision "2015-11-09" {
    description
      "IOS XR 6.0 revision.";
  }


  grouping DUMPER-PKG-TABLE {
    description "Package Information";
    leaf name {
      type string;
      description "Package name";
    }
    leaf source {
      type string;
      description "Package Source";
    }
  }

  grouping DUMPER-DLL-TABLE {
    description "DLL Information";
    leaf path {
      type string;
      description "DLL Path";
    }
    leaf text-addr {
      type uint32;
      description "text addr";
    }
    leaf text-size {
      type uint32;
      description "text size";
    }
    leaf data-addr {
      type uint32;
      description "data addr";
    }
    leaf data-size {
      type uint32;
      description "data size";
    }
    leaf version {
      type uint32;
      description "version";
    }
  }

  grouping STACK-TRACE-ST {
    description "Stack Trace";
    leaf stack-trace {
      type uint32;
      description "stack trace";
    }
  }

  grouping CONTEXT-LOGS {
    description "Context of a process core";
    leaf process-name {
      type string;
      description "Process name";
    }
    leaf pid {
      type uint32;
      description "Process ID";
    }
    leaf tid {
      type uint32;
      description "Thread ID";
    }
    leaf core-dump-time {
      type string;
      description "Core dump time/Crash time";
    }
    leaf sig-num {
      type uint32;
      description "Signal number";
    }
    leaf sin-err-str {
      type string;
      description "Signal error string";
    }
    leaf sig-send-pid {
      type uint32;
      description "Sender pid";
    }
    leaf sig-code {
      type uint32;
      description "Signal code";
    }
    leaf sin-info {
      type string;
      description "Signal info";
    }
    leaf core-for-process {
      type string;
      description "Core for process at ";
    }
    leaf registers-info {
      type string;
      description "Registers Info";
    }

    list stack-trace {
      description "Stack Trace";
      uses STACK-TRACE-ST;
    }

    list dll-info {
      description "DLL Information";
      uses DUMPER-DLL-TABLE;
    }
  }

  grouping DUMPER-CONTEXT-INFO-XML {
    description "Dumper Context of a process core";
    leaf node {
      type string;
      description "Node name";
    }

    list context-info {
      description "Context Information";
      uses CONTEXT-LOGS;
    }

    list crash-package-information {
      description "Crash Package Information";
      uses DUMPER-PKG-TABLE;
    }
  }

  grouping DUMPER-CRASH-INFO-XML {
    description "all crash info";

    list crash-info {
      description "All crash info";
      uses DUMPER-CONTEXT-INFO-XML;
    }
  }
}
