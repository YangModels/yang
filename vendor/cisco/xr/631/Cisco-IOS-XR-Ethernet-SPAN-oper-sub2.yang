submodule Cisco-IOS-XR-Ethernet-SPAN-oper-sub2 {

  belongs-to Cisco-IOS-XR-Ethernet-SPAN-oper {
    prefix Cisco-IOS-XR-Ethernet-SPAN-oper;
  }

  /*** LINKAGE (IMPORTS / INCLUDES) ***/

  import Cisco-IOS-XR-types { prefix "xr"; }

  include Cisco-IOS-XR-Ethernet-SPAN-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR Ethernet-SPAN package operational data.

     Copyright (c) 2013-2017 by Cisco Systems, Inc.
     All rights reserved.";

  revision "2015-11-09" {
    description
      "IOS XR 6.0 revision.";
  }

  typedef Im-state-enum {
    type enumeration {
      enum im-state-not-ready {
        description "im state not ready";
      }
      enum im-state-admin-down {
        description "im state admin down";
      }
      enum im-state-down {
        description "im state down";
      }
      enum im-state-up {
        description "im state up";
      }
      enum im-state-shutdown {
        description "im state shutdown";
      }
      enum im-state-err-disable {
        description "im state err disable";
      }
      enum im-state-down-immediate {
        description "im state down immediate";
      }
      enum im-state-down-immediate-admin {
        description "im state down immediate admin";
      }
      enum im-state-down-graceful {
        description "im state down graceful";
      }
      enum im-state-begin-shutdown {
        description "im state begin shutdown";
      }
      enum im-state-end-shutdown {
        description "im state end shutdown";
      }
      enum im-state-begin-error-disable {
        description "im state begin error disable";
      }
      enum im-state-end-error-disable {
        description "im state end error disable";
      }
      enum im-state-begin-down-graceful {
        description "im state begin down graceful";
      }
      enum im-state-reset {
        description "im state reset";
      }
      enum im-state-operational {
        description "im state operational";
      }
      enum im-state-not-operational {
        description "im state not operational";
      }
      enum im-state-unknown {
        description "im state unknown";
      }
      enum im-state-last {
        description "im state last";
      }
    }
    description "Im state enum";
  }

  grouping SPAN-MA-ATTACHMENT-BAG {
    description "SPAN MA Attachment Information";

    container traffic-parameters {
      description "Traffic mirroring parameters";
      uses TRAFFIC-MIRRORING-PARAMETERS;
    }

    container destination-id {
      description "Destination ID";
      uses DESTINATION-ID;
    }
    leaf name {
      type string;
      description "Session Name";
    }
    leaf local-class {
      type Session-class;
      description "Local attachment class";
    }
    leaf id {
      type uint32;
      description "Numerical ID assigned to session";
    }
    leaf global-class {
      type Session-class;
      description "Global session class";
    }
    leaf session-is-configured {
      type boolean;
      description "The Session is configured globally";
    }
    leaf source-interface {
      type xr:Interface-name;
      description "Source interface";
    }
    leaf source-interface-state {
      type Im-state-enum;
      description "Source interface state";
    }
    leaf pfi-error {
      type uint32;
      description "Last error returned from PFI for this interface";
    }
    leaf dest-pw-type-not-supported {
      type boolean;
      description "The destination PW type is not supported";
    }
    leaf source-interface-is-a-destination {
      type boolean;
      description
        "This source interface is a destination for
        another monitor-session";
    }
    leaf destination-interface {
      type xr:Interface-name;
      description
        "Destination interface (deprecated by
        DestinationID, invalid for pseudowires)";
    }
    leaf traffic-direction {
      type Traffic-direction;
      description
        "Traffic mirroring direction (deprecated by
        TrafficParameters)";
    }
  }

  grouping SPAN-MA-STATISTICS-BAG {
    description "SPAN MA Statistics Information";
    leaf rx-packets-mirrored {
      type uint64;
      description "RX Packets Mirrored";
    }
    leaf rx-octets-mirrored {
      type uint64;
      description "RX Octets Mirrored";
    }
    leaf tx-packets-mirrored {
      type uint64;
      description "TX Packets Mirrored";
    }
    leaf tx-octets-mirrored {
      type uint64;
      description "TX Octets Mirrored";
    }
    leaf packets-not-mirrored {
      type uint64;
      description "Packets Not Mirrored";
    }
    leaf octets-not-mirrored {
      type uint64;
      description "Octets Not Mirrored";
    }
  }
}
