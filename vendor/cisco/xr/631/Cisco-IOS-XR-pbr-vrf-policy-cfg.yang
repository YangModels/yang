module Cisco-IOS-XR-pbr-vrf-policy-cfg {

  /*** NAMESPACE / PREFIX DEFINITION ***/

  namespace "http://cisco.com/ns"+
    "/yang/Cisco-IOS-XR-pbr-vrf-policy-cfg";


  prefix "pbr-vrf-policy-cfg";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR pbr-vrf-policy package configuration.

     This module contains definitions
     for the following management objects:
       vrf-policy: VRF Policy PBR configuration

     Copyright (c) 2013-2017 by Cisco Systems, Inc.
     All rights reserved.";

  revision "2015-11-09" {
    description
      "IOS XR 6.0 revision.";
  }

  typedef Pbr-afi {
    type string {
      pattern "(ipv4)";
    }
    description
      "ipv4: Comment: v4 string for <afi_name>;         
      ipv6: Comment: v6 string for <afi_name>";
  }

  container vrf-policy {
    description "VRF Policy PBR configuration";

    list vrf {
      key "vrf-name";
      description "VRF Name";
      leaf vrf-name {
        type xr:Cisco-ios-xr-string;
        description "VRF name";
      }

      list afi {
        key "afi-type";
        description "address family";
        leaf service-policy-in {
          type string;
          description "Policy map name";
        }
        leaf afi-type {
          type Pbr-afi;
          description "AFI name";
        }
      }
    }
  }
}
