submodule Cisco-IOS-XR-asic-errors-oper-sub1 {

  belongs-to Cisco-IOS-XR-asic-errors-oper {
    prefix Cisco-IOS-XR-asic-errors-oper;
  }

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR asic-errors package operational data.

     Copyright (c) 2013-2017 by Cisco Systems, Inc.
     All rights reserved.";

  revision "2015-11-09" {
    description
      "IOS XR 6.0 revision.";
  }


  grouping CIHERR-ERROR-DATA-BG {
    description "CIHERR ERROR DATA BG";
    leaf at-time {
      type uint64;
      description "at time";
    }
    leaf at-time-nsec {
      type uint64;
      description "at time nsec";
    }
    leaf counter-val {
      type uint32;
      description "counter val";
    }
    leaf error-desc {
      type string;
      description "error desc";
    }
    leaf-list error-regval {
      type uint8;
      description "error regval";
    }
  }

  grouping CSRS-INFO-BG {
    description "CSRS INFO BG";
    leaf name {
      type string;
      description "name";
    }
    leaf address {
      type uint64;
      description "address";
    }
    leaf width {
      type uint32;
      description "width";
    }
  }

  grouping CIHERR-NODE-BG {
    description "CIHERR NODE BG";
    leaf name {
      type string;
      description "Name assigned to mem";
    }
    leaf asic-info {
      type string;
      description "Name of rack/board/asic";
    }
    leaf node-key {
      type uint32;
      description "32 bit key";
    }
    leaf alarm-on {
      type boolean;
      description "High threshold crossed";
    }
    leaf thresh-hi {
      type uint32;
      description "High threshold value";
    }
    leaf period-hi {
      type uint32;
      description "High period value";
    }
    leaf thresh-lo {
      type uint32;
      description "High threshold value";
    }
    leaf period-lo {
      type uint32;
      description "High period value";
    }
    leaf count {
      type uint32;
      description "Accumulated count";
    }
    leaf intr-type {
      type uint32;
      description "Type of error";
    }
    leaf leaf-id {
      type uint32;
      description "Leaf ID defined in user data";
    }
    leaf last-cleared {
      type uint64;
      description "Time  cleared";
    }

    list csrs-info {
      description "List of csrs_info";
      uses CSRS-INFO-BG;
    }

    list last-err {
      description "Last Printable error information";
      uses CIHERR-ERROR-DATA-BG;
    }
  }

  grouping CIHERR-NODES-BG {
    description "CIHERR NODES BG";

    list error {
      description "Collection of errors";
      uses CIHERR-NODE-BG;
    }
  }
}
