module Cisco-IOS-XR-skp-qos-oper {

  /*** NAMESPACE / PREFIX DEFINITION ***/

  namespace "http://cisco.com/ns/yang/Cisco-IOS-XR-skp-qos-oper";


  prefix "skp-qos-oper";

  /*** LINKAGE (IMPORTS / INCLUDES) ***/

  import Cisco-IOS-XR-types { prefix "xr"; }

  include Cisco-IOS-XR-skp-qos-oper-sub2 {
    revision-date 2016-02-18;
  }

  include Cisco-IOS-XR-skp-qos-oper-sub1 {
    revision-date 2016-02-18;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR skp-qos package operational data.

     This module contains definitions
     for the following management objects:
       platform-qos: QoS Skywarp platform operational data 
       platform-qos-ea: platform qos ea

     Copyright (c) 2013-2017 by Cisco Systems, Inc.
     All rights reserved.";

  revision "2016-02-18" {
    description
      "Implementing Oper Yang Model";
  }

  revision "2015-11-09" {
    description
      "IOS XR 6.0 revision.";
  }


  grouping NV-SATELLITE-INPUT {
    description
      "Common node of nv-satellite-interface,
      satellite-id, member-interface";

    container nv-satellite-input {
      description
        "A piece of Satellite QoS policy-map operational
        data for input";
      uses NV-SAT-STATISTICS;
    }
  }

  grouping DETAILS {
    description
      "Common node of output, input, bundle-input,
      bundle-output";

    container details {
      description "QoS-EA policy details";
      uses QOS-SHOW-EA-POLICY-ST;
    }
  }

  grouping STATISTICS {
    description "Common node of input, output, policy-name";

    container statistics {
      description
        "Policy-map statistics operational data for an
        interface";
      uses QOS-STATS;
    }
  }

  grouping INTERFACE {
    description
      "Common node of interface-table,
      nv-interface-table";

    list interface {
      key "interface-name";
      description
        "QoS policy-map operational data for a particular
        interface";
      leaf interface-name {
        type xr:Interface-name;
        description "Name of the interface";
      }
      uses OUTPUT;
      uses INPUT;
      uses MEMBER-INTERFACE-TABLE;
      uses SATELLITE-ID-TABLE;
    }
  }

  grouping INPUT {
    description
      "Common node of shared-policy-instance,
      member-interface, interface";

    container input {
      description
        "A piece of QoS policy-map operational data for
        an interface";
      uses POLICY-NAME-TABLE;
      uses STATISTICS;
    }
  }

  grouping MEMBER-INTERFACE-TABLE {
    description
      "Common node of interface, nv-satellite-interface,
      shared-policy-instance";

    container member-interfaces {
      description "QoS policy-map member interface table";

      list member-interface {
        key "interface-name";
        description "QoS policy-map member interface statistics";
        leaf interface-name {
          type xr:Interface-name;
          description "Name of member interface";
        }
        uses OUTPUT;
        uses NV-SATELLITE-OUTPUT;
        uses INPUT;
        uses NV-SATELLITE-INPUT;
        uses SATELLITE-ID-TABLE;
      }
    }
  }

  grouping POLICY-NAME-TABLE {
    description "Common node of input, output";

    container policy-names {
      description
        "Policy-map statistics operational data for an
        interface";

      list policy-name {
        key "pmap-name";
        description
          "Policy-map statistics operational data for an
          interface";
        leaf pmap-name {
          type xr:Cisco-ios-xr-string;
          description "Name of the policy";
        }
        uses STATISTICS;
      }
    }
  }

  grouping NV-SATELLITE-OUTPUT {
    description
      "Common node of nv-satellite-interface,
      satellite-id, member-interface";

    container nv-satellite-output {
      description
        "A piece of Satellite QoS policy-map operational
        data for an interface";
      uses NV-SAT-STATISTICS;
    }
  }

  grouping OUTPUT {
    description
      "Common node of shared-policy-instance,
      member-interface, interface";

    container output {
      description
        "A piece of QoS policy-map operational data for
        an interface";
      uses POLICY-NAME-TABLE;
      uses STATISTICS;
    }
  }

  grouping NV-SAT-STATISTICS {
    description
      "Common node of nv-satellite-input,
      nv-satellite-output";

    container nv-sat-statistics {
      description
        "Policy-map statistics operational data for
        satellite interface";
      uses QOS-STATS;
    }
  }

  grouping SATELLITE-ID-TABLE {
    description "Common node of interface, member-interface";

    container satellite-ids {
      description "Satellite ID information";

      list satellite-id {
        key "nv-satellite-id";
        description "Satellite ID information";
        leaf nv-satellite-id {
          type int32;
          description "Satellite ID";
        }
        uses NV-SATELLITE-OUTPUT;
        uses NV-SATELLITE-INPUT;
      }
    }
  }

  container platform-qos {
    config false;
    description "QoS Skywarp platform operational data ";

    container nodes {
      description
        "List of nodes with platform specific QoS
        configuration";

      list node {
        key "node-name";
        description "Node with platform specific QoS configuration";

        container bundle-interfaces {
          description "QoS list of bundle interfaces";

          list bundle-interface {
            key "interface-name";
            description "QoS interface name";

            container member-interfaces {
              description "QoS list of member interfaces";

              list member-interface {
                key "interface-name";
                description "QoS interface name";

                container bundle-input {
                  description "QoS policy direction input";
                  uses QOS-SHOW-POLICY-ST;
                }

                container bundle-output {
                  description "QoS policy direction output";
                  uses QOS-SHOW-POLICY-ST;
                }
                leaf interface-name {
                  type xr:Interface-name;
                  description "Memeber interface";
                }
              }
            }
            leaf interface-name {
              type xr:Interface-name;
              description "Bundle interface name";
            }
          }
        }

        container capability {
          description "QoS system capability";
          uses QOS-EA-CAPABILITY;
        }

        container interfaces {
          description "QoS list of interfaces";

          list interface {
            key "interface-name";
            description "QoS interface name";

            container output {
              description "QoS policy direction egress";
              uses QOS-SHOW-POLICY-ST;
            }

            container input {
              description "QoS policy direction ingress";
              uses QOS-SHOW-POLICY-ST;
            }
            leaf interface-name {
              type xr:Interface-name;
              description "The name of the interface";
            }
          }
        }
        leaf node-name {
          type xr:Node-id;
          description "Node name";
        }
      }
    }
  }

  container platform-qos-ea {
    config false;
    description "platform qos ea";

    container nodes {
      description
        "List of nodes with platform specific QoS-EA
        configuration";

      list node {
        key "node-name";
        description
          "Node with platform specific QoS-EA
          configuration";

        container bundle-interfaces {
          description "QoS-EA list of bundle interfaces";

          list bundle-interface {
            key "interface-name";
            description "QoS-EA interface name";

            container member-interfaces {
              description "QoS-EA list of member interfaces";

              list member-interface {
                key "interface-name";
                description "QoS-EA interface name";

                container bundle-output {
                  description "QoS-EA policy direction output";
                  uses DETAILS;
                }

                container bundle-input {
                  description "QoS-EA policy direction input";
                  uses DETAILS;
                }
                leaf interface-name {
                  type xr:Interface-name;
                  description "Memeber interface";
                }
              }
            }
            leaf interface-name {
              type xr:Interface-name;
              description "Bundle interface name";
            }
          }
        }

        container interfaces {
          description "QoS-EA list of interfaces";

          list interface {
            key "interface-name";
            description "QoS-EA interface name";

            container output {
              description "QoS-EA policy direction egress";
              uses DETAILS;
            }

            container input {
              description "QoS-EA policy direction ingress";
              uses DETAILS;
            }
            leaf interface-name {
              type xr:Interface-name;
              description "The name of the interface";
            }
          }
        }
        leaf node-name {
          type xr:Node-id;
          description "Node name";
        }
      }
    }
  }
}
