module Cisco-IOS-XR-dnx-port-mapper-oper {

  /*** NAMESPACE / PREFIX DEFINITION ***/

  namespace "http://cisco.com/ns/yang"+
    "/Cisco-IOS-XR-dnx-port-mapper-oper";


  prefix "dnx-port-mapper-oper";

  /*** LINKAGE (IMPORTS / INCLUDES) ***/

  import Cisco-IOS-XR-types { prefix "xr"; }

  include Cisco-IOS-XR-dnx-port-mapper-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR dnx-port-mapper package operational data.

     This module contains definitions
     for the following management objects:
       oor: Out of Resource Data

     Copyright (c) 2013-2017 by Cisco Systems, Inc.
     All rights reserved.";

  revision "2015-11-09" {
    description
      "IOS XR 6.0 revision.";
  }


  container oor {
    config false;
    description "Out of Resource Data";

    container nodes {
      description "OOR data for available nodes";

      list node {
        key "node-name";
        description "DPA operational data for a particular node";

        container summary {
          description "Summary";
          uses OOR-SUMMARY;
        }

        container interface-names {
          description "OOR Interface Information";

          list interface-name {
            key "interface-name";
            description "OOR Data for particular interface";
            leaf interface-name {
              type xr:Cisco-ios-xr-string;
              description "The name of the interface";
            }
            uses OOR-INTERFACE-INFO;
          }
        }
        leaf node-name {
          type xr:Node-id;
          description "Node ID";
        }
      }
    }
  }
}
