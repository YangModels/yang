submodule Cisco-IOS-XR-icpe-infra-oper-sub5 {

  belongs-to Cisco-IOS-XR-icpe-infra-oper {
    prefix Cisco-IOS-XR-icpe-infra-oper;
  }

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR icpe-infra package operational data.

     Copyright (c) 2013-2017 by Cisco Systems, Inc.
     All rights reserved.";

  revision "2015-11-09" {
    description
      "IOS XR 6.0 revision.";
  }


  grouping ICPE-INSTALL-PROGRESS {
    description "Current percentage of install";
    leaf operation-id-xr {
      type uint32;
      description "Operation ID";
    }
    leaf progress-percentage {
      type uint16;
      units "percentage";
      description "Progress percentage";
    }
    leaf satellite-count {
      type uint32;
      description "Satellite count";
    }
  }
}
