module Cisco-IOS-XR-crypto-macsec-mka-oper {

  /*** NAMESPACE / PREFIX DEFINITION ***/

  namespace "http://cisco.com/ns/yang"+
    "/Cisco-IOS-XR-crypto-macsec-mka-oper";


  prefix "crypto-macsec-mka-oper";

  /*** LINKAGE (IMPORTS / INCLUDES) ***/

  import Cisco-IOS-XR-types { prefix "xr"; }

  include Cisco-IOS-XR-crypto-macsec-mka-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR crypto-macsec-mka package operational data.

     This module contains definitions
     for the following management objects:
       macsec: Macsec operational data

     Copyright (c) 2013-2017 by Cisco Systems, Inc.
     All rights reserved.";

  revision "2015-11-09" {
    description
      "IOS XR 6.0 revision.";
  }


  container macsec {
    config false;
    description "Macsec operational data";

    container mka {
      description "MKA Data";

      container interfaces {
        description "MKA Data";

        list interface {
          key "name";
          description "MKA Data for the Interface";

          container session {
            description "MKA Session Data";
            uses MKA-SESSION;
          }
          leaf name {
            type xr:Interface-name;
            description "Interface Name";
          }
        }
      }
    }
  }
}
