module Cisco-IOS-XR-ncs1001-ots-cfg {

  /*** NAMESPACE / PREFIX DEFINITION ***/

  namespace "http://cisco.com/ns/yang/Cisco-IOS-XR-ncs1001-ots-cfg";


  prefix "ncs1001-ots-cfg";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ncs1001-ots package configuration.

     This module contains definitions
     for the following management objects:
       hardware-module: NCS1k HW module config

     Copyright (c) 2013-2017 by Cisco Systems, Inc.
     All rights reserved.";

  revision "2015-11-09" {
    description
      "IOS XR 6.0 revision.";
  }

  typedef Ots-amplifier-node {
    type enumeration {
      enum term {
        value 0;
        description "Nodetype TERM";
      }
      enum ila {
        value 1;
        description "Nodetype InLine Amplifier";
      }
      enum roadm {
        value 2;
        description "Nodetype ROADM";
      }
    }
    description "Ots amplifier node";
  }
  typedef Ots-amplifier-grid-mode {
    type enumeration {
      enum 100g-hz {
        value 0;
        description "100GHz mode";
      }
      enum 50g-hz {
        value 1;
        description "50GHz mode";
      }
      enum gr-idle-ss {
        value 2;
        description "Gridless mode";
      }
    }
    description "Ots amplifier grid mode";
  }
  typedef Ots-psm-manual-switch {
    type enumeration {
      enum working {
        value 1;
        description "Working port";
      }
      enum protected {
        value 2;
        description "Protected port";
      }
    }
    description "Ots psm manual switch";
  }
  typedef Ots-psm-lockout-from {
    type enumeration {
      enum working {
        value 1;
        description "Working port";
      }
      enum protected {
        value 2;
        description "Protected port";
      }
    }
    description "Ots psm lockout from";
  }

  container hardware-module {
    description "NCS1k HW module config";

    list node {
      key "location";
      description "Node";
      leaf location {
        type xr:Cisco-ios-xr-string;
        description "Fully qualified line card specification";
      }

      list slot {
        key "slot-id";
        description "Slot Id";

        container amplifier {
          description "Amplifier Configs";
          leaf node-type {
            type Ots-amplifier-node;
            description
              "Define the type of node in which the
              amplifier is set to work";
          }
          leaf grid-mode {
            type Ots-amplifier-grid-mode;
            description
              "Define the working mode for the optical
              module";
          }
          leaf udc-vlan {
            type uint32 {
              range "2..4080";
            }
            description "Define the VLAN ID in range <2-4080>";
          }
        }

        container psm {
          description "PSM Configs";
          leaf mono-dir {
            type boolean;
            description "Psm Uni directional configuration";
          }
          leaf auto-threshold {
            type boolean;
            description "Psm Automatic Threshold Setting";
          }
          leaf path-protection {
            type boolean;
            description "Psm path protection configuration";
          }
          leaf section-protection {
            type boolean;
            description "Psm section protection configuration";
          }
          leaf lockout-from {
            type Ots-psm-lockout-from;
            description "Exclude selected port from protection";
          }
          leaf manual-switch-to {
            type Ots-psm-manual-switch;
            description "Switch active path on selected port";
          }
        }
        leaf slot-id {
          type uint32 {
            range "1..3";
          }
          description "Set Slot";
        }
      }
    }
  }
}
