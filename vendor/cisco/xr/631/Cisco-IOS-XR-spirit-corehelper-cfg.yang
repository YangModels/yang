module Cisco-IOS-XR-spirit-corehelper-cfg {

  /*** NAMESPACE / PREFIX DEFINITION ***/

  namespace "http://cisco.com/ns/yang"+
    "/Cisco-IOS-XR-spirit-corehelper-cfg";


  prefix "spirit-corehelper-cfg";

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR spirit-corehelper package configuration.

     This module contains definitions
     for the following management objects:
       exception: Core dump configuration commands

     Copyright (c) 2013-2017 by Cisco Systems, Inc.
     All rights reserved.";

  revision "2015-11-09" {
    description
      "IOS XR 6.0 revision.";
  }


  container exception {
    description "Core dump configuration commands";

    container file {
      description "Container for the order of preference";
      leaf choice2 {
        type string;
        description "Preference of the dump location";
      }
      leaf choice1 {
        type string;
        description "Preference of the dump location";
      }
      leaf choice3 {
        type string;
        description "Preference of the dump location";
      }
    }
  }
}
