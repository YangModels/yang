//*************  DO-NOT EDIT  **************
//*********** Auto-generated file ********** 

 module cisco-xr-openconfig-platform-deviations {

  prefix  "oc-platformdevs";

  namespace "http://cisco.com/ns/yang/cisco-xr-openconfig-platform-deviations";

  import openconfig-interfaces { prefix oc-if; }
  import openconfig-platform { prefix oc-platform; }

  organization "Cisco Systems, Inc.";

  contact
    "Cisco Systems, Inc.
     Customer Service

     Postal: 170 West Tasman Drive
     San Jose, CA 95134

     Tel: +1 800 553-NETS

     E-mail: cs-yang@cisco.com";

  description
    "This module contains a set of deviations for 
 
     openconfig-platform.yang@2016-06-06 

     on Cisco IOS-XR devices.

     Copyright (c) 2016 by Cisco Systems, Inc.
     All rights reserved.";

  revision "2016-10-16" {
    description
      "Initial revision applicable to IOS-XR 6.2.1";
  }


  deviation /oc-platform:components/oc-platform:component/oc-platform:properties/oc-platform:property {
    deviate not-supported;
  }

  deviation /oc-if:interfaces/oc-if:interface/oc-if:state/oc-platform:hardware-port {
    deviate not-supported;
  }


}
//total deviations:2
