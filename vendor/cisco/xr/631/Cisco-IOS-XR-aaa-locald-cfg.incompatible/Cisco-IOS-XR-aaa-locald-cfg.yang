module Cisco-IOS-XR-aaa-locald-cfg {

  /*** NAMESPACE / PREFIX DEFINITION ***/

  namespace "http://cisco.com/ns/yang/Cisco-IOS-XR-aaa-locald-cfg";


  prefix "aaa-locald-cfg";

  /*** LINKAGE (IMPORTS / INCLUDES) ***/

  import Cisco-IOS-XR-types { prefix "xr"; }

  import Cisco-IOS-XR-aaa-lib-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR aaa-locald package configuration.

     This YANG module augments the
       Cisco-IOS-XR-aaa-lib-cfg
     module with configuration data.

     Copyright (c) 2013-2017 by Cisco Systems, Inc.
     All rights reserved.";

  revision "2015-11-09" {
    description
      "IOS XR 6.0 revision.";
  }

  typedef Aaa-locald-task-id {
    type string;
    description "Aaa locald task id";
  }
  typedef Aaa-password {
    type enumeration {
      enum type5 {
        value 5;
        description "Type 5 password";
      }
      enum type8 {
        value 8;
        description "Type 8 password";
      }
      enum type9 {
        value 9;
        description "Type 9 password";
      }
    }
    description "Aaa password";
  }
  typedef Aaa-locald-task-class {
    type enumeration {
      enum read {
        value 0;
        description "Permits read operation for a Task ID";
      }
      enum write {
        value 1;
        description "Permits write operation for a Task ID";
      }
      enum execute {
        value 2;
        description "Permits execute operation for a Task ID";
      }
      enum debug {
        value 3;
        description "Permits debug operation for a Task ID";
      }
    }
    description "Aaa locald task class";
  }

  augment "/a1:aaa" {

    container server-groups {
      description "AAA group definitions";
    }
    description
      "This augment extends the configuration data of
      'Cisco-IOS-XR-aaa-lib-cfg'";
  }

  augment "/a1:aaa" {
    leaf default-taskgroup {
      type string;
      description
        "This class is used for setting the default
        taskgroup to be used for remote server
        authentication";
    }
    description
      "This augment extends the configuration data of
      'Cisco-IOS-XR-aaa-lib-cfg'";
  }

  augment "/a1:aaa" {

    container usernames {
      description "Configure local usernames";

      list username {
        key "name";
        description "Local username";

        container secret {
          description "Specify the secret for the user";
          leaf type {
            type Aaa-password;
            description "Password type";
          }
          leaf secret5 {
            when "../type = 'type5'" {
              description "../Type = Type5";
            }
            type xr:Md5-password;
            description "The user's secret password";
          }
          leaf secret8 {
            when "../type = 'type8'" {
              description "../Type = Type8";
            }
            type xr:Type8-password;
            description "Type 8 password";
          }
          leaf secret9 {
            when "../type = 'type9'" {
              description "../Type = Type9";
            }
            type xr:Type9-password;
            description "Type 9 password";
          }
        }

        container usergroup-under-usernames {
          description
            "Specify the usergroup to which this user
            belongs";

          list usergroup-under-username {
            key "name";
            description "Name of the usergroup";
            leaf name {
              type xr:Cisco-ios-xr-string;
              description "Name of the usergroup";
            }
          }
        }
        leaf password {
          type xr:Proprietary-password;
          description "Specify the password for the user";
        }
        leaf name {
          type string;
          description "Username";
        }
      }
    }
    description
      "This augment extends the configuration data of
      'Cisco-IOS-XR-aaa-lib-cfg'";
  }

  augment "/a1:aaa" {

    container taskgroups {
      description "Specify a taskgroup to inherit from";

      list taskgroup {
        key "name";
        description "Taskgroup name";

        container taskgroup-under-taskgroups {
          description "Specify a taskgroup to inherit from";

          list taskgroup-under-taskgroup {
            key "name";
            description "Name of the task group to include";
            leaf name {
              type xr:Cisco-ios-xr-string;
              description "Name of the task group to include";
            }
          }
        }

        container tasks {
          description "Specify task IDs to be part of this group";

          list task {
            key "type task-id";
            description "Task ID to be included";
            leaf type {
              type Aaa-locald-task-class;
              description
                "This specifies the operation permitted for
                this task eg: read/write/execute/debug";
            }
            leaf task-id {
              type Aaa-locald-task-id;
              description
                "Task ID to which permission is to be granted
                (please use class AllTasks to get a list of
                valid task IDs)";
            }
          }
        }
        leaf description {
          type string;
          description "Description for the task group";
        }
        leaf name {
          type string;
          description "Taskgroup name";
        }
      }
    }
    description
      "This augment extends the configuration data of
      'Cisco-IOS-XR-aaa-lib-cfg'";
  }

  augment "/a1:aaa" {

    container usergroups {
      description "Specify a Usergroup to inherit from";

      list usergroup {
        key "name";
        description "Usergroup name";

        container taskgroup-under-usergroups {
          description "Task group associated with this group";

          list taskgroup-under-usergroup {
            key "name";
            description "Name of the task group";
            leaf name {
              type xr:Cisco-ios-xr-string;
              description "Name of the task group";
            }
          }
        }

        container usergroup-under-usergroups {
          description "User group to be inherited by this group";

          list usergroup-under-usergroup {
            key "name";
            description "Name of the user group";
            leaf name {
              type xr:Cisco-ios-xr-string;
              description "Name of the user group";
            }
          }
        }
        leaf description {
          type string;
          description "Description for the user group";
        }
        leaf name {
          type string;
          description "Usergroup name";
        }
      }
    }
    description
      "This augment extends the configuration data of
      'Cisco-IOS-XR-aaa-lib-cfg'";
  }
}
