module Cisco-IOS-XR-sdr-invmgr-diag-oper {

  /*** NAMESPACE / PREFIX DEFINITION ***/

  namespace "http://cisco.com/ns/yang"+
    "/Cisco-IOS-XR-sdr-invmgr-diag-oper";


  prefix "sdr-invmgr-diag-oper";

  /*** LINKAGE (IMPORTS / INCLUDES) ***/

  import Cisco-IOS-XR-types { prefix "xr"; }

  include Cisco-IOS-XR-sdr-invmgr-diag-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR sdr-invmgr-diag package operational data.

     This module contains definitions
     for the following management objects:
       diag: Diag information

     Copyright (c) 2013-2017 by Cisco Systems, Inc.
     All rights reserved.";

  revision "2015-11-09" {
    description
      "IOS XR 6.0 revision.";
  }


  grouping INFORMATION {
    description "Common node of power-supply, fans";

    container information {
      description "Basic information";
      uses DIAG-EEPROM;
    }
  }

  container diag {
    config false;
    description "Diag information";

    container racks {
      description "Table of racks";

      list rack {
        key "rack-name";
        description "Rack name";

        container power-shelfs {
          description "Table for rack power shelf ";

          list power-shelf {
            key "power-shelf-name";
            description "Power shelf name";

            container power-supplies {
              description "Table for rack power supply ";

              list power-supply {
                key "power-supply-name";
                description "Power Supply name";
                leaf power-supply-name {
                  type xr:Cisco-ios-xr-string;
                  description "Power Supply name";
                }
                uses INFORMATION;
              }
            }
            leaf power-shelf-name {
              type xr:Cisco-ios-xr-string;
              description "Power Shelf name";
            }
          }
        }

        container fan-traies {
          description "Table for rack fan trays";

          list fan-tray {
            key "fan-tray-name";
            description "Fan tray name";

            container fanses {
              description "Table for rack fans ";

              list fans {
                key "fans-name";
                description "Fan name";
                leaf fans-name {
                  type xr:Cisco-ios-xr-string;
                  description "Fans name";
                }
                uses INFORMATION;
              }
            }
            leaf fan-tray-name {
              type xr:Cisco-ios-xr-string;
              description "Fan tray name";
            }
          }
        }

        container slots {
          description "Table of slots";

          list slot {
            key "slot-name";
            description "Slot name";

            container instances {
              description "Table of instances";

              list instance {
                key "name";
                description "instance number";

                container detail {
                  description "Detail information";
                  uses DIAG-CARD;
                }
                leaf name {
                  type xr:Cisco-ios-xr-string;
                  description "Instance name";
                }
              }
            }
            leaf slot-name {
              type xr:Cisco-ios-xr-string;
              description "Slot name";
            }
          }
        }

        container chassis {
          description "Chassis information";
          uses DIAG-EEPROM;
        }
        leaf rack-name {
          type xr:Cisco-ios-xr-string;
          description "Rack name";
        }
      }
    }
  }
}
