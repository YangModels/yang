submodule Cisco-IOS-XR-pmengine-oper-sub1 {

  belongs-to Cisco-IOS-XR-pmengine-oper {
    prefix Cisco-IOS-XR-pmengine-oper;
  }

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR pmengine package operational data.

     Copyright (c) 2013-2017 by Cisco Systems, Inc.
     All rights reserved.";

  revision "2017-05-01" {
    description
      "Fixing backward compatibility error in module.";
  }

  revision "2017-03-30" {
    description
      "OTU PRBS Stats Added";
  }

  revision "2015-11-09" {
    description
      "IOS XR 6.0 revision.";
  }

  typedef Pm-sonet-path-width-enum {
    type enumeration {
      enum none {
        value 0;
        description "Sonet Path Width NONE ";
      }
      enum sts1 {
        value 1;
        description "Sonet Path Width STS1 ";
      }
      enum sts3c-stm1 {
        value 2;
        description "Sonet Path Width sts3cSTM1 ";
      }
      enum sts12c-stm4 {
        value 3;
        description "Sonet Path Width sts12cSTM4 ";
      }
      enum sts24c {
        value 4;
        description "Sonet Path Width sts24 ";
      }
      enum sts48c-stm16 {
        value 5;
        description "Sonet Path Width sts48cSTM16 ";
      }
      enum sts192c-stm64 {
        value 6;
        description "Sonet Path Width sts192cSTM64 ";
      }
      enum sts768c-stm256 {
        value 7;
        description "Sonet Path Width sts768cSTM256 ";
      }
    }
    description "Sonet Path Width Enum";
  }
  typedef Pm-prbs-status-et {
    type enumeration {
      enum not-applicable {
        value 0;
        description "not applicable";
      }
      enum locked {
        value 1;
        description "locked";
      }
      enum un-locked {
        value 2;
        description "unlocked";
      }
    }
    description "PM PRBS Status Mode Enum";
  }
  typedef Pm-prbs-pattern-et {
    type enumeration {
      enum prbs-none {
        value 0;
        description "pn none";
      }
      enum pn31 {
        value 1;
        description "pn31";
      }
      enum pn23 {
        value 2;
        description "pn23";
      }
      enum pn11 {
        value 4;
        description "pn11";
      }
      enum inv-pn31 {
        value 8;
        description "inv pn31";
      }
      enum inv-pn11 {
        value 16;
        description "inv pn11";
      }
      enum pn15 {
        value 32;
        description "pn15";
      }
    }
    description "PM PRBS Pattern Mode Enum";
  }

  grouping PM-OPTICS-PARAMETER-STRING {
    description "one parameter in optics";
    leaf valid {
      type boolean;
      description "valid";
    }
    leaf minimum {
      type string;
      description "minimum";
    }
    leaf average {
      type string;
      description "average";
    }
    leaf maximum {
      type string;
      description "maximum";
    }
    leaf minimum-threshold {
      type string;
      description "minimun threshold";
    }
    leaf minimum-tca-report {
      type boolean;
      description "enable/disable to report TCA on min";
    }
    leaf maximum-threshold {
      type string;
      description "maximum threshold";
    }
    leaf maximum-tca-report {
      type boolean;
      description "enable/disable to report TCA on max";
    }
  }

  grouping PM-OPTICS-PARAMETER {
    description "one parameter in optics";
    leaf valid {
      type boolean;
      description "valid";
    }
    leaf minimum {
      type int32;
      description "minimum";
    }
    leaf average {
      type int32;
      description "average";
    }
    leaf maximum {
      type int32;
      description "maximum";
    }
    leaf minimum-threshold {
      type int32;
      description "minimun threshold";
    }
    leaf minimum-tca-report {
      type boolean;
      description "enable/disable to report TCA on min";
    }
    leaf maximum-threshold {
      type int32;
      description "maximum threshold";
    }
    leaf maximum-tca-report {
      type boolean;
      description "enable/disable to report TCA on max";
    }
  }

  grouping PM-OPTICS-PARAS {
    description "all paras in optics";

    container lbc {
      description "LBC";
      uses PM-OPTICS-PARAMETER;
    }

    container lbc-pc {
      description "LBC in percentage";
      uses PM-OPTICS-PARAMETER-STRING;
    }

    container opt {
      description "OPT";
      uses PM-OPTICS-PARAMETER-STRING;
    }

    container opr {
      description "OPR";
      uses PM-OPTICS-PARAMETER-STRING;
    }

    container cd {
      description "Chromatic Dispersion";
      uses PM-OPTICS-PARAMETER;
    }

    container dgd {
      description "Differential group Delay";
      uses PM-OPTICS-PARAMETER-STRING;
    }

    container pmd {
      description "Polarization Mode Dispersion";
      uses PM-OPTICS-PARAMETER-STRING;
    }

    container osnr {
      description "Optical Signal to Noise Ratio";
      uses PM-OPTICS-PARAMETER-STRING;
    }

    container center-wavelength {
      description "Center Wavelength/Frequency";
      uses PM-OPTICS-PARAMETER-STRING;
    }

    container pdl {
      description "Polarization Dependent Loss";
      uses PM-OPTICS-PARAMETER-STRING;
    }

    container pcr {
      description "Polarization Change Rate";
      uses PM-OPTICS-PARAMETER-STRING;
    }

    container pn {
      description "Phase Noise";
      uses PM-OPTICS-PARAMETER-STRING;
    }

    container rx-sig-pow {
      description "Rx signal power";
      uses PM-OPTICS-PARAMETER-STRING;
    }

    container low-sig-freq-off {
      description "low freq sig off";
      uses PM-OPTICS-PARAMETER;
    }
    leaf index {
      type uint32;
      description "index";
    }
    leaf valid {
      type boolean;
      description "valid";
    }
    leaf timestamp {
      type string;
      description "timestamp";
    }
    leaf last-clear-time {
      type string;
      description "last clear time";
    }
    leaf last-clear15-min-time {
      type string;
      description "last clear time";
    }
    leaf last-clear30-sec-time {
      type string;
      description "last clear time";
    }
    leaf last-clear24-hr-time {
      type string;
      description "last clear time";
    }
    leaf sec30-support {
      type boolean;
      description "30 sec support";
    }
  }

  grouping SONET-FAR-END-LINE-ENTRY {
    description "SONET FAR END LINE ENTRY";

    container far-end-line-e-ss {
      description "The number of Errored Seconds";
      uses PM-SONET-PARAMETER;
    }

    container far-end-line-se-ss {
      description "The number of Severely Errored Seconds";
      uses PM-SONET-PARAMETER;
    }

    container far-end-line-c-vs {
      description "The number of Coding Violations";
      uses PM-SONET-PARAMETER;
    }

    container far-end-line-ua-ss {
      description "The number of Unavailable Seconds";
      uses PM-SONET-PARAMETER;
    }

    container far-end-line-fc-ls {
      description "The number of Failure counts Seconds";
      uses PM-SONET-PARAMETER;
    }
  }

  grouping SONET-LINE-ENTRY {
    description "SONET LINE ENTRY";

    container line-e-ss {
      description "The number of Errored Seconds";
      uses PM-SONET-PARAMETER;
    }

    container line-se-ss {
      description "The number of Severely Errored Seconds";
      uses PM-SONET-PARAMETER;
    }

    container line-c-vs {
      description "The number of Coding Violations";
      uses PM-SONET-PARAMETER;
    }

    container line-ua-ss {
      description "The number of Unavailable Seconds";
      uses PM-SONET-PARAMETER;
    }

    container line-fc-ls {
      description "The number of Failure counts Seconds";
      uses PM-SONET-PARAMETER;
    }
    leaf line-status {
      type int32;
      description " status of the interface";
    }
  }

  grouping PM-SONET-PARAMETER {
    description "pm one parameter";
    leaf data {
      type uint32;
      description "the number in the interval";
    }
    leaf threshold {
      type uint32;
      description "the threshold users set";
    }
    leaf tca-report {
      type boolean;
      description "enable/disable to report TCA";
    }
  }

  grouping SONET-SECTION-ENTRY {
    description "SONET SECTION ENTRY";

    container section-e-ss {
      description "The number of Errored Seconds";
      uses PM-SONET-PARAMETER;
    }

    container section-se-ss {
      description "The number of Severely Errored Seconds";
      uses PM-SONET-PARAMETER;
    }

    container section-sef-ss {
      description "The number of Severely Errored Framing Seconds";
      uses PM-SONET-PARAMETER;
    }

    container section-c-vs {
      description "The number of Coding Violations";
      uses PM-SONET-PARAMETER;
    }
    leaf section-status {
      type int32;
      description " status of the interface";
    }
  }

  grouping PM-SONET-PARAS {
    description "all paras in ocn";

    container section {
      description "SECTION";
      uses SONET-SECTION-ENTRY;
    }

    container line {
      description "LINE";
      uses SONET-LINE-ENTRY;
    }

    container fe-line {
      description "FarEnd LINE";
      uses SONET-FAR-END-LINE-ENTRY;
    }
    leaf index {
      type uint32;
      description "index";
    }
    leaf valid {
      type boolean;
      description "valid";
    }
    leaf timestamp {
      type string {
        length "0..64";
      }
      description "timestamp";
    }
    leaf last-clear-time {
      type string {
        length "0..64";
      }
      description "last clear time";
    }
    leaf last-clear15-min-time {
      type string {
        length "0..64";
      }
      description "last clear time";
    }
    leaf last-clear24-hr-time {
      type string {
        length "0..64";
      }
      description "last clear time";
    }
  }

  grouping SONET-FAR-END-PATH-ENTRY {
    description "SONET FAR END PATH ENTRY";
    leaf far-end-path-e-ss {
      type uint32;
      units "second";
      description "The number of Errored Seconds";
    }
    leaf far-end-path-se-ss {
      type uint32;
      units "second";
      description "The number of Severely Errored Seconds";
    }
    leaf far-end-path-c-vs {
      type uint32;
      description "The number of Coding Violations";
    }
    leaf far-end-path-ua-ss {
      type uint32;
      units "second";
      description "The number of Unavailable Seconds";
    }
  }

  grouping PM-SONET-PATH-PARAMETER {
    description "pm one parameter";
    leaf data {
      type uint32;
      description "the number in the interval";
    }
    leaf threshold {
      type uint32;
      description "the threshold users set";
    }
    leaf tca-report {
      type boolean;
      description "enable/disable to report TCA";
    }
  }

  grouping SONET-PATH-ENTRY {
    description "SONET PATH ENTRY";

    container path-e-ss {
      description "The number of Errored Seconds";
      uses PM-SONET-PATH-PARAMETER;
    }

    container path-se-ss {
      description "The number of Severely Errored Seconds";
      uses PM-SONET-PATH-PARAMETER;
    }

    container path-c-vs {
      description "The number of Coding Violations";
      uses PM-SONET-PATH-PARAMETER;
    }

    container path-ua-ss {
      description "The number of Unavailable Seconds";
      uses PM-SONET-PATH-PARAMETER;
    }
    leaf path-width {
      type Pm-sonet-path-width-enum;
      description "Indicates the type of the SONET/SDH Path";
    }
    leaf path-status {
      type int32;
      description " status of the interface";
    }
  }

  grouping PM-SONET-PATH-PARAS {
    description "all paras in sts";

    container path {
      description "PATH";
      uses SONET-PATH-ENTRY;
    }

    container fe-path {
      description "Far End PATH";
      uses SONET-FAR-END-PATH-ENTRY;
    }
    leaf index {
      type uint32;
      description "index";
    }
    leaf valid {
      type boolean;
      description "valid";
    }
    leaf timestamp {
      type string {
        length "0..64";
      }
      description "timestamp";
    }
    leaf last-clear-time {
      type string {
        length "0..64";
      }
      description "last clear time";
    }
    leaf last-clear15-min-time {
      type string {
        length "0..64";
      }
      description "last clear time";
    }
    leaf last-clear24-hr-time {
      type string {
        length "0..64";
      }
      description "last clear time";
    }
  }

  grouping STM-FAR-END-LINE-ENTRY {
    description "STM FAR END LINE ENTRY";

    container far-end-line-e-ss {
      description "The number of Errored Seconds";
      uses PM-STM-PARAMETER;
    }

    container far-end-line-es-rs {
      description "The number of Errored Seconds Ratio";
      uses PM-STM-PARAMETER-RATIO;
    }

    container far-end-line-ebb-es {
      description "The number of Background Block Errors";
      uses PM-STM-PARAMETER;
    }

    container far-end-line-bbe-rs {
      description "The number of Background Block Errors";
      uses PM-STM-PARAMETER-RATIO;
    }

    container far-end-line-se-ss {
      description "The number of Severely Errored Second";
      uses PM-STM-PARAMETER;
    }

    container far-end-line-ses-rs {
      description "The number of Severely Errored Second Ratio";
      uses PM-STM-PARAMETER-RATIO;
    }

    container far-end-line-ua-ss {
      description "The number of Unavailable Second";
      uses PM-STM-PARAMETER;
    }

    container far-end-line-e-bs {
      description "The number of Errored Block Second";
      uses PM-STM-PARAMETER;
    }
  }

  grouping STM-LINE-ENTRY {
    description "STM LINE ENTRY";

    container line-e-ss {
      description "The number of Errored Seconds";
      uses PM-STM-PARAMETER;
    }

    container line-es-rs {
      description "The number of Errored Seconds Ratio";
      uses PM-STM-PARAMETER-RATIO;
    }

    container line-bb-es {
      description "The number of Background Block Errors";
      uses PM-STM-PARAMETER;
    }

    container line-bbe-rs {
      description "The number of Background Block Errors";
      uses PM-STM-PARAMETER-RATIO;
    }

    container line-se-ss {
      description "The number of Severely Errored Second";
      uses PM-STM-PARAMETER;
    }

    container line-ses-rs {
      description "The number of Severely Errored Second Ratio";
      uses PM-STM-PARAMETER-RATIO;
    }

    container line-ua-ss {
      description "The number of Unavailable Second";
      uses PM-STM-PARAMETER;
    }

    container line-e-bs {
      description "The number of Errored Block Second";
      uses PM-STM-PARAMETER;
    }
    leaf line-status {
      type int32;
      description " status of the interface";
    }
  }

  grouping PM-STM-PARAMETER-RATIO {
    description "pm one parameter";
    leaf data {
      type string {
        length "0..8";
      }
      description "the number in the interval";
    }
    leaf threshold {
      type string {
        length "0..8";
      }
      description "the threshold users set";
    }
    leaf tca-report {
      type boolean;
      description "enable/disable to report TCA";
    }
  }

  grouping PM-STM-PARAMETER {
    description "pm one parameter";
    leaf data {
      type uint32;
      description "the number in the interval";
    }
    leaf threshold {
      type uint32;
      description "the threshold users set";
    }
    leaf tca-report {
      type boolean;
      description "enable/disable to report TCA";
    }
  }

  grouping STM-SECTION-ENTRY {
    description "STM SECTION ENTRY";

    container section-e-ss {
      description "The number of Errored Seconds";
      uses PM-STM-PARAMETER;
    }

    container section-es-rs {
      description "The number of Errored Seconds Ratio";
      uses PM-STM-PARAMETER-RATIO;
    }

    container section-bb-es {
      description "The number of Background Block Errors";
      uses PM-STM-PARAMETER;
    }

    container section-bbe-rs {
      description "The number of Background Block Errors";
      uses PM-STM-PARAMETER-RATIO;
    }

    container section-se-ss {
      description "The number of Severely Errored Second";
      uses PM-STM-PARAMETER;
    }

    container section-ses-rs {
      description "The number of Severely Errored Second Ratio";
      uses PM-STM-PARAMETER-RATIO;
    }

    container section-ua-ss {
      description "The number of Unavailable Second";
      uses PM-STM-PARAMETER;
    }

    container section-e-bs {
      description "The number of Errored Block Second";
      uses PM-STM-PARAMETER;
    }
    leaf section-status {
      type int32;
      description " status of the interface";
    }
  }

  grouping PM-STM-PARAS {
    description "all paras in stm";

    container section {
      description "SECTION";
      uses STM-SECTION-ENTRY;
    }

    container line {
      description "LINE";
      uses STM-LINE-ENTRY;
    }

    container fe-line {
      description "FarEnd LINE";
      uses STM-FAR-END-LINE-ENTRY;
    }
    leaf index {
      type uint32;
      description "index";
    }
    leaf valid {
      type boolean;
      description "valid";
    }
    leaf timestamp {
      type string {
        length "0..64";
      }
      description "timestamp";
    }
    leaf last-clear-time {
      type string {
        length "0..64";
      }
      description "last clear time";
    }
    leaf last-clear15-min-time {
      type string {
        length "0..64";
      }
      description "last clear time";
    }
    leaf last-clear24-hr-time {
      type string {
        length "0..64";
      }
      description "last clear time";
    }
  }

  grouping PM-FEC-PARAM-STRING {
    description "pm avg fec parameter";
    leaf minimum {
      type string;
      description "minimum";
    }
    leaf average {
      type string;
      description "average";
    }
    leaf maximum {
      type string;
      description "maximum";
    }
    leaf minimum-threshold {
      type string;
      description "minimun threshold";
    }
    leaf minimum-tca-report {
      type boolean;
      description "enable/disable to report TCA on min";
    }
    leaf maximum-threshold {
      type string;
      description "maximum threshold";
    }
    leaf maximum-tca-report {
      type boolean;
      description "enable/disable to report TCA";
    }
    leaf valid {
      type boolean;
      description "valid";
    }
  }

  grouping PM-FEC-PARAM {
    description "pm avg fec param";
    leaf data {
      type uint64;
      description "the number in the interval";
    }
    leaf threshold {
      type uint64;
      description "the threshold users set";
    }
    leaf tca-report {
      type boolean;
      description "enable/disable to report TCA";
    }
    leaf valid {
      type boolean;
      description "valid";
    }
  }

  grouping PM-FEC-PARAS {
    description "all paras in fec";

    container ec-bits {
      description "EC BITS";
      uses PM-FEC-PARAM;
    }

    container uc-words {
      description "UC WORDS";
      uses PM-FEC-PARAM;
    }

    container pre-fec-ber {
      description "Pre FEC BER";
      uses PM-FEC-PARAM-STRING;
    }

    container post-fec-ber {
      description "Post FEC BER";
      uses PM-FEC-PARAM-STRING;
    }

    container q {
      description "Q";
      uses PM-FEC-PARAM-STRING;
    }

    container qmargin {
      description "Q Margin";
      uses PM-FEC-PARAM-STRING;
    }
    leaf index {
      type uint32;
      description "index";
    }
    leaf valid {
      type boolean;
      description "valid";
    }
    leaf timestamp {
      type string;
      description "timestamp";
    }
    leaf last-clear-time {
      type string;
      description "last clear time";
    }
    leaf last-clear15-min-time {
      type string;
      description "last clear time";
    }
    leaf last-clear30-sec-time {
      type string;
      description "last clear time";
    }
    leaf last-clear24-hr-time {
      type string;
      description "last clear time";
    }
    leaf sec30-support {
      type boolean;
      description "30 sec support";
    }
  }

  grouping PM-OTN-PARAMETER-RATIO {
    description "pm one parameter";
    leaf data {
      type string;
      description "the number in the interval";
    }
    leaf threshold {
      type string;
      description "the threshold users set";
    }
    leaf tca-report {
      type boolean;
      description "enable/disable to report TCA";
    }
  }

  grouping PM-OTN-PARAMETER {
    description "pm one parameter";
    leaf data {
      type uint64;
      description "the number in the interval";
    }
    leaf threshold {
      type uint64;
      description "the threshold users set";
    }
    leaf tca-report {
      type boolean;
      description "enable/disable to report TCA";
    }
  }

  grouping PM-OTN-PARAS {
    description "all paras in otn";

    container lbc {
      description "LBC";
      uses PM-OTN-PARAMETER;
    }

    container es-ne {
      description "ES SM NE";
      uses PM-OTN-PARAMETER;
    }

    container esr-ne {
      description "ESR PM NE";
      uses PM-OTN-PARAMETER-RATIO;
    }

    container ses-ne {
      description "SES SM NE";
      uses PM-OTN-PARAMETER;
    }

    container sesr-ne {
      description "SESR SM NE";
      uses PM-OTN-PARAMETER-RATIO;
    }

    container uas-ne {
      description "UAS SM NE";
      uses PM-OTN-PARAMETER;
    }

    container bbe-ne {
      description "BBE SM NE";
      uses PM-OTN-PARAMETER;
    }

    container bber-ne {
      description "BBER SM NE";
      uses PM-OTN-PARAMETER-RATIO;
    }

    container fc-ne {
      description "FC SM NE";
      uses PM-OTN-PARAMETER;
    }

    container es-fe {
      description "ES SM FE";
      uses PM-OTN-PARAMETER;
    }

    container esr-fe {
      description "ESR PM FE";
      uses PM-OTN-PARAMETER-RATIO;
    }

    container ses-fe {
      description "SES SM FE";
      uses PM-OTN-PARAMETER;
    }

    container sesr-fe {
      description "SESR SM FE";
      uses PM-OTN-PARAMETER-RATIO;
    }

    container uas-fe {
      description "UAS SM FE";
      uses PM-OTN-PARAMETER;
    }

    container bbe-fe {
      description "BBE SM FE";
      uses PM-OTN-PARAMETER;
    }

    container bber-fe {
      description "BBER SM FE";
      uses PM-OTN-PARAMETER-RATIO;
    }

    container fc-fe {
      description "FC SM FE";
      uses PM-OTN-PARAMETER;
    }
    leaf index {
      type uint32;
      description "index";
    }
    leaf valid {
      type boolean;
      description "valid";
    }
    leaf timestamp {
      type string;
      description "timestamp";
    }
    leaf last-clear-time {
      type string;
      description "last clear time";
    }
    leaf last-clear15-min-time {
      type string;
      description "last clear time";
    }
    leaf last-clear30-sec-time {
      type string;
      description "last clear time";
    }
    leaf last-clear24-hr-time {
      type string;
      description "last clear time";
    }
    leaf sec30-support {
      type boolean;
      description "30 sec support";
    }
  }

  grouping PM-PRBS-STATUS-PARAMETER {
    description "one parameter in optics";
    leaf valid {
      type boolean;
      description "valid";
    }
    leaf prbs-status {
      type Pm-prbs-status-et;
      description "Prbs Status";
    }
  }

  grouping PM-PRBS-PARAMETER {
    description "one parameter in optics";
    leaf valid {
      type boolean;
      description "valid";
    }
    leaf rcv-patt {
      type Pm-prbs-pattern-et;
      description "RCVD PTRN";
    }
  }

  grouping PM-PRBS-PARAS {
    description "all paras in prbs";

    container rcv-patt {
      description "RCVD PTRN";
      uses PM-PRBS-PARAMETER;
    }

    container prbs-status {
      description "PRBS STATUS";
      uses PM-PRBS-STATUS-PARAMETER;
    }
    leaf index {
      type uint32;
      description "index";
    }
    leaf valid {
      type boolean;
      description "valid";
    }
    leaf timestamp {
      type string {
        length "0..64";
      }
      description "timestamp";
    }
    leaf last-clear-time {
      type string {
        length "0..64";
      }
      description "last clear time";
    }
    leaf last-clear15-min-time {
      type string {
        length "0..64";
      }
      description "last clear time";
    }
    leaf last-clear24-hr-time {
      type string {
        length "0..64";
      }
      description "last clear time";
    }
    leaf ebc {
      type uint64;
      description "EBC";
    }
    leaf found-count {
      type uint32;
      description "FOUND COUNT";
    }
    leaf lost-count {
      type uint32;
      description "LOST COUNT";
    }
    leaf found-at-time {
      type uint64;
      description "FOUND AT TS";
    }
    leaf lost-at-time {
      type uint64;
      description "LOST AT TS";
    }
    leaf conf-patt {
      type Pm-prbs-pattern-et;
      description "CONFIG PTRN";
    }
  }

  grouping PM-GFP-PARAM {
    description "PM GFP PARAM";
    leaf data {
      type uint64;
      description "the number in the interval";
    }
    leaf threshold {
      type uint64;
      description "the threshold users set";
    }
    leaf tca-report {
      type boolean;
      description "enable/disable to report TCA";
    }
  }

  grouping PM-GFP-PARAS {
    description "PM GFP PARAS";

    container rx-bit-err {
      description "RX BIT ERR";
      uses PM-GFP-PARAM;
    }

    container rx-inv-typ {
      description "RX INV TYP";
      uses PM-GFP-PARAM;
    }

    container rx-crc {
      description "RX CRC";
      uses PM-GFP-PARAM;
    }

    container rx-lfd {
      description "RX LFD";
      uses PM-GFP-PARAM;
    }

    container rx-csf {
      description "RX CSF";
      uses PM-GFP-PARAM;
    }
    leaf index {
      type uint32;
      description "index";
    }
    leaf valid {
      type boolean;
      description "valid";
    }
    leaf timestamp {
      type string {
        length "0..64";
      }
      description "timestamp";
    }
    leaf last-clear-time {
      type string {
        length "0..64";
      }
      description "last clear time";
    }
    leaf last-clear15-min-time {
      type string {
        length "0..64";
      }
      description "last clear time";
    }
    leaf last-clear30-sec-time {
      type string {
        length "0..64";
      }
      description "last clear time";
    }
    leaf last-clear24-hr-time {
      type string {
        length "0..64";
      }
      description "last clear time";
    }
    leaf sec30-support {
      type boolean;
      description "30 sec support";
    }
  }

  grouping HO-VC-FAR-END-PATH-ENTRY {
    description "HO VC FAR END PATH ENTRY";
    leaf far-end-path-e-ss {
      type uint32;
      units "second";
      description "The number of Errored Seconds";
    }
    leaf far-end-path-se-ss {
      type uint32;
      units "second";
      description "The number of Severely Errored Seconds";
    }
    leaf far-end-path-c-vs {
      type uint32;
      description "The number of Coding Violations";
    }
    leaf far-end-path-ua-ss {
      type uint32;
      units "second";
      description "The number of Unavailable Seconds";
    }
  }

  grouping PM-HO-VC-PARAMETER-RATIO {
    description "pm one parameter";
    leaf data {
      type string {
        length "0..8";
      }
      description "the number in the interval";
    }
    leaf threshold {
      type string {
        length "0..8";
      }
      description "the threshold users set";
    }
    leaf tca-report {
      type boolean;
      description "enable/disable to report TCA";
    }
  }

  grouping PM-HO-VC-PARAMETER {
    description "pm one parameter";
    leaf data {
      type uint32;
      description "the number in the interval";
    }
    leaf threshold {
      type uint32;
      description "the threshold users set";
    }
    leaf tca-report {
      type boolean;
      description "enable/disable to report TCA";
    }
  }

  grouping HO-VC-ENTRY {
    description "HO VC ENTRY";

    container path-e-ss {
      description "The number of Errored Seconds";
      uses PM-HO-VC-PARAMETER;
    }

    container path-es-rs {
      description "The number of Errored Seconds";
      uses PM-HO-VC-PARAMETER-RATIO;
    }

    container path-se-ss {
      description "The number of Severely Errored Seconds";
      uses PM-HO-VC-PARAMETER;
    }

    container path-ses-rs {
      description "The number of Severely Errored Seconds";
      uses PM-HO-VC-PARAMETER-RATIO;
    }

    container path-e-bs {
      description "The number of Errored blocks";
      uses PM-HO-VC-PARAMETER;
    }

    container path-ua-ss {
      description "The number of Unavailable Seconds";
      uses PM-HO-VC-PARAMETER;
    }

    container path-bb-es {
      description "The number of background block errors";
      uses PM-HO-VC-PARAMETER;
    }

    container path-bbe-rs {
      description "The number of background block errors";
      uses PM-HO-VC-PARAMETER-RATIO;
    }
    leaf path-status {
      type int32;
      description " status of the interface";
    }
  }

  grouping PM-HO-VC-PARAS {
    description "all paras in ho_vc";

    container path {
      description "PATH";
      uses HO-VC-ENTRY;
    }

    container fe-path {
      description "Far End PATH";
      uses HO-VC-FAR-END-PATH-ENTRY;
    }
    leaf index {
      type uint32;
      description "index";
    }
    leaf valid {
      type boolean;
      description "valid";
    }
    leaf timestamp {
      type string {
        length "0..64";
      }
      description "timestamp";
    }
    leaf last-clear-time {
      type string {
        length "0..64";
      }
      description "last clear time";
    }
    leaf last-clear15-min-time {
      type string {
        length "0..64";
      }
      description "last clear time";
    }
    leaf last-clear24-hr-time {
      type string {
        length "0..64";
      }
      description "last clear time";
    }
  }

  grouping PM-ETHER-PARAM-STRING {
    description "PM ETHER PARAM STRING";
    leaf data {
      type string;
      description "the number in the interval";
    }
    leaf threshold {
      type string;
      description "the threshold users set";
    }
    leaf tca-report {
      type boolean;
      description "enable/disable to report TCA";
    }
    leaf valid {
      type boolean;
      description "valid";
    }
  }

  grouping PM-ETHER-PARAM {
    description "PM ETHER PARAM";
    leaf data {
      type uint64;
      description "the number in the interval";
    }
    leaf threshold {
      type uint64;
      description "the threshold users set";
    }
    leaf tca-report {
      type boolean;
      description "enable/disable to report TCA";
    }
    leaf valid {
      type boolean;
      description "valid";
    }
  }

  grouping PM-ETHERNET-PARAS {
    description "all paras in ether";

    container rx-pkt {
      description "RX PKT";
      uses PM-ETHER-PARAM;
    }

    container stat-pkt {
      description "STAT PKT";
      uses PM-ETHER-PARAM;
    }

    container octet-stat {
      description "OCTET STAT";
      uses PM-ETHER-PARAM;
    }

    container oversize-pkt-stat {
      description "OVERSIZE PKT";
      uses PM-ETHER-PARAM;
    }

    container fcs-errors-stat {
      description "FCS ERR";
      uses PM-ETHER-PARAM;
    }

    container long-frames-stat {
      description "LONG FRAMES";
      uses PM-ETHER-PARAM;
    }

    container jabber-stat {
      description "JABBER STATS";
      uses PM-ETHER-PARAM;
    }

    container ether64-octets {
      description "SIXTY FOUR OCTET";
      uses PM-ETHER-PARAM;
    }

    container ether65127-octet {
      description "OCTET";
      uses PM-ETHER-PARAM;
    }

    container ether128255-octet {
      description "TFF OCTET";
      uses PM-ETHER-PARAM;
    }

    container ether256511-octet {
      description "FOO OCTET";
      uses PM-ETHER-PARAM;
    }

    container ether5121023-octet {
      description "OZTT OCTET";
      uses PM-ETHER-PARAM;
    }

    container ether10241518-octet {
      description "OFO OCTET";
      uses PM-ETHER-PARAM;
    }

    container in-ucast-pkt {
      description "IN UCAST";
      uses PM-ETHER-PARAM;
    }

    container in-mcast-pkt {
      description "IN MCAST";
      uses PM-ETHER-PARAM;
    }

    container in-bcast-pkt {
      description "IN BCAST";
      uses PM-ETHER-PARAM;
    }

    container out-ucast-pkt {
      description "OUT UCAST";
      uses PM-ETHER-PARAM;
    }

    container out-bcast-pkt {
      description "OUT BCAST";
      uses PM-ETHER-PARAM;
    }

    container out-mcast-pkt {
      description "OUT MCAST";
      uses PM-ETHER-PARAM;
    }

    container tx-pkt {
      description "TX PKT";
      uses PM-ETHER-PARAM;
    }

    container if-in-errors {
      description "IFIN ERRORS";
      uses PM-ETHER-PARAM;
    }

    container if-in-octets {
      description "IFIN OCTETS";
      uses PM-ETHER-PARAM;
    }

    container ether-stat-multicast-pkt {
      description "ETHER STAT MULTICAST PKT";
      uses PM-ETHER-PARAM;
    }

    container ether-stat-broadcast-pkt {
      description "ETHER STAT BROADCAST PKT";
      uses PM-ETHER-PARAM;
    }

    container ether-stat-undersized-pkt {
      description "ETHER STAT UNDERSIZED PKT";
      uses PM-ETHER-PARAM;
    }

    container out-octets {
      description "OUT OCTET";
      uses PM-ETHER-PARAM;
    }

    container in-pause-frame {
      description "INPUT PAUSE FRAME";
      uses PM-ETHER-PARAM;
    }

    container in-good-bytes {
      description "INPUT GOOD BYTES";
      uses PM-ETHER-PARAM;
    }

    container in8021q-frames {
      description "INPUT 802 1Q FRAMES";
      uses PM-ETHER-PARAM;
    }

    container in-pkts1519-max-octets {
      description "INPUT PKTS 1519MAX OCTETS";
      uses PM-ETHER-PARAM;
    }

    container in-good-pkts {
      description "INPUT GOOD PKTS";
      uses PM-ETHER-PARAM;
    }

    container in-drop-overrun {
      description "INPUT DROP OVERRUN";
      uses PM-ETHER-PARAM;
    }

    container in-drop-abort {
      description "INPUT DROP ABORT";
      uses PM-ETHER-PARAM;
    }

    container in-drop-invalid-vlan {
      description "INPUT DROP INVALID VLAN";
      uses PM-ETHER-PARAM;
    }

    container in-drop-invalid-dmac {
      description "INPUT DROP INVALID DMAC";
      uses PM-ETHER-PARAM;
    }

    container in-drop-invalid-encap {
      description "INPUT DROP INVALID ENCAP";
      uses PM-ETHER-PARAM;
    }

    container in-drop-other {
      description "INPUT DROP OTHER";
      uses PM-ETHER-PARAM;
    }

    container in-mib-giant {
      description "INPUT MIB GIANT";
      uses PM-ETHER-PARAM;
    }

    container in-mib-jabber {
      description "INPUT MIB JABBER";
      uses PM-ETHER-PARAM;
    }

    container in-mibcrc {
      description "IN MIB CRC";
      uses PM-ETHER-PARAM;
    }

    container in-error-collisions {
      description "IN ERROR COLLISIONS";
      uses PM-ETHER-PARAM;
    }

    container in-error-symbol {
      description "IN ERROR SYMBOL";
      uses PM-ETHER-PARAM;
    }

    container out-good-bytes {
      description "OUT GOOD BYTES";
      uses PM-ETHER-PARAM;
    }

    container out8021q-frames {
      description "OUT 802 1Q FRAMES";
      uses PM-ETHER-PARAM;
    }

    container out-pause-frames {
      description "OUT PAUSE FRAMES";
      uses PM-ETHER-PARAM;
    }

    container out-pkts1519-max-octets {
      description "OUT PKTS 1519 MAX OCTETS";
      uses PM-ETHER-PARAM;
    }

    container out-good-pkts {
      description "OUT GOOD PKTS";
      uses PM-ETHER-PARAM;
    }

    container out-drop-underrun {
      description "OUT DROP UNDERRUN";
      uses PM-ETHER-PARAM;
    }

    container out-drop-abort {
      description "OUT DROP ABORT";
      uses PM-ETHER-PARAM;
    }

    container out-drop-other {
      description "OUT DROP OTHER";
      uses PM-ETHER-PARAM;
    }

    container out-error-other {
      description "OUT ERROR OTHER";
      uses PM-ETHER-PARAM;
    }

    container in-error-giant {
      description "IN ERROR GIANT";
      uses PM-ETHER-PARAM;
    }

    container in-error-runt {
      description "IN ERROR RUNT";
      uses PM-ETHER-PARAM;
    }

    container in-error-jabbers {
      description "IN ERROR JABBERS";
      uses PM-ETHER-PARAM;
    }

    container in-error-fragments {
      description "IN ERROR FRAGMENTS";
      uses PM-ETHER-PARAM;
    }

    container in-error-other {
      description "IN ERROR OTHER";
      uses PM-ETHER-PARAM;
    }

    container in-pkt64-octet {
      description "IN PKT 64 OCTET";
      uses PM-ETHER-PARAM;
    }

    container in-pkts65-to127-octets {
      description "IN PKTS 65 127OCTETS";
      uses PM-ETHER-PARAM;
    }

    container in-pkts128-to255-octets {
      description "IN PKTS 128 255 OCTETS";
      uses PM-ETHER-PARAM;
    }

    container in-pkts256-to511-octets {
      description "IN PKTS 256 511 OCTETS";
      uses PM-ETHER-PARAM;
    }

    container in-pkts512-to1023-octets {
      description "IN PKTS 512 1023 OCTETS";
      uses PM-ETHER-PARAM;
    }

    container in-pkts1024-to1518-octets {
      description "IN PKTS 1024 1518 OCTETS";
      uses PM-ETHER-PARAM;
    }

    container outpkt64octet {
      description "OUT PKT 64 OCTET";
      uses PM-ETHER-PARAM;
    }

    container out-pkts65127-octets {
      description "OUT PKTS 65 127OCTETS";
      uses PM-ETHER-PARAM;
    }

    container out-pkts128255-octets {
      description "OUT PKTS 128 255 OCTETS";
      uses PM-ETHER-PARAM;
    }

    container out-pkts256511-octets {
      description "OUT PKTS 256 511 OCTETS";
      uses PM-ETHER-PARAM;
    }

    container out-pkts5121023-octets {
      description "OUT PKTS 512 1023 OCTETS";
      uses PM-ETHER-PARAM;
    }

    container out-pkts10241518-octets {
      description "OUT PKTS 1024 1518 OCTETS";
      uses PM-ETHER-PARAM;
    }

    container rx-util {
      description "Rx Utilization in Percent";
      uses PM-ETHER-PARAM-STRING;
    }

    container tx-util {
      description "Tx Utilization in Percent";
      uses PM-ETHER-PARAM-STRING;
    }

    container tx-undersized-pkt {
      description "TX Undersized Pkt";
      uses PM-ETHER-PARAM;
    }

    container tx-oversized-pkt {
      description "TX Oversized Pkt";
      uses PM-ETHER-PARAM;
    }

    container tx-fragments {
      description "TX Fragments";
      uses PM-ETHER-PARAM;
    }

    container tx-jabber {
      description "TX Jabber";
      uses PM-ETHER-PARAM;
    }

    container tx-bad-fcs {
      description "TX Bad Fcs";
      uses PM-ETHER-PARAM;
    }
    leaf index {
      type uint32;
      description "index";
    }
    leaf valid {
      type boolean;
      description "valid";
    }
    leaf timestamp {
      type string {
        length "0..64";
      }
      description "timestamp";
    }
    leaf last-clear-time {
      type string;
      description "last clear time";
    }
    leaf last-clear30-sec-time {
      type string;
      description "last clear time";
    }
    leaf last-clear15-min-time {
      type string;
      description "last clear time";
    }
    leaf last-clear24-hr-time {
      type string;
      description "last clear time";
    }
    leaf sec30-support {
      type boolean;
      description "30 sec support";
    }
  }

  grouping PM-SECY-TX-PARAM {
    description "PM SECY TX PARAM";
    leaf data {
      type uint64;
      description "the number in the interval";
    }
    leaf threshold {
      type uint64;
      description "the threshold users set";
    }
    leaf tca-report {
      type boolean;
      description "enable/disable to report TCA";
    }
    leaf valid {
      type boolean;
      description "valid";
    }
  }

  grouping PM-SECY-TX-PARAS {
    description "PM SECY TX PARAS";

    container out-pkts-protected {
      description "Out Packets Protected";
      uses PM-SECY-TX-PARAM;
    }

    container out-pkts-encrypted {
      description "Out Packets Encrypted";
      uses PM-SECY-TX-PARAM;
    }

    container out-octets-protected {
      description "Out Octets Protected ";
      uses PM-SECY-TX-PARAM;
    }

    container out-octets-encrypted {
      description "Out Octets Encrypted";
      uses PM-SECY-TX-PARAM;
    }

    container out-pkts-too-long {
      description "Out Packets Too Long";
      uses PM-SECY-TX-PARAM;
    }
    leaf index {
      type uint32;
      description "index";
    }
    leaf valid {
      type boolean;
      description "valid";
    }
    leaf timestamp {
      type string {
        length "0..64";
      }
      description "timestamp";
    }
    leaf last-clear-time {
      type string {
        length "0..64";
      }
      description "last clear time";
    }
    leaf last-clear15-min-time {
      type string {
        length "0..64";
      }
      description "last clear time";
    }
    leaf last-clear30-sec-time {
      type string {
        length "0..64";
      }
      description "last clear time";
    }
    leaf last-clear24-hr-time {
      type string {
        length "0..64";
      }
      description "last clear time";
    }
    leaf sec30-support {
      type boolean;
      description "30 sec support";
    }
    leaf sample-count {
      type uint64;
      description "Running Sample Count";
    }
  }

  grouping PM-SECY-RX-PARAM {
    description "PM SECY RX PARAM";
    leaf data {
      type uint64;
      description "the number in the interval";
    }
    leaf threshold {
      type uint64;
      description "the threshold users set";
    }
    leaf tca-report {
      type boolean;
      description "enable/disable to report TCA";
    }
    leaf valid {
      type boolean;
      description "valid";
    }
  }

  grouping PM-SECY-RX-PARAS {
    description "PM SECY RX PARAS";

    container in-pkts-unchecked {
      description "In Packet Unchecked";
      uses PM-SECY-RX-PARAM;
    }

    container in-pkts-delayed {
      description "In Packet Delay";
      uses PM-SECY-RX-PARAM;
    }

    container in-pkts-late {
      description "In Packet Late";
      uses PM-SECY-RX-PARAM;
    }

    container in-pkts-ok {
      description "In Packet Ok";
      uses PM-SECY-RX-PARAM;
    }

    container in-pkts-invalid {
      description "In Packet Invalid";
      uses PM-SECY-RX-PARAM;
    }

    container in-pkts-not-valid {
      description "In Packet Not Valid";
      uses PM-SECY-RX-PARAM;
    }

    container in-pkts-not-using-sa {
      description "In Packet Not Using SA";
      uses PM-SECY-RX-PARAM;
    }

    container in-pkts-unused-sa {
      description "In Packet Unused SA";
      uses PM-SECY-RX-PARAM;
    }

    container in-pkts-untagged-hit {
      description "In Packet Untagged Hit";
      uses PM-SECY-RX-PARAM;
    }

    container in-octets-validated {
      description "In Octet Validated";
      uses PM-SECY-RX-PARAM;
    }

    container in-octets-decrypted {
      description "In Octet Decrypted";
      uses PM-SECY-RX-PARAM;
    }
    leaf index {
      type uint32;
      description "index";
    }
    leaf valid {
      type boolean;
      description "valid";
    }
    leaf timestamp {
      type string {
        length "0..64";
      }
      description "timestamp";
    }
    leaf last-clear-time {
      type string {
        length "0..64";
      }
      description "last clear time";
    }
    leaf last-clear15-min-time {
      type string {
        length "0..64";
      }
      description "last clear time";
    }
    leaf last-clear30-sec-time {
      type string {
        length "0..64";
      }
      description "last clear time";
    }
    leaf last-clear24-hr-time {
      type string {
        length "0..64";
      }
      description "last clear time";
    }
    leaf sec30-support {
      type boolean;
      description "30 sec support";
    }
    leaf sample-count {
      type uint64;
      description "Running Sample Count";
    }
  }

  grouping PM-SECY-IF-PARAM {
    description "PM SECY IF PARAM";
    leaf data {
      type uint64;
      description "the number in the interval";
    }
    leaf threshold {
      type uint64;
      description "the threshold users set";
    }
    leaf tca-report {
      type boolean;
      description "enable/disable to report TCA";
    }
    leaf valid {
      type boolean;
      description "valid";
    }
  }

  grouping PM-SECY-IF-PARAS {
    description "PM SECY IF PARAS";

    container in-pkts-untagged {
      description "In Packet Untagged";
      uses PM-SECY-IF-PARAM;
    }

    container in-pkts-no-tag {
      description "In Packet No tag";
      uses PM-SECY-IF-PARAM;
    }

    container in-pkts-bad-tag {
      description "In Packet Bad tag";
      uses PM-SECY-IF-PARAM;
    }

    container in-pkts-unknown-sci {
      description "In Packet Unknown sci";
      uses PM-SECY-IF-PARAM;
    }

    container in-pkts-no-sci {
      description "In Packet No sci";
      uses PM-SECY-IF-PARAM;
    }

    container in-pkts-overrun {
      description "In Packet Overrun";
      uses PM-SECY-IF-PARAM;
    }

    container in-octets-validated {
      description "In Octet Validated";
      uses PM-SECY-IF-PARAM;
    }

    container in-octets-decrypted {
      description "In Octet Decrypted";
      uses PM-SECY-IF-PARAM;
    }

    container out-pkts-untagged {
      description "Out Packet Untagged";
      uses PM-SECY-IF-PARAM;
    }

    container out-pkts-too-long {
      description "Out Packet Too Long";
      uses PM-SECY-IF-PARAM;
    }

    container out-octets-protected {
      description "Out Octet Protected";
      uses PM-SECY-IF-PARAM;
    }

    container out-octets-encrypted {
      description "Out Octet encrypted";
      uses PM-SECY-IF-PARAM;
    }
    leaf index {
      type uint32;
      description "index";
    }
    leaf valid {
      type boolean;
      description "valid";
    }
    leaf timestamp {
      type string {
        length "0..64";
      }
      description "timestamp";
    }
    leaf last-clear-time {
      type string {
        length "0..64";
      }
      description "last clear time";
    }
    leaf last-clear15-min-time {
      type string {
        length "0..64";
      }
      description "last clear time";
    }
    leaf last-clear30-sec-time {
      type string {
        length "0..64";
      }
      description "last clear time";
    }
    leaf last-clear24-hr-time {
      type string {
        length "0..64";
      }
      description "last clear time";
    }
    leaf sec30-support {
      type boolean;
      description "30 sec support";
    }
    leaf sample-count {
      type uint64;
      description "Running Sample Count";
    }
  }
}
