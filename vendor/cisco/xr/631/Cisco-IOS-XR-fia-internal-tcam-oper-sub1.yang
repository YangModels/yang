submodule Cisco-IOS-XR-fia-internal-tcam-oper-sub1 {

  belongs-to Cisco-IOS-XR-fia-internal-tcam-oper {
    prefix Cisco-IOS-XR-fia-internal-tcam-oper;
  }

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR fia-internal-tcam package operational data.

     Copyright (c) 2013-2017 by Cisco Systems, Inc.
     All rights reserved.";

  revision "2015-11-09" {
    description
      "IOS XR 6.0 revision.";
  }


  grouping FIA-TCAM-DB {
    description "FIA TCAM DB";
    leaf db-id {
      type uint32;
      description "db id";
    }
    leaf db-inuse-entries {
      type uint32;
      description "db inuse entries";
    }
    leaf db-prefix {
      type string;
      description "db prefix";
    }
  }

  grouping FIA-TCAM-BANK {
    description "FIA TCAM BANK";
    leaf bank-id {
      type string;
      description "bank id";
    }
    leaf bank-key-size {
      type string;
      description "bank key size";
    }
    leaf bank-free-entries {
      type uint32;
      description "bank free entries";
    }
    leaf bank-inuse-entries {
      type uint32;
      description "bank inuse entries";
    }
    leaf owner {
      type string;
      description "owner";
    }
    leaf nof-dbs {
      type uint32;
      description "nof dbs";
    }

    list bank-db {
      description "bank db";
      uses FIA-TCAM-DB;
    }
  }

  grouping FIA-NPU-TCAM {
    description "FIA NPU TCAM";
    leaf npu-id {
      type uint32;
      description "npu id";
    }

    list tcam-bank {
      description "tcam bank";
      uses FIA-TCAM-BANK;
    }
  }

  grouping FIA-CARD-TCAM {
    description "FIA CARD TCAM";

    list npu-tcam {
      description "npu tcam";
      uses FIA-NPU-TCAM;
    }
  }
}
