module Cisco-IOS-XR-asr9k-ptp-pd-cfg {

  /*** NAMESPACE / PREFIX DEFINITION ***/

  namespace "http://cisco.com/ns/yang/Cisco-IOS-XR-asr9k-ptp-pd-cfg";


  prefix "asr9k-ptp-pd-cfg";

  /*** LINKAGE (IMPORTS / INCLUDES) ***/

  import Cisco-IOS-XR-ptp-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR asr9k-ptp-pd package configuration.

     This YANG module augments the
       Cisco-IOS-XR-ptp-cfg
     module with configuration data.

     Copyright (c) 2013-2017 by Cisco Systems, Inc.
     All rights reserved.";

  revision "2017-05-20" {
    description
      "IOS-XR 6.3.1 revision.";
  }

  revision "2015-11-09" {
    description
      "IOS XR 6.0 revision.";
  }


  augment "/a1:ptp/a1:logging" {

    container servo {
      description "PTP PD Servo logging configuration";
      leaf events {
        type empty;
        description "Enable servo events logging";
      }
    }
    description
      "This augment extends the configuration data of
      'Cisco-IOS-XR-ptp-cfg'";
  }
}
