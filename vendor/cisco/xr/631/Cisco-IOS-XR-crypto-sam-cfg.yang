module Cisco-IOS-XR-crypto-sam-cfg {

  /*** NAMESPACE / PREFIX DEFINITION ***/

  namespace "http://cisco.com/ns/yang/Cisco-IOS-XR-crypto-sam-cfg";


  prefix "crypto-sam-cfg";

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR crypto-sam package configuration.

     This module contains definitions
     for the following management objects:
       crypto: Crypto configuration

     Copyright (c) 2013-2017 by Cisco Systems, Inc.
     All rights reserved.";

  revision "2015-01-07" {
    description
      "IOS XR 5.3.1 revision.";
  }

  typedef Crypto-sam-action {
    type enumeration {
      enum proceed {
        value 1;
        description "To respond YES to the SAM prompt";
      }
      enum terminate {
        value 2;
        description "To respond NO to the SAM prompt";
      }
    }
    description "Crypto sam action";
  }

  container crypto {
    description "Crypto configuration";

    container sam {
      description "Software Authentication Manager (SAM) Config";

      container prompt-interval {
        presence "Indicates a prompt-interval node is configured.";
        description "Set prompt interval at reboot time";
        leaf action {
          type Crypto-sam-action;
          mandatory true;
          description
            "Respond to SAM prompt either Proceed/Terminate";
        }
        leaf prompt-time {
          type uint32 {
            range "0..300";
          }
          units "second";
          mandatory true;
          description "Prompt time from 0 - 300 seconds";
        }
      }
    }
  }
}
