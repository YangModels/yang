module Cisco-IOS-XR-asr9k-np-oper {

  /*** NAMESPACE / PREFIX DEFINITION ***/

  namespace "http://cisco.com/ns/yang/Cisco-IOS-XR-asr9k-np-oper";


  prefix "asr9k-np-oper";

  /*** LINKAGE (IMPORTS / INCLUDES) ***/

  import Cisco-IOS-XR-types { prefix "xr"; }

  include Cisco-IOS-XR-asr9k-np-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR asr9k-np package operational data.

     This module contains definitions
     for the following management objects:
       hardware-module-np: Hardware NP Counters

     Copyright (c) 2013-2017 by Cisco Systems, Inc.
     All rights reserved.";

  revision "2015-11-09" {
    description
      "IOS XR 6.0 revision.";
  }

  typedef Np {
    type string {
      pattern "(np0)|(np1)|(np2)|(np3)|(np4)|(np5)|(np6)|(np7)";
    }
    description
      "np0:NP0, np1:NP1, np2:NP2, np3:NP3, np4:NP4, np5
      :NP5, np6:NP6, np7:NP7";
  }

  container hardware-module-np {
    config false;
    description "Hardware NP Counters";

    container nodes {
      description "Table of nodes";

      list node {
        key "node-name";
        description "Number";

        container nps {
          description "List of all NP";

          list np {
            key "np-name";
            description "np0 to np7";

            container chn-load {
              description "prm channel load info";
              uses PRM-NP-CHN-LOAD;
            }

            container tcam-summary {
              description "prm tcam summary info";
              uses TCAM-INFO-SHOW-SUM;
            }

            container counters {
              description "prm counters info";
              uses PRM-NP-COUNTERS;
            }

            container fast-drop {
              description "prm fast drop counters info";
              uses PRM-NP-FAST-DROP;
            }
            leaf np-name {
              type Np;
              description "NP name";
            }
          }
        }
        leaf node-name {
          type xr:Node-id;
          description "node number";
        }
      }
    }
  }
}
