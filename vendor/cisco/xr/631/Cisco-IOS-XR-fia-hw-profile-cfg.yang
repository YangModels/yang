module Cisco-IOS-XR-fia-hw-profile-cfg {

  /*** NAMESPACE / PREFIX DEFINITION ***/

  namespace "http://cisco.com/ns"+
    "/yang/Cisco-IOS-XR-fia-hw-profile-cfg";


  prefix "fia-hw-profile-cfg";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR fia-hw-profile package configuration.

     This module contains definitions
     for the following management objects:
       hw-module-profile-config: none

     Copyright (c) 2013-2017 by Cisco Systems, Inc.
     All rights reserved.";

  revision "2016-06-22" {
    description
      "Schema added.";
  }

  revision "2015-11-09" {
    description
      "IOS XR 6.0 revision.";
  }


  container hw-module-profile-config {
    description "none";

    container profile {
      description "Configure profile.";

      container tcam-table {
        description "Configure profile for TCAM LC cards";

        container fib-table {
          description "FIB table for TCAM LC cards";

          container ipv4-address {
            description "IPv4 table for TCAM LC cards";

            container ipv4-unicast {
              description "Unicast table for TCAM LC cards";

              container ipv4-unicast-prefix-lengths {
                description "IPv4 Unicast prefix ";

                list ipv4-unicast-prefix-length {
                  key "prefix-length";
                  description "IPv4 Unicast prefix length";
                  leaf ipv4-unicast-prefix-percent {
                    type string;
                    units "percentage";
                    description
                      "curve out percentage of TCAM table
                      entries";
                  }
                  leaf prefix-length {
                    type uint32 {
                      range "0..32";
                    }
                    description "prefix length";
                  }
                }
              }
              leaf ipv4-unicast-percent {
                type uint32 {
                  range "0..100";
                }
                units "percentage";
                description
                  "curve out percentage of TCAM table entries";
              }
            }
          }

          container ipv6-address {
            description "IPv6 table for TCAM LC cards";

            container ipv6-unicast {
              description "Unicast table for TCAM LC cards";

              container ipv6-unicast-prefix-lengths {
                description "IPv6 Unicast prefix ";

                list ipv6-unicast-prefix-length {
                  key "prefix-length";
                  description "IPv6 Unicast prefix length";
                  leaf ipv6-unicast-prefix-percent {
                    type string;
                    units "percentage";
                    description
                      "curve out percentage of TCAM table
                      entries";
                  }
                  leaf prefix-length {
                    type uint32 {
                      range "0..128";
                    }
                    description "prefix length";
                  }
                }
              }
              leaf ipv6-unicast-percent {
                type uint32 {
                  range "0..100";
                }
                units "percentage";
                description
                  "curve out percentage of TCAM table entries";
              }
            }
          }
        }
      }

      container stats {
        description "Configure stats";
        leaf counter-profile {
          type int32;
          description
            "Configure stats for qos-enhanced and
            acl-permit";
        }
      }

      container qos {
        description "Configure profile.";

        container hqos-enable-all {
          description "Configure Hqos profile";
          leaf hqos-enable {
            type int32;
            description " Hqos profile value";
          }
        }

        container ingress-model-root-def {
          description "Configure Ingress Model Default";
          leaf ingress-model-leaf-def {
            type int32;
            description "Ingress Model Default";
          }
        }

        container ingress-models {
          description "Configure Ingress Model Root";

          list ingress-model {
            key "node-name";
            description "Configure Ingress Model";
            leaf node-name {
              type xr:Cisco-ios-xr-string;
              description "NodeName";
            }

            list ingress-model-leaf {
              key "location";
              description "Configure Ingress Model Leaf";
              leaf ingress-model-leaf {
                type int32;
                mandatory true;
                description "IngressModelLeaf";
              }
              leaf location {
                type int32;
                description "Location";
              }
            }
          }
        }

        container trunks {
          description "Configure Max Trunk Size";
          leaf trunk-size {
            type int32;
            description "Max Trunk Size";
          }
        }

        container class-maps-root-def {
          description "Configure Class Maps Default";
          leaf class-map-size-def {
            type int32;
            description "Class Map Size Default";
          }
        }

        container class-maps {
          description "Configure Class Map Root";

          list class-map {
            key "node-name";
            description "Configure Class Maps";
            leaf node-name {
              type xr:Cisco-ios-xr-string;
              description "NodeName";
            }

            list class-map-size {
              key "location";
              description "Class Map Size";
              leaf class-map-size {
                type int32;
                mandatory true;
                description "ClassMapSize";
              }
              leaf location {
                type int32;
                description "Location";
              }
            }
          }
        }
      }
    }

    container fib-scale {
      description "Configure Fib for Scale for noTcam LC.";

      container ipv6-unicast-scale-no-tcam {
        description "IPv6 table for NOTCAM LC Scale.";

        container scale-ipv6-no-tcam {
          description "Scale for IPv6 table for NoTCAM LC.";
          leaf internet-optimized-ipv6-no-tcam {
            type string;
            description
              "Internet-optimized Scale for IPv6 table for
              NoTCAM LC.";
          }
        }
      }

      container ipv4-unicast-scale-no-tcam {
        description "IPv4 table for NOTCAM LC Scale.";

        container scale-ipv4-no-tcam {
          description "Scale for IPv4 table for NoTCAM LC.";
          leaf host-optimized-ipv4-no-tcam {
            type string;
            description
              "Host-optimized Scale for IPv4 table for
              NoTCAM LC.";
          }
          leaf internet-optimized-ipv4-no-tcam {
            type string;
            description
              "Internet-optimized Scale for IPv4 table for
              NoTCAM LC.";
          }
        }
      }
    }

    container tcam {
      description "Configure Tcam.";

      container fib-tcam-scale {
        description "Configure Fib iscale for Tcam.";

        container ipv4-unicast-scale {
          description "IPv4 table for TCAM LC Scale.";
          leaf ipv4-scale {
            type empty;
            description "Scale for IPv4 table for TCAM LC.";
          }
        }
      }
    }
  }
}
