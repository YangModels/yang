module Cisco-IOS-XR-ncs1k-mxp-cfg {

  /*** NAMESPACE / PREFIX DEFINITION ***/

  namespace "http://cisco.com/ns/yang/Cisco-IOS-XR-ncs1k-mxp-cfg";


  prefix "ncs1k-mxp-cfg";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ncs1k-mxp package configuration.

     This module contains definitions
     for the following management objects:
       hardware-module: NCS1k HW module config

     Copyright (c) 2013-2017 by Cisco Systems, Inc.
     All rights reserved.";

  revision "2015-11-09" {
    description
      "IOS XR 6.0 revision.";
  }

  typedef Trunk-data-rate {
    type enumeration {
      enum hundred-gig {
        value 2;
        description "HundredGig";
      }
      enum two-hundred-gig {
        value 3;
        description "TwoHundredGig";
      }
      enum two-hundred-fifty-gig {
        value 4;
        description "TwoHundredFiftyGig";
      }
    }
    description "Trunk data rate";
  }
  typedef Client-data-rate {
    type enumeration {
      enum ten-gig {
        value 1;
        description "TenGig";
      }
      enum forty-gig {
        value 2;
        description "FortyGig";
      }
      enum hundred-gig {
        value 3;
        description "HundredGig";
      }
      enum ten-and-hundred-gig {
        value 4;
        description "TenAndHundredGig";
      }
    }
    description "Client data rate";
  }
  typedef Fec {
    type enumeration {
      enum sd7 {
        value 1;
        description "SoftDecision7";
      }
      enum sd20 {
        value 2;
        description "SoftDecision20";
      }
    }
    description "Fec";
  }

  container hardware-module {
    description "NCS1k HW module config";

    list node {
      key "location";
      description "Node";
      leaf location {
        type xr:Cisco-ios-xr-string;
        description "Fully qualified line card specification";
      }

      list slice {
        key "slice-id";
        description "Slice to be Provisioned";

        container values {
          description "Data rates & FEC";
          leaf client-rate {
            type Client-data-rate;
            description "Client Rate";
          }
          leaf trunk-rate {
            type Trunk-data-rate;
            description "TrunkRate";
          }
          leaf fec {
            type Fec;
            description "FEC";
          }
          leaf encrypted {
            type boolean;
            default "false";
            description "Encrypted";
          }
        }
        leaf lldp {
          type boolean;
          description "Drop LLDP Packets";
        }
        leaf slice-id {
          type xr:Cisco-ios-xr-string;
          description "Set Slice";
        }
      }
    }
  }
}
