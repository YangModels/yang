module Cisco-IOS-XR-ncs1k-mxp-oper {

  /*** NAMESPACE / PREFIX DEFINITION ***/

  namespace "http://cisco.com/ns/yang/Cisco-IOS-XR-ncs1k-mxp-oper";


  prefix "ncs1k-mxp-oper";

  /*** LINKAGE (IMPORTS / INCLUDES) ***/

  include Cisco-IOS-XR-ncs1k-mxp-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ncs1k-mxp package operational data.

     This module contains definitions
     for the following management objects:
       hw-module: mxp hw-module command chain

     Copyright (c) 2013-2017 by Cisco Systems, Inc.
     All rights reserved.";

  revision "2015-11-09" {
    description
      "IOS XR 6.0 revision.";
  }


  container hw-module {
    config false;
    description "mxp hw-module command chain";

    container slice-ids {
      description "Slice information";

      list slice-id {
        key "slice-num";
        description "Per slice num data";
        leaf slice-num {
          type int32;
          description
            "Details associated with a particular slice
            number";
        }
        uses MXP-HWMOD-OP;
      }
    }

    container slice-all {
      description "Information for all slices";
      uses MXP-HWMOD-OP;
    }
  }
}
