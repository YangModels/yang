module Cisco-IOS-XR-ip-rib-ipv4-oper {

  /*** NAMESPACE / PREFIX DEFINITION ***/

  namespace "http://cisco.com/ns/yang/Cisco-IOS-XR-ip-rib-ipv4-oper";


  prefix "ip-rib-ipv4-oper";

  /*** LINKAGE (IMPORTS / INCLUDES) ***/

  import ietf-inet-types { prefix "inet"; }

  import Cisco-IOS-XR-types { prefix "xr"; }

  include Cisco-IOS-XR-ip-rib-ipv4-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ip-rib-ipv4 package operational data.

     This module contains definitions
     for the following management objects:
       rib-stdby: RIB standby node operational data
       rib: rib

     Copyright (c) 2013-2017 by Cisco Systems, Inc.
     All rights reserved.";

  revision "2015-11-09" {
    description
      "IOS XR 6.0 revision.";
  }

  typedef Rib-saf-name {
    type string {
      pattern "(Unicast)|(Multicast)";
    }
    description
      "Unicast:   Comment: Ucast string for <safi_name>,
      Multicast: Comment: Mcast string for <safi_name>";
  }
  typedef Rib-af-name {
    type string {
      pattern "(IPv4)|(IPv6)";
    }
    description
      "IPv4: Comment: v4 string for <afi_name>, IPv6:
      Comment: v6 string for <afi_name>";
  }

  grouping VRF-TABLE {
    description "Common node of rib, rib-stdby";

    container vrfs {
      description "VRF table";

      list vrf {
        key "vrf-name";
        description "Specific VRF";

        container afs {
          description "Address Family (AF) table";

          list af {
            key "af-name";
            description "Specific AF information";

            container safs {
              description "Subsequent Address Family (SAF) table";

              list saf {
                key "saf-name";
                description "Specific SAF information";

                container ip-rib-route-table-names {
                  description "Global container of routes";

                  list ip-rib-route-table-name {
                    key "route-table-name";
                    description
                      "IP RIB Route table name for a topology";

                    container routes {
                      description "Route information ";

                      list route {
                        description
                          "Route information of a specific Network
                          Address ";
                        leaf address {
                          type inet:ipv4-address-no-zone;
                          description "Network Address";
                        }
                        leaf prefix-length {
                          type xr:Ipv4-prefix-length;
                          description "Prefix Length";
                        }
                        leaf next-hop-address {
                          type inet:ipv4-address-no-zone;
                          description "NextHop Address";
                        }
                        leaf interface-name {
                          type xr:Interface-name;
                          description "Outgoing Interface";
                        }
                        uses IPV4-RIB-EDM-ROUTE;
                      }
                    }

                    container deleted-routes {
                      description "Deleted";

                      list deleted-route {
                        description
                          "Route information for a specific
                          deleted address ";
                        leaf address {
                          type inet:ipv4-address-no-zone;
                          description "Network Address";
                        }
                        leaf prefix-length {
                          type xr:Ipv4-prefix-length;
                          description "Prefix Length";
                        }
                        uses IPV4-RIB-EDM-ROUTE;
                      }
                    }

                    container destination-kw {
                      description "Destination KW";

                      container dest-best-routes {
                        description "Best Local";

                        list dest-best-route {
                          key "address";
                          description
                            "Best local route information for a
                            specific Address ";
                          leaf address {
                            type inet:ipv4-address-no-zone;
                            description "Network Address";
                          }
                          uses IPV4-RIB-EDM-ROUTE;
                        }
                      }

                      container dest-q-routes {
                        description "Quarantine";

                        list dest-q-route {
                          description
                            "Route information of a specific Backup
                            Address ";
                          leaf address {
                            type inet:ipv4-address-no-zone;
                            description "Network Address";
                          }
                          leaf prefix-length {
                            type xr:Ipv4-prefix-length;
                            description "Prefix Length";
                          }
                          uses IPV4-RIB-EDM-ROUTE;
                        }
                      }

                      container dest-backup-routes {
                        description "Backup";

                        list dest-backup-route {
                          description
                            "Route information of a specific Backup
                            Address ";
                          leaf address {
                            type inet:ipv4-address-no-zone;
                            description "Network Address";
                          }
                          leaf prefix-length {
                            type xr:Ipv4-prefix-length;
                            description "Prefix Length";
                          }
                          uses IPV4-RIB-EDM-ROUTE;
                        }
                      }

                      container dest-next-hop-routes {
                        description "Resolving next hop";

                        list dest-next-hop-route {
                          key "address";
                          description
                            "Nexthop information for a specific
                            address";
                          leaf address {
                            type inet:ipv4-address-no-zone;
                            description "Network Address";
                          }
                          uses IPV4-RIB-EDM-ROUTE;
                        }
                      }
                    }

                    container opaques {
                      description "Opaque information ";

                      list opaque {
                        description "Opaque item ";
                        leaf opaque-clientid {
                          type int32;
                          description "Opaque Client ID";
                        }
                        leaf opaque-protoid {
                          type int32;
                          description "Opaque Proto ID";
                        }
                        leaf opaque-key-type {
                          type int32;
                          description "Opaque key type";
                        }
                        leaf opaque-key-size {
                          type int32;
                          description "Opaque key size";
                        }
                        leaf opaque-data-size {
                          type int32;
                          description "Opaque data size";
                        }
                        leaf opaque-string {
                          type xr:Cisco-ios-xr-string;
                          description "Opaque string";
                        }
                        uses RIB-EDM-OPAQUE-OBJ;
                      }
                    }

                    container protocol {
                      description
                        "Contains the classification of routes by
                        protocol";

                      container mobile {
                        description "Mobile Protocol";
                        uses NON-AS;
                      }

                      container subscriber {
                        description "Subscriber Protocol";
                        uses NON-AS;
                      }

                      container connected {
                        description "Connected Protocol";
                        uses NON-AS;
                      }

                      container dagr {
                        description
                          "DAGR Protocol(Direct-Attached Gateway
                          Redundancy) Protocol";
                        uses NON-AS;
                      }

                      container rip {
                        description "RIP Protocol";
                        uses NON-AS;
                      }

                      container ospf {
                        description "OSPF Protocol";
                        uses AS;
                      }

                      container static {
                        description "Static Protocol";
                        uses NON-AS;
                      }

                      container rpl {
                        description "RPL Protocol";
                        uses AS;
                      }

                      container application {
                        description "Application Protocol";
                        uses NON-AS;
                      }

                      container te-client {
                        description "TEClient Protocol";
                        uses NON-AS;
                      }

                      container eigrp {
                        description "EIGRP Protocol";
                        uses AS;
                      }

                      container local {
                        description "Local Protocol";

                        container smiap {
                          description "SMIAP";
                          uses PROTOCOL-ROUTE-TABLE;
                          uses INFORMATION;
                        }

                        container lspv {
                          description
                            "LSPV(Label Switched Path Verification)
                            Protocol";
                          uses PROTOCOL-ROUTE-TABLE;
                          uses INFORMATION;
                        }
                        uses NON-AS;
                      }

                      container bgp {
                        description "BGP Protocol";
                        uses AS;
                      }

                      container isis {
                        description "ISIS Protocol";
                        uses AS;
                      }
                    }

                    container q-routes {
                      description "Quarantine";

                      list q-route {
                        description
                          "Route information for a specific
                          quarantined address ";
                        leaf address {
                          type inet:ipv4-address-no-zone;
                          description "Network Address";
                        }
                        leaf prefix-length {
                          type xr:Ipv4-prefix-length;
                          description "Prefix Length";
                        }
                        uses IPV4-RIB-EDM-ROUTE;
                      }
                    }

                    container backup-routes {
                      description
                        "Backup route information for the given
                        table";

                      list backup-route {
                        description
                          "Route information for a specific backup
                          address ";
                        leaf address {
                          type inet:ipv4-address-no-zone;
                          description "Network Address";
                        }
                        leaf prefix-length {
                          type xr:Ipv4-prefix-length;
                          description "Prefix Length";
                        }
                        leaf protoid {
                          type int32;
                          description "Proto ID";
                        }
                        uses IPV4-RIB-EDM-ROUTE;
                      }
                    }

                    container adverts {
                      description "Route advertiser information ";

                      list advert {
                        description
                          "Route information of a specific Network
                          Address ";
                        leaf address {
                          type inet:ipv4-address-no-zone;
                          description "Network Address";
                        }
                        leaf prefix-length {
                          type xr:Ipv4-prefix-length;
                          description "Prefix Length";
                        }
                        uses IPV4-RIB-EDM-ADVERT;
                      }
                    }
                    leaf route-table-name {
                      type xr:Cisco-ios-xr-string;
                      description "Name of the route table";
                    }
                  }
                }
                leaf saf-name {
                  type Rib-saf-name;
                  description "Name of the SAF";
                }
              }
            }
            leaf af-name {
              type Rib-af-name;
              description "Name of the AF";
            }
          }
        }
        leaf vrf-name {
          type xr:Cisco-ios-xr-string;
          description "Name of the VRF";
        }
      }
    }
  }

  grouping AS {
    description "Common node of bgp, ospf, isis, eigrp, rpl";

    list as {
      key "as";
      description "Autonomous System of protocol";
      leaf as {
        type xr:Cisco-ios-xr-string;
        description "Autonomous system";
      }
      uses PROTOCOL-ROUTE-TABLE;
      uses INFORMATION;
    }
  }

  grouping INFORMATION {
    description "Common node of as, non-as, smiap, lspv";

    container information {
      description "Protocol related Information";
      uses IPV4-RIB-EDM-PROTO;
    }
  }

  grouping RIB-TABLE {
    description "Common node of rib, rib-stdby";

    container rib-table-ids {
      description "RIB table";

      list rib-table-id {
        key "tableid";
        description "Specific Table";

        container summary-protos {
          description "RIB table summary";

          list summary-proto {
            key "protoid";
            description
              "Route summary information for a specific
              table/protocol ";
            leaf protoid {
              type int32;
              description "Proto ID";
            }
            uses RIB-EDM-PROTO-ROUTE-SUMM-DETAIL;
          }
        }

        container rib-table-itf-hndls {
          description "RIB table interface";

          list rib-table-itf-hndl {
            key "handle";
            description "Interface handle";
            leaf handle {
              type int32;
              description "Itf Handle";
            }

            list itf-route {
              key "address";
              description
                "Route information for a specific
                table/interface ";
              leaf address {
                type inet:ipv4-address-no-zone;
                description "Network Address";
              }
              uses IPV4-RIB-EDM-ROUTE;
            }
          }
        }

        container information {
          description "Table related Information";
          uses IPV4-RIB-EDM-TABLE;
        }
        leaf tableid {
          type xr:Hex-integer;
          description "Table ID";
        }
      }
    }
  }

  grouping NON-AS {
    description
      "Common node of local, connected, rip, static,
      subscriber, mobile, dagr, application, te-client";

    container non-as {
      description "Non Autonomous System of protocol";
      uses PROTOCOL-ROUTE-TABLE;
      uses INFORMATION;
    }
  }

  grouping PROTOCOL-ROUTE-TABLE {
    description "Common node of as, non-as, smiap, lspv";

    container protocol-routes {
      description "Protocol specific Route";

      list protocol-route {
        description
          " Route information of a specific Network
          Address ";
        leaf address {
          type inet:ipv4-address-no-zone;
          description "Network Address";
        }
        leaf prefix-length {
          type xr:Ipv4-prefix-length;
          description "Prefix Length";
        }
        uses IPV4-RIB-EDM-ROUTE;
      }
    }
  }

  container rib-stdby {
    config false;
    description "RIB standby node operational data";
    uses VRF-TABLE;
    uses RIB-TABLE;
  }

  container rib {
    config false;
    description "rib";
    uses VRF-TABLE;
    uses RIB-TABLE;
  }
}
