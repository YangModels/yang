module Cisco-IOS-XR-ptp-pd-oper {

  /*** NAMESPACE / PREFIX DEFINITION ***/

  namespace "http://cisco.com/ns/yang/Cisco-IOS-XR-ptp-pd-oper";


  prefix "ptp-pd-oper";

  /*** LINKAGE (IMPORTS / INCLUDES) ***/

  import Cisco-IOS-XR-ptp-oper { prefix "a1"; }

  include Cisco-IOS-XR-ptp-pd-oper-sub1 {
    revision-date 2016-06-08;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ptp-pd package operational data.

     This YANG module augments the
       Cisco-IOS-XR-ptp-oper
     module with state data.

     Copyright (c) 2013-2017 by Cisco Systems, Inc.
     All rights reserved.";

  revision "2016-06-08" {
    description
      "Schema added.";
  }

  revision "2015-11-09" {
    description
      "IOS XR 6.0 revision.";
  }


  augment "/a1:ptp" {

    container platform {
      description "PTP platform specific data";

      container servo {
        description "PTP servo related parameters";
        uses PTP-PD-SERVO-INFO;
      }
    }
    description
      "This augment extends the operational data of
      'Cisco-IOS-XR-ptp-oper'";
  }
}
