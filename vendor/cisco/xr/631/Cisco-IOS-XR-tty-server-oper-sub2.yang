submodule Cisco-IOS-XR-tty-server-oper-sub2 {

  belongs-to Cisco-IOS-XR-tty-server-oper {
    prefix Cisco-IOS-XR-tty-server-oper;
  }

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR tty-server package operational data.

     Copyright (c) 2013-2017 by Cisco Systems, Inc.
     All rights reserved.";

  revision "2015-07-30" {
    description
      "Descriptions updated.";
  }

  revision "2015-01-07" {
    description
      "IOS XR 5.3.1 revision.";
  }


  grouping TTY-AAA-STATS {
    description "AAA statistics";
    leaf user-name {
      type string;
      description "The authenticated username";
    }
  }
}
