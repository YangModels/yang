submodule Cisco-IOS-XR-icpe-sdacp-oper-sub1 {

  belongs-to Cisco-IOS-XR-icpe-sdacp-oper {
    prefix Cisco-IOS-XR-icpe-sdacp-oper;
  }

  /*** LINKAGE (IMPORTS / INCLUDES) ***/

  import ietf-inet-types { prefix "inet"; }

  include Cisco-IOS-XR-icpe-sdacp-oper-sub2 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR icpe-sdacp package operational data.

     Copyright (c) 2013-2017 by Cisco Systems, Inc.
     All rights reserved.";

  revision "2015-11-09" {
    description
      "IOS XR 6.0 revision.";
  }

  typedef Icpe-cpm-chan-fsm-state {
    type enumeration {
      enum icpe-cpm-chan-fsm-state-down {
        description "Down";
      }
      enum icpe-cpm-chan-fsm-state-not-supported {
        description "Not supported";
      }
      enum icpe-cpm-chan-fsm-state-closed {
        description "Closed";
      }
      enum icpe-cpm-chan-fsm-state-opening {
        description "Opening";
      }
      enum icpe-cpm-chan-fsm-state-opened {
        description "Opened";
      }
      enum icpe-cpm-chan-fsm-state-open {
        description "Open";
      }
    }
    description "Icpe cpm chan fsm state";
  }
  typedef Icpe-cpm-channel-resync-state {
    type enumeration {
      enum icpe-cpm-channel-resync-state-unknown {
        description "Unknown";
      }
      enum icpe-cpm-channel-resync-state-not-in-resync {
        description "Not in resync";
      }
      enum icpe-cpm-channel-resync-state-in-client-resync {
        description "In client resync";
      }
      enum icpe-cpm-channel-resync-state-in-satellite-resync {
        description "In satellite resync";
      }
    }
    description "Icpe cpm channel resync state";
  }
  typedef Icpe-cpm-control-fsm-state {
    type enumeration {
      enum icpe-cpm-control-fsm-state-disconnected {
        description "Disconnected";
      }
      enum icpe-cpm-control-fsm-state-connecting {
        description "Connecting";
      }
      enum icpe-cpm-control-fsm-state-authenticating {
        description "Authenticating";
      }
      enum icpe-cpm-control-fsm-state-check-ing-ver {
        description "Checking Version";
      }
      enum icpe-cpm-control-fsm-state-connected {
        description "Connected";
      }
      enum icpe-cpm-control-fsm-state-issu {
        description "ISSU In Progress";
      }
    }
    description "Icpe cpm control fsm state";
  }

  grouping ICPE-CPM-OPER-CHAN-TYPE {
    description "ICPE CPM OPER CHAN TYPE";

    container capabilities {
      description "Capabilities";
      uses ICPE-YANG-CAPABILITIES-TYPE;
    }

    container resync-state-timestamp {
      description "Timestamp";
      uses ICPE-TIMESTAMP-TYPE;
    }

    container channel-state-timestamp {
      description "Timestamp";
      uses ICPE-TIMESTAMP-TYPE;
    }
    leaf channel-id {
      type uint16;
      description "Channel ID";
    }
    leaf resync-state {
      type Icpe-cpm-channel-resync-state;
      description "Resync state";
    }
    leaf channel-state {
      type Icpe-cpm-chan-fsm-state;
      description "Channel state";
    }
    leaf control-messages-sent {
      type uint64;
      description "Control messages sent";
    }
    leaf normal-messages-sent {
      type uint64;
      description "Normal messages sent";
    }
    leaf control-messages-received {
      type uint64;
      description "Control messages received";
    }
    leaf normal-messages-received {
      type uint64;
      description "Normal messages received";
    }
    leaf control-messages-dropped {
      type uint64;
      description "Control messages dropped";
    }
    leaf normal-messages-dropped {
      type uint64;
      description "Normal messages dropped";
    }
    leaf secs-since-last-cleared {
      type uint64;
      units "second";
      description "Secs since last cleared";
    }
    leaf version {
      type uint16;
      description "Version";
    }
  }

  grouping ICPE-CPM-TIMESTAMP-TYPE {
    description "ICPE CPM TIMESTAMP TYPE";
    leaf seconds {
      type uint32;
      units "second";
      description "Seconds";
    }
    leaf nanoseconds {
      type uint32;
      units "nanosecond";
      description "Nanoseconds";
    }
  }

  grouping ICPE-TIMESTAMP-TYPE {
    description "ICPE TIMESTAMP TYPE";
    leaf seconds {
      type uint32;
      units "second";
      description "Seconds";
    }
    leaf nanoseconds {
      type uint32;
      units "nanosecond";
      description "Nanoseconds";
    }
  }

  grouping ICPE-CPM-OPER-SAT {
    description "SDAC Protocol Discovery information";

    container protocol-state-timestamp {
      description "Timestamp";
      uses ICPE-TIMESTAMP-TYPE;
    }

    container transport-error-timestamp {
      description "Timestamp";
      uses ICPE-CPM-TIMESTAMP-TYPE;
    }
    leaf satellite-id-xr {
      type uint16;
      description "Satellite ID";
    }
    leaf satellite-ip-address {
      type inet:ipv4-address;
      description "Satellite IP address";
    }
    leaf ip-address-auto {
      type boolean;
      description "IP address auto";
    }
    leaf vrf-name {
      type Xr-yang-string;
      description "VRF name";
    }
    leaf control-protocol-state {
      type Icpe-cpm-control-fsm-state;
      description "Control protocol state";
    }
    leaf transport-error {
      type uint32;
      description "Transport error";
    }

    list channel {
      description "Channels on satellite table";
      uses ICPE-CPM-OPER-CHAN-TYPE;
    }
  }
}
