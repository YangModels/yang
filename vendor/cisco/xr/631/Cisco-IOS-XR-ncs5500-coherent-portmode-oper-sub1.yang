submodule Cisco-IOS-XR-ncs5500-coherent-portmode-oper-sub1 {

  belongs-to Cisco-IOS-XR-ncs5500-coherent-portmode-oper {
    prefix Cisco-IOS-XR-ncs5500-coherent-portmode-oper;
  }

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ncs5500-coherent-portmode package operational data.

     Copyright (c) 2013-2017 by Cisco Systems, Inc.
     All rights reserved.";

  revision "2015-11-09" {
    description
      "IOS XR 6.0 revision.";
  }


  grouping PORTMODE-INFO {
    description "portmode entry of optics controller";
    leaf intf-name {
      type string {
        length "0..128";
      }
      description "intf name";
    }
    leaf speed {
      type string {
        length "0..128";
      }
      description "speed";
    }
    leaf fec {
      type string {
        length "0..128";
      }
      description "fec";
    }
    leaf diff {
      type string {
        length "0..128";
      }
      description "diff";
    }
    leaf modulation {
      type string {
        length "0..128";
      }
      description "modulation";
    }
  }
}
