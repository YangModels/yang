submodule Cisco-IOS-XR-ncs1k-mxp-lldp-oper-sub1 {

  belongs-to Cisco-IOS-XR-ncs1k-mxp-lldp-oper {
    prefix Cisco-IOS-XR-ncs1k-mxp-lldp-oper;
  }

  /*** LINKAGE (IMPORTS / INCLUDES) ***/

  import ietf-inet-types { prefix "inet"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ncs1k-mxp-lldp package operational data.

     Copyright (c) 2013-2017 by Cisco Systems, Inc.
     All rights reserved.";

  revision "2016-10-13" {
    description
      "Added Additional bag for show lldp neighbor command.";
  }

  revision "2015-11-09" {
    description
      "IOS XR 6.0 revision.";
  }

  typedef In6-addr {
    type inet:ipv6-address;
    description "In6 addr";
  }
  typedef Lldp-l3-addr-protocol {
    type enumeration {
      enum ipv4 {
        description "IPv4";
      }
      enum ipv6 {
        description "IPv6";
      }
    }
    description "Lldp l3 addr protocol";
  }

  grouping LLDP-L3-ADDR {
    description "LLDP L3 ADDR";
    leaf address-type {
      type Lldp-l3-addr-protocol;
      description "AddressType";
    }
    leaf ipv4-address {
      when "../address-type = 'ipv4'" {
        description "../AddressType = 'IPv4'";
      }
      type inet:ipv4-address;
      description "IPv4 address";
    }
    leaf ipv6-address {
      when "../address-type = 'ipv6'" {
        description "../AddressType = 'IPv6'";
      }
      type In6-addr;
      description "IPv6 address";
    }
  }

  grouping LLDP-ADDRESS-ENTRY {
    description "LLDP Address entry";

    list lldp-addr-entry {
      description "lldp addr entry";

      container address {
        description "Network layer address";
        uses LLDP-L3-ADDR;
      }
      leaf ma-subtype {
        type uint8;
        description "MA sub type";
      }
      leaf if-num {
        type uint32;
        description "Interface num";
      }
    }
  }

  grouping MXP-LLDP-NEIGHBOR {
    description "LLDP neighbor info";

    container network-addresses {
      description "Management Addresses";
      uses LLDP-ADDRESS-ENTRY;
    }
    leaf source-mac {
      type string;
      description "Mac address of the neighbor";
    }
    leaf chassis-id {
      type string;
      description "Chassis id";
    }
    leaf port-id-detail {
      type string;
      description "Outgoing port identifier";
    }
    leaf hold-time {
      type uint16;
      description "Remaining hold time";
    }
    leaf port-description {
      type string;
      description "Port Description";
    }
    leaf system-name {
      type string;
      description "System Name";
    }
    leaf system-description {
      type string;
      description "System Description";
    }
    leaf system-capabilities {
      type string;
      description "System Capabilities";
    }
    leaf enabled-capabilities {
      type string;
      description "Enabled Capabilities";
    }
    leaf lldp-neighbor {
      type string {
        length "0..40";
      }
      description "LldpNeighbor";
    }
    leaf drop-enabled {
      type boolean;
      description "LLDP Packet Drop Enabled";
    }
    leaf rx-lldp-pkts {
      type uint64;
      description "Received LLDP Packets count";
    }
  }

  grouping LLDP-NEIGHBOR-BRIEF-ENTRY {
    description "LLDP NEIGHBOR BRIEF ENTRY";

    list lldp-neighbor-brief-entry {
      description "lldp neighbor brief entry";
      leaf chassis-id {
        type string;
        description "Chassis id";
      }
      leaf port-id-detail {
        type string;
        description "Outgoing port identifier";
      }
      leaf system-name {
        type string;
        description "System Name";
      }
      leaf enabled-capabilities {
        type string;
        description "Enabled Capabilities";
      }
      leaf recv-intf {
        type string;
        description "Receive Interface";
      }
      leaf hold-time {
        type uint16;
        description "Remaining hold time";
      }
    }
  }

  grouping LLDP-NEIGHB-BRIEF {
    description "LLDP Neighbor Breif entries";

    container neighbours {
      description "List of LLDP neighbors";
      uses LLDP-NEIGHBOR-BRIEF-ENTRY;
    }
    leaf number-of-entries {
      type uint16;
      description "Number of active neighbors entries";
    }
  }
}
