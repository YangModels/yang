module Cisco-IOS-XR-group-cfg {

  namespace "http://cisco.com/ns/yang/Cisco-IOS-XR-group-cfg";
  prefix "group-cfg";

  import Cisco-IOS-XR-types { 
    prefix "xr"; 
  } 

  organization "Cisco Systems, Inc.";

  contact 
    "Cisco Systems, Inc.
     Customer Service

     Postal: 170 W Tasman Drive
     San Jose, CA 95134

     Tel: +1 1800 553-NETS

     E-mail: cs-yang@cisco.com";


  description       
    "This module contains IOS-XR group YANG data 
     for flexible cli groups 
    
     Copyright (c) 2013-2016 by Cisco Systems, Inc.
     All rights reserved.";

  revision "2016-04-29" {
    description
      "Initial revision.";
  }

  container groups {
    description "config groups";

    list group {
      key "group-name";
      description "Group config definition";
      leaf group-name {
        type xr:Cisco-ios-xr-string {
          length "0..32";
        }
        description "Group name";
      }
    }
  }

  container apply-groups {
    description "apply groups";
    leaf apply-group {
        type xr:Cisco-ios-xr-string;
        description "apply-group name";
      }
  }

}
