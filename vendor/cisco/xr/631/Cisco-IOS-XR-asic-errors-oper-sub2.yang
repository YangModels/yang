submodule Cisco-IOS-XR-asic-errors-oper-sub2 {

  belongs-to Cisco-IOS-XR-asic-errors-oper {
    prefix Cisco-IOS-XR-asic-errors-oper;
  }

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR asic-errors package operational data.

     Copyright (c) 2013-2017 by Cisco Systems, Inc.
     All rights reserved.";

  revision "2015-11-09" {
    description
      "IOS XR 6.0 revision.";
  }


  grouping SUMMARY-DATA-BG {
    description "SUMMARY DATA BG";
    leaf num-nodes {
      type uint32;
      description "num nodes";
    }
    leaf crc-err-count {
      type uint32;
      description "crc err count";
    }
    leaf sbe-err-count {
      type uint32;
      description "sbe err count";
    }
    leaf mbe-err-count {
      type uint32;
      description "mbe err count";
    }
    leaf par-err-count {
      type uint32;
      description "par err count";
    }
    leaf gen-err-count {
      type uint32;
      description "gen err count";
    }
    leaf reset-err-count {
      type uint32;
      description "reset err count";
    }
    leaf-list err-count {
      type uint32;
      description "err count";
    }
    leaf-list pcie-err-count {
      type uint32;
      description "pcie err count";
    }
    leaf-list node-key {
      type uint32;
      description "node key";
    }
  }

  grouping ASIC-SUMMARY-BG {
    description "ASIC SUMMARY BG";
    leaf legacy-client {
      type boolean;
      description "legacy client";
    }
    leaf cih-client {
      type boolean;
      description "cih client";
    }

    list sum-data {
      description "sum data";
      uses SUMMARY-DATA-BG;
    }
  }
}
