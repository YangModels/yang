submodule Cisco-IOS-XR-infra-xtc-oper-sub1 {

  belongs-to Cisco-IOS-XR-infra-xtc-oper {
    prefix Cisco-IOS-XR-infra-xtc-oper;
  }

  /*** LINKAGE (IMPORTS / INCLUDES) ***/

  import ietf-inet-types { prefix "inet"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR infra-xtc package operational data.

     Copyright (c) 2013-2017 by Cisco Systems, Inc.
     All rights reserved.";

  revision "2017-06-26" {
    description
      "Change identifiers to be more readable.";
  }

  revision "2017-05-01" {
    description
      "Fixing backward compatibility error in module.";
  }

  revision "2016-05-31" {
    description
      "Revision description string.";
  }

  revision "2015-11-09" {
    description
      "IOS XR 6.0 revision.";
  }

  typedef Pce-cspf-rc {
    type enumeration {
      enum pce-cspf-not-set {
        description "Not set";
      }
      enum pce-cspf-src-not-found {
        description "Source not found";
      }
      enum pce-cspf-dst-not-found {
        description "Destination not found";
      }
      enum pce-cspf-second-src-not-found {
        description "Second source not found";
      }
      enum pce-cspf-second-dst-not-found {
        description "Second destination not found";
      }
      enum pce-cspf-no-mem {
        description "No memory";
      }
      enum pce-cspf-ex-path-not-resolved {
        description "Second path not resolved";
      }
      enum pce-cspf-no-path {
        description "No path";
      }
      enum pce-cspf-sp-success {
        description "Shortest path success";
      }
      enum pce-cspf-error {
        description "Error";
      }
      enum pce-cspf-fallback-srlg-node-node {
        description "Fallback from SRLG-NODE to NODE";
      }
      enum pce-cspf-fallback-srlg-node-link {
        description "Fallback from SRLG-NODE to LINK";
      }
      enum pce-cspf-fallback-srlg-node-sp {
        description "Fallback from SRLG-NODE to SP";
      }
      enum pce-cspf-fallback-node-link {
        description "Fallback from NODE to LINK";
      }
      enum pce-cspf-fallback-link-sp {
        description "Fallback from LINK to SP";
      }
      enum pce-cspf-fallback-node-sp {
        description "Fallback from NODE to SP";
      }
      enum pce-cspf-fallback-srlg-link {
        description "Fallback from SRLG to LINK";
      }
      enum pce-cspf-fallback-srlg-sp {
        description "Fallback from SRLG to SP";
      }
      enum pce-cspf-dp-success {
        description "Disjoint path success";
      }
    }
    description "PCE CSPF Result Code";
  }
  typedef Pce-headend-swap {
    type enumeration {
      enum pcehs-none {
        description "Headends not swapped";
      }
      enum pcehs-plain {
        description "Headends swapped";
      }
      enum pcehs-rwi {
        description "Headends swapped with increment";
      }
    }
    description "PCE Headends Swap Code";
  }
  typedef Pce-ipv6-address {
    type inet:ipv6-address;
    description "Pce ipv6 address";
  }
  typedef Pce-af-id {
    type enumeration {
      enum none {
        value 0;
        description "None";
      }
      enum ipv4 {
        value 1;
        description "IPv4";
      }
      enum ipv6 {
        value 2;
        description "IPv6";
      }
    }
    description "Pce af id";
  }
  typedef Sid {
    type enumeration {
      enum sr-protected-adj-sid {
        value 1;
        description "Protected Adjacency SID";
      }
      enum sr-unprotected-adj-sid {
        value 2;
        description "Unprotected Adjacency SID";
      }
      enum sr-bgp-egress-peer-engineering-sid {
        value 3;
        description "BGP egress peer engineering SID";
      }
      enum sr-reqular-prefix-sid {
        value 4;
        description "Regular prefix SID";
      }
      enum sr-strict-prefix-sid {
        value 5;
        description "Strict prefix SID";
      }
    }
    description "SID Types";
  }
  typedef Pce-ipv4-address {
    type inet:ipv4-address;
    description "Pce ipv4 address";
  }
  typedef Pce-igp-info-id {
    type enumeration {
      enum isis {
        value 1;
        description "ISIS";
      }
      enum ospf {
        value 2;
        description "OSPF";
      }
      enum bgp {
        value 3;
        description "BGP";
      }
    }
    description "IGP IDs";
  }
  typedef Pcep-state {
    type enumeration {
      enum tcp-close {
        description "TCP close";
      }
      enum tcp-listen {
        description "TCP listen";
      }
      enum tcp-connect {
        description "TCP connect";
      }
      enum pcep-closed {
        description "PCEP closed";
      }
      enum pcep-opening {
        description "PCEP opening";
      }
      enum pcep-open {
        description "PCEP open";
      }
    }
    description "PCEP State";
  }
  typedef Pce-proto {
    type enumeration {
      enum pcep {
        description "PCE protocol";
      }
      enum netconf {
        description "Netconf protocol";
      }
    }
    description "PCE peer protocol";
  }
  typedef Pce-rro {
    type enumeration {
      enum rro-type-ipv4-address {
        description "IPv4 Address";
      }
      enum rro-type-mpls-label {
        description "MPLS Label";
      }
      enum rro-type-sripv4-node-sid {
        description "Segment Routing IPv4 Node SID";
      }
      enum rro-type-sripv4-adjacency-sid {
        description "Segment Routing IPv4 Adjacency SID";
      }
      enum rro-type-sr-nai-null {
        description "Segment Routing with NAI null";
      }
    }
    description "PCE RRO type";
  }
  typedef Pce-sr-sid {
    type enumeration {
      enum ipv4-node-sid {
        description "IPv4 Node SID";
      }
      enum ipv4-adjacency-sid {
        description "IPv4 Adjacency SID";
      }
      enum unknown-sid {
        description "Unknown SID";
      }
    }
    description "PCE SR SID type";
  }
  typedef Lsp-state {
    type enumeration {
      enum lsp-down {
        description "LSP is down";
      }
      enum lsp-up {
        description "LSP is up";
      }
    }
    description "LSP setup type";
  }
  typedef Pcep-lsp-state {
    type enumeration {
      enum lsp-down {
        description "LSP is down";
      }
      enum lsp-up {
        description "LSP is up";
      }
      enum lsp-active {
        description "LSP is active (carrying traffic)";
      }
      enum lsp-going-down {
        description "LSP is going down";
      }
      enum lsp-being-signaled {
        description "LSP is being signaled";
      }
    }
    description "PCEP operation protocol";
  }
  typedef Lsp-setup {
    type enumeration {
      enum setup-rsvp {
        description "LSP is established using RSVP-TE";
      }
      enum setup-sr {
        description "LSP is established using SR-TE";
      }
      enum setup-unknown {
        description "Unknown LSP establishment method";
      }
    }
    description "LSP setup type";
  }

  grouping PCE-ADDR-BAG {
    description "PCE Address Information";
    leaf address-family {
      type uint8;
      description "Address Family";
    }
    leaf ipv4-prefix {
      type inet:ipv4-address;
      description "IPv4 prefix";
    }
    leaf ipv6-prefix {
      type inet:ipv6-address;
      description "IPv6 prefix";
    }
  }

  grouping PCE-PATH-BAG {
    description "PCE path information";

    container source {
      description "Source of path";
      uses PCE-IP-ADDR-TYPE;
    }

    container destination {
      description "Destination of path";
      uses PCE-IP-ADDR-TYPE;
    }
    leaf cost {
      type uint64;
      description "Cost";
    }

    list hops {
      description "Hop addresses";
      uses PCE-ADDR-BAG;
    }
  }

  grouping PCE-PATH-LIST-BAG {
    description "PCE path list";
    leaf headends-swapped {
      type Pce-headend-swap;
      description "Headends swapped";
    }
    leaf cspf-result {
      type Pce-cspf-rc;
      description "CSPF Result";
    }

    list output-path {
      description "Output PCE paths";
      uses PCE-PATH-BAG;
    }
  }

  grouping PCE-ASSO-LSP-INFO {
    description "Association LSP common information";
    leaf pcc-address {
      type inet:ipv4-address;
      description "PCC address";
    }
    leaf tunnel-id {
      type uint32;
      description "Tunnel ID";
    }
    leaf lspid {
      type uint32;
      description "LSP ID";
    }
    leaf tunnel-name {
      type string;
      description "Tunnel Name";
    }
    leaf pce-based {
      type boolean;
      description "PCE Based";
    }
    leaf plsp-id {
      type uint32;
      description "PLSP ID";
    }
  }

  grouping PCE-ASSO-BAG {
    description "PCE Association information";
    leaf association-type {
      type uint32;
      description "Association Type";
    }
    leaf association-id {
      type uint32;
      description "Association ID";
    }
    leaf association-source {
      type inet:ipv4-address;
      description "Association Source";
    }
    leaf strict {
      type boolean;
      description "Association Strict Mode";
    }
    leaf status {
      type uint32;
      description "Association Status";
    }
    leaf headends-swapped {
      type uint32;
      description "Headends Swapped";
    }

    list association-lsp {
      description "Association LSP Info";
      uses PCE-ASSO-LSP-INFO;
    }
  }

  grouping PCE-PFX-BAG {
    description "PCE Prefix Information";

    container node-protocol-identifier {
      description "Node protocol identifier";
      uses PCE-NODE-PID-BAG;
    }
    leaf node-identifier-xr {
      type uint32;
      description "Node identifier";
    }

    list address {
      description "Prefix address";
      uses PCE-IP-ADDR-TYPE;
    }
  }

  grouping PCE-IPV6-LINK-BAG {
    description "PCE IPv6 Link Information";

    container local-igp-information {
      description "Local node IGP information";
      uses PCE-IGP-INFO-BAG;
    }

    container remote-node-protocol-identifier {
      description "Remote node protocol identifier";
      uses PCE-NODE-PID-BAG;
    }
    leaf local-ipv6-address {
      type inet:ipv6-address;
      description "Local IPv6 address";
    }
    leaf remote-ipv6-address {
      type inet:ipv6-address;
      description "Remote IPv6 address";
    }
    leaf igp-metric {
      type uint32;
      description "IGP Metric";
    }
    leaf te-metric {
      type uint32;
      description "TE Metric";
    }
    leaf maximum-link-bandwidth {
      type uint64;
      description "Max link bandwidth";
    }
    leaf max-reservable-bandwidth {
      type uint64;
      description "Max Reservable bandwidth";
    }

    list adjacency-sid {
      description "Adjacency SIDs";
      uses PCE-SID-BAG;
    }
  }

  grouping PCE-IPV4-LINK-BAG {
    description "PCE IPv4 Link Information";

    container local-igp-information {
      description "Local node IGP information";
      uses PCE-IGP-INFO-BAG;
    }

    container remote-node-protocol-identifier {
      description "Remote node protocol identifier";
      uses PCE-NODE-PID-BAG;
    }
    leaf local-ipv4-address {
      type inet:ipv4-address;
      description "Local IPv4 address";
    }
    leaf remote-ipv4-address {
      type inet:ipv4-address;
      description "Remote IPv4 address";
    }
    leaf igp-metric {
      type uint32;
      description "IGP Metric";
    }
    leaf te-metric {
      type uint32;
      description "TE Metric";
    }
    leaf maximum-link-bandwidth {
      type uint64;
      description "Max link bandwidth";
    }
    leaf max-reservable-bandwidth {
      type uint64;
      description "Max Reservable bandwidth";
    }
    leaf-list srlgs {
      type uint32;
      description "SRLG Values";
    }

    list adjacency-sid {
      description "Adjacency SIDs";
      uses PCE-SID-BAG;
    }
  }

  grouping PCE-IP-ADDR-TYPE {
    description "PCE IP ADDR TYPE";
    leaf af-name {
      type Pce-af-id;
      description "AFName";
    }
    leaf ipv4 {
      when "../af-name = 'ipv4'" {
        description "../AFName = 'IPv4'";
      }
      type Pce-ipv4-address;
      description "IPv4 address type";
    }
    leaf ipv6 {
      when "../af-name = 'ipv6'" {
        description "../AFName = 'IPv6'";
      }
      type Pce-ipv6-address;
      description "IPv6 address type";
    }
  }

  grouping PCE-SID-BAG {
    description "PCE SID bags";

    container sid-prefix {
      description "Prefix";
      uses PCE-IP-ADDR-TYPE;
    }
    leaf sid-type {
      type Sid;
      description "SID Type";
    }
    leaf mpls-label {
      type uint32;
      description "MPLS Label";
    }
    leaf domain-identifier {
      type uint64;
      description "Domain identifier";
    }
    leaf rflag {
      type boolean;
      description "R Flag";
    }
    leaf nflag {
      type boolean;
      description "N Flag";
    }
    leaf pflag {
      type boolean;
      description "P Flag";
    }
    leaf eflag {
      type boolean;
      description "E Flag";
    }
    leaf vflag {
      type boolean;
      description "V Flag";
    }
    leaf lflag {
      type boolean;
      description "L Flag";
    }
  }

  grouping PCE-SRGB-INFO-BAG {
    description "PCE SRGB information bag";

    container igp-srgb {
      description "IGP-specific information";
      uses PCE-IGP-INFO-TYPE;
    }
    leaf start {
      type uint32;
      description "SRGB start";
    }
    leaf size {
      type uint32;
      description "SRGB size";
    }
  }

  grouping PCE-IGP-INFO-BGP {
    description "PCE BGP Information";
    leaf router-id {
      type Pce-ipv4-address;
      description "BGP router ID";
    }
    leaf confed-asn {
      type uint32;
      description "Confederation ASN";
    }
  }

  grouping PCE-IGP-INFO-OSPF {
    description "PCE OSPF Information";
    leaf router-id {
      type Pce-ipv4-address;
      description "OSPF router ID";
    }
    leaf area {
      type uint32;
      description "OSPF area";
    }
  }

  grouping PCE-IGP-INFO-ISIS {
    description "PCE ISIS Information";
    leaf system-id {
      type string;
      description "ISIS system ID";
    }
    leaf level {
      type uint32;
      description "ISIS level";
    }
  }

  grouping PCE-IGP-INFO-TYPE {
    description "PCE IGP INFO TYPE";

    container isis {
      when "../igp-id = 'isis'" {
        description "../IGP_ID = 'ISIS'";
      }
      description "ISIS information";
      uses PCE-IGP-INFO-ISIS;
    }

    container ospf {
      when "../igp-id = 'ospf'" {
        description "../IGP_ID = 'OSPF'";
      }
      description "OSPF information";
      uses PCE-IGP-INFO-OSPF;
    }

    container bgp {
      when "../igp-id = 'bgp'" {
        description "../IGP_ID = 'BGP'";
      }
      description "BGP information";
      uses PCE-IGP-INFO-BGP;
    }
    leaf igp-id {
      type Pce-igp-info-id;
      description "IGP ID";
    }
  }

  grouping PCE-IGP-INFO-BAG {
    description "PCE IGP information bag";

    container igp {
      description "IGP-specific information";
      uses PCE-IGP-INFO-TYPE;
    }
    leaf domain-identifier {
      type uint64;
      description "Domain identifier";
    }
    leaf autonomous-system-number {
      type uint32;
      description "Autonomous System Number";
    }
  }

  grouping PCE-NODE-PID-BAG {
    description "PCE Node Protocol Identifier Information";
    leaf node-name {
      type string;
      description "Node Name";
    }
    leaf ipv4-bgp-router-id-set {
      type boolean;
      description "True if IPv4 BGP router ID is set";
    }
    leaf ipv4-bgp-router-id {
      type inet:ipv4-address;
      description "IPv4 TE router ID";
    }
    leaf ipv4te-router-id-set {
      type boolean;
      description "True if IPv4 TE router ID is set";
    }
    leaf ipv4te-router-id {
      type inet:ipv4-address;
      description "IPv4 BGP router ID";
    }

    list igp-information {
      description "IGP information";
      uses PCE-IGP-INFO-BAG;
    }

    list srgb-information {
      description "SRGB information";
      uses PCE-SRGB-INFO-BAG;
    }
  }

  grouping PCE-XTC-NODE-BAG {
    description "PCE XTC Node Information";

    container node-protocol-identifier {
      description "Node protocol identifier";
      uses PCE-NODE-PID-BAG;
    }
    leaf node-identifier-xr {
      type uint32;
      description "Node identifier";
    }
    leaf overload {
      type boolean;
      description "Node Overload Bit";
    }

    list prefix-sid {
      description "Prefix SIDs";
      uses PCE-SID-BAG;
    }

    list ipv4-link {
      description "IPv4 Link information";
      uses PCE-IPV4-LINK-BAG;
    }

    list ipv6-link {
      description "IPv6 Link information";
      uses PCE-IPV6-LINK-BAG;
    }
  }

  grouping PCE-TOPO-STATS-BAG {
    description "Statistics on topology update";
    leaf num-nodes-added {
      type uint32;
      description "Number of nodes added";
    }
    leaf num-nodes-deleted {
      type uint32;
      description "Number of nodes deleted";
    }
    leaf num-links-added {
      type uint32;
      description "Number of links added";
    }
    leaf num-links-deleted {
      type uint32;
      description "Number of links deleted";
    }
    leaf num-prefixes-added {
      type uint32;
      description "Number of prefixes added";
    }
    leaf num-prefixes-deleted {
      type uint32;
      description "Number of prefixes deleted";
    }
  }

  grouping PCE-NODE-SUMMARY-BAG {
    description "PCE Node Summary Information";

    container stats-topology-update {
      description "Statistics on topology update";
      uses PCE-TOPO-STATS-BAG;
    }
    leaf nodes {
      type uint32;
      description "Number of PCE nodes";
    }
    leaf lookup-nodes {
      type uint32;
      description "Number of lookup nodes";
    }
    leaf prefixes {
      type uint32;
      description "Number of prefixes";
    }
    leaf prefix-sids {
      type uint32;
      description "Number of total prefix SIDs";
    }
    leaf regular-prefix-sids {
      type uint32;
      description "Number of reguar prefix SIDs";
    }
    leaf strict-prefix-sids {
      type uint32;
      description "Number of strict prefix SIDs";
    }
    leaf links {
      type uint32;
      description "Number of links";
    }
    leaf epe-links {
      type uint32;
      description "Number of EPE links";
    }
    leaf adjacency-sids {
      type uint32;
      description "Number of total adjacency SIDs";
    }
    leaf epesids {
      type uint32;
      description "Number of total EPE SIDs";
    }
    leaf protected-adjacency-sids {
      type uint32;
      description "Number of protected adjacency SIDs";
    }
    leaf un-protected-adjacency-sids {
      type uint32;
      description "Number of unprotected adjacency SIDs";
    }
    leaf topology-consistent {
      type boolean;
      description "True if topology is consistent";
    }
  }

  grouping PCE-PEER-BAG {
    description "Peer information";

    container brief-pcep-information {
      description "PCE protocol information";
      uses PCE-PCEP-BAG;
    }
    leaf peer-address-xr {
      type inet:ipv4-address;
      description "Peer address";
    }
    leaf peer-protocol {
      type Pce-proto;
      description "Protocol between PCE and peer";
    }
  }

  grouping PCE-PCEP-ERROR-BAG {
    description "PCEP Error information";
    leaf pc-error-type {
      type uint8;
      description "PCEP Error type";
    }
    leaf pc-error-value {
      type uint8;
      description "PCEP Error Value";
    }
  }

  grouping PCE-PCEP-BAG {
    description "PCEP information";
    leaf pcep-state {
      type Pcep-state;
      description "PCEP State";
    }
    leaf stateful {
      type boolean;
      description "Stateful";
    }
    leaf capability-update {
      type boolean;
      description "Update capability";
    }
    leaf capability-instantiate {
      type boolean;
      description "Instantiation capability";
    }
    leaf capability-segment-routing {
      type boolean;
      description "Segment Routing capability";
    }
    leaf capability-triggered-sync {
      type boolean;
      description "Triggered Synchronization capability";
    }
    leaf capability-db-version {
      type boolean;
      description "DB version capability";
    }
    leaf capability-delta-sync {
      type boolean;
      description "Delta Synchronization capability";
    }
  }

  grouping PCE-PCEP-DETAIL-BAG {
    description "Detailed PCE protocol information";

    container brief-pcep-information {
      description "Brief PCE protocol information";
      uses PCE-PCEP-BAG;
    }

    container last-error-rx {
      description "Last PCError received";
      uses PCE-PCEP-ERROR-BAG;
    }

    container last-error-tx {
      description "Last PCError sent";
      uses PCE-PCEP-ERROR-BAG;
    }
    leaf error {
      type string;
      description "Error (for display only)";
    }
    leaf speaker-id {
      type string;
      description "Speaker Entity ID";
    }
    leaf pcep-up-time {
      type uint32;
      description "PCEP Up Time";
    }
    leaf keepalives {
      type uint32;
      description "Keepalive count";
    }
    leaf md5-enabled {
      type boolean;
      description "MD5 Authentication Enabled";
    }
    leaf keychain-enabled {
      type boolean;
      description "Keychain based Authentication Enabled";
    }
    leaf negotiated-local-keepalive {
      type uint32;
      description "Negotiated KA";
    }
    leaf negotiated-remote-keepalive {
      type uint32;
      description "Negotiated KA";
    }
    leaf negotiated-dead-time {
      type uint32;
      description "Negotiated DT";
    }
    leaf pce-request-rx {
      type uint32;
      description "PCEReq Rx";
    }
    leaf pce-request-tx {
      type uint32;
      description "PCEReq Tx";
    }
    leaf pce-reply-rx {
      type uint32;
      description "PCERep Rx";
    }
    leaf pce-reply-tx {
      type uint32;
      description "PCERep Tx";
    }
    leaf pce-error-rx {
      type uint32;
      description "PCEErr Rx";
    }
    leaf pce-error-tx {
      type uint32;
      description "PCEErr Tx";
    }
    leaf pce-open-tx {
      type uint32;
      description "PCEOpen Tx";
    }
    leaf pce-open-rx {
      type uint32;
      description "PCEOpen Rx";
    }
    leaf pce-report-rx {
      type uint32;
      description "PCERpt Rx";
    }
    leaf pce-report-tx {
      type uint32;
      description "PCERpt Tx";
    }
    leaf pce-update-rx {
      type uint32;
      description "PCEUpd Rx";
    }
    leaf pce-update-tx {
      type uint32;
      description "PCEUpd Tx";
    }
    leaf pce-initiate-rx {
      type uint32;
      description "PCEInit Rx";
    }
    leaf pce-initiate-tx {
      type uint32;
      description "PCEInit Tx";
    }
    leaf pce-keepalive-tx {
      type uint64;
      description "PCE Keepalive Tx";
    }
    leaf pce-keepalive-rx {
      type uint64;
      description "PCE Keepalive Rx";
    }
    leaf local-session-id {
      type uint8;
      description "Local PCEP session ID";
    }
    leaf remote-session-id {
      type uint8;
      description "Remote PCEP session ID";
    }
    leaf minimum-keepalive-interval {
      type uint8;
      description "Minimum keepalive interval for the peer";
    }
    leaf maximum-dead-interval {
      type uint8;
      description "Maximum dead interval for the peer";
    }
  }

  grouping PCE-PEER-DETAIL-BAG {
    description "Detailed PCEP peer information";

    container detail-pcep-information {
      description "Detailed PCE protocol information";
      uses PCE-PCEP-DETAIL-BAG;
    }
    leaf peer-address-xr {
      type inet:ipv4-address;
      description "Peer address";
    }
    leaf peer-protocol {
      type Pce-proto;
      description "Protocol between PCE and peer";
    }
  }

  grouping PCE-EVENT-INFO {
    description "PCE Event information";
    leaf event-message {
      type string;
      description "Event message";
    }
    leaf time-stamp {
      type uint32;
      description "Event time, relative to Jan 1, 1970";
    }
  }

  grouping PCE-EVENT-BAG {
    description "Private LSP information";

    list event-buffer {
      description "LSP Event buffer";
      uses PCE-EVENT-INFO;
    }
  }

  grouping PCE-LSPA-INFO {
    description "PCE LSP attribute information";
    leaf affinity-exclude-any {
      type uint32;
      description "Affinity exclude any";
    }
    leaf affinity-include-any {
      type uint32;
      description "Affinity include any";
    }
    leaf affinity-include-all {
      type uint32;
      description "Affinity include all";
    }
    leaf setup-priority {
      type uint8;
      description "Setup Priority";
    }
    leaf hold-priority {
      type uint8;
      description "Hold Priority";
    }
    leaf local-protection {
      type boolean;
      description "True, if local protection is desired";
    }
  }

  grouping PCE-ASSO-INFO {
    description "PCE LSP association information";
    leaf association-type {
      type uint32;
      description "Association Type";
    }
    leaf association-id {
      type uint32;
      description "Association ID";
    }
    leaf association-source {
      type inet:ipv4-address;
      description "Association Source";
    }
  }

  grouping PCE-LSP-RSVP-ERROR-BAG {
    description "RSVP error information";
    leaf node-address {
      type inet:ipv4-address;
      description "RSVP error node address";
    }
    leaf error-flags {
      type uint8;
      description "RSVP error flags";
    }
    leaf error-code {
      type uint8;
      description "RSVP error code";
    }
    leaf error-value {
      type uint16;
      description "RSVP error value";
    }
  }

  grouping PCE-PCEP-INFO {
    description "PCEP LSP information";

    container rsvp-error {
      description "RSVP error info";
      uses PCE-LSP-RSVP-ERROR-BAG;
    }
    leaf pcepid {
      type uint32;
      description "PCE protocol identifier";
    }
    leaf pcep-flag-d {
      type boolean;
      description "PCEP LSP delegation flag";
    }
    leaf pcep-flag-s {
      type boolean;
      description "PCEP LSP state-sync flag";
    }
    leaf pcep-flag-r {
      type boolean;
      description "PCEP LSP remove flag";
    }
    leaf pcep-flag-a {
      type boolean;
      description "PCEP LSP admin flag";
    }
    leaf pcep-flag-o {
      type uint8;
      description "PCEP LSP operation flag";
    }
  }

  grouping PCE-RRO-INFO {
    description "RRO information";

    container sr-rro {
      description "Segment Routing RRO info";
      uses PCE-SR-HOP-TYPE;
    }
    leaf rro-type {
      type Pce-rro;
      description "RRO Type";
    }
    leaf ipv4-address {
      type inet:ipv4-address;
      description "IPv4 address of RRO";
    }
    leaf mpls-label {
      type uint32;
      description "MPLS label of RRO";
    }
    leaf flags {
      type uint8;
      description "RRO Flags";
    }
  }

  grouping PCE-SR-HOP-TYPE {
    description "SR hop type";
    leaf sid-type {
      type Pce-sr-sid;
      description "SID type";
    }
    leaf mpls-label {
      type uint32;
      description "Label";
    }
    leaf local-addr {
      type inet:ipv4-address;
      description "Local Address";
    }
    leaf remote-addr {
      type inet:ipv4-address;
      description "Remote Address";
    }
  }

  grouping PCE-RSVP-HOP-TYPE {
    description "RSVP hop type";
    leaf hop-address {
      type inet:ipv4-address;
      description "RSVP hop address";
    }
  }

  grouping PCE-ERO-INFO {
    description "ERO information";
    leaf reported-metric-type {
      type uint32;
      description "Reported Metric Type";
    }
    leaf reported-metric-value {
      type uint32;
      description "Reported Metric Value";
    }
    leaf computed-metric-type {
      type uint32;
      description "Computed Metric Type";
    }
    leaf computed-metric-value {
      type uint32;
      description "Computed Metric Value";
    }
    leaf computed-hop-list-time {
      type uint32;
      description "Computed Hop List Time";
    }

    list reported-rsvp-path {
      description "Reported RSVP path";
      uses PCE-RSVP-HOP-TYPE;
    }

    list reported-sr-path {
      description "Reported SR path";
      uses PCE-SR-HOP-TYPE;
    }

    list computed-rsvp-path {
      description "Computed RSVP path";
      uses PCE-RSVP-HOP-TYPE;
    }

    list computed-sr-path {
      description "Computed SR path";
      uses PCE-SR-HOP-TYPE;
    }
  }

  grouping PCE-LSP-DETAIL-INFO {
    description "Detailed LSP information";

    container brief-lsp-information {
      description "Brief LSP information";
      uses PCE-LSP-INFO;
    }

    container er-os {
      description "Paths";
      uses PCE-ERO-INFO;
    }

    container lsppcep-information {
      description "PCEP related LSP information";
      uses PCE-PCEP-INFO;
    }

    container lsp-association-info {
      description "LSP association information";
      uses PCE-ASSO-INFO;
    }

    container lsp-attributes {
      description "LSP attributes";
      uses PCE-LSPA-INFO;
    }
    leaf signaled-bandwidth-specified {
      type boolean;
      description "True if router notifies signal bandwidth";
    }
    leaf signaled-bandwidth {
      type uint64;
      description "Signaled Bandwidth";
    }
    leaf actual-bandwidth-specified {
      type boolean;
      description "True if router notifies actual bandwidth";
    }
    leaf actual-bandwidth {
      type uint64;
      description "Actual bandwidth utilized in the data-plane";
    }
    leaf lsp-role {
      type uint32;
      description "LSP Role";
    }
    leaf computing-pce {
      type uint32;
      description "Computing PCE";
    }
    leaf sub-delegated-pce {
      type inet:ipv4-address;
      description "Sub delegated PCE";
    }
    leaf state-sync-pce {
      type inet:ipv4-address;
      description "State-sync PCE";
    }
    leaf reporting-pcc-address {
      type inet:ipv4-address;
      description "Reporting PCC address";
    }
    leaf-list srlg-info {
      type uint32;
      description "List of SLRGs used by LSP";
    }

    list rro {
      description "RRO";
      uses PCE-RRO-INFO;
    }
  }

  grouping PCE-TUN-DETAIL-BAG {
    description "Tunnel detail information";

    container private-lsp-information {
      description "Private LSP information";
      uses PCE-EVENT-BAG;
    }
    leaf pcc-address {
      type inet:ipv4-address;
      description "PCC address";
    }
    leaf tunnel-name-xr {
      type string;
      description "Tunnel Name";
    }

    list detail-lsp-information {
      description "Detail LSP information";
      uses PCE-LSP-DETAIL-INFO;
    }
  }

  grouping PCE-LSP-COUNTS-BAG {
    description "Number of LSPs";
    leaf all-ls-ps {
      type uint32;
      description "Number of all LSPs";
    }
    leaf up-ls-ps {
      type uint32;
      description "Number of operational LSPs";
    }
    leaf admin-up-ls-ps {
      type uint32;
      description "Number of administratively up LSPs";
    }
    leaf sr-ls-ps {
      type uint32;
      description "Number of LSPs with Segment routing setup type";
    }
    leaf rsvp-ls-ps {
      type uint32;
      description "Number of LSPs with RSVP setup type";
    }
  }

  grouping PCE-LSP-PER-PEER-SUMMARY-BAG {
    description "Number of LSPs for specific peer";

    container lsp-summary {
      description "Number of LSPs for specific peer";
      uses PCE-LSP-COUNTS-BAG;
    }
    leaf peer-address {
      type inet:ipv4-address;
      description "Peer IPv4 address";
    }
  }

  grouping PCE-LSP-SUMMARY-BAG {
    description "PCE LSP summary information";

    container all-ls-ps {
      description "Summary for all peers";
      uses PCE-LSP-COUNTS-BAG;
    }

    list peer-ls-ps-info {
      description "Number of LSPs for specific peer";
      uses PCE-LSP-PER-PEER-SUMMARY-BAG;
    }
  }

  grouping PCE-LSP-INFO {
    description "LSP common information";
    leaf source-address {
      type inet:ipv4-address;
      description "Source address";
    }
    leaf destination-address {
      type inet:ipv4-address;
      description "Destination address";
    }
    leaf tunnel-id {
      type uint32;
      description "Tunnel ID";
    }
    leaf lspid {
      type uint32;
      description "LSP ID";
    }
    leaf binding-sid {
      type uint32;
      description "Binding SID";
    }
    leaf lsp-setup-type {
      type Lsp-setup;
      description "LSP Setup Type";
    }
    leaf operational-state {
      type Pcep-lsp-state;
      description "Operational state";
    }
    leaf administrative-state {
      type Lsp-state;
      description "Admin state";
    }
  }

  grouping PCE-TUN-BAG {
    description "Tunnel information";
    leaf pcc-address {
      type inet:ipv4-address;
      description "PCC address";
    }
    leaf tunnel-name-xr {
      type string;
      description "Tunnel Name";
    }

    list brief-lsp-information {
      description "Brief LSP information";
      uses PCE-LSP-INFO;
    }
  }
}
