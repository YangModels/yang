submodule Cisco-IOS-XR-l2vpn-oper-sub3 {

  belongs-to Cisco-IOS-XR-l2vpn-oper {
    prefix Cisco-IOS-XR-l2vpn-oper;
  }

  /*** LINKAGE (IMPORTS / INCLUDES) ***/

  import ietf-inet-types { prefix "inet"; }

  import ietf-yang-types { prefix "yang"; }

  import Cisco-IOS-XR-types { prefix "xr"; }

  include Cisco-IOS-XR-l2vpn-oper-sub2 {
    revision-date 2017-06-26;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR l2vpn package operational data.

     Copyright (c) 2013-2017 by Cisco Systems, Inc.
     All rights reserved.";

  revision "2017-06-26" {
    description
      "Change identifiers to be more readable.";
  }

  revision "2017-05-01" {
    description
      "Fixing backward compatibility error in module.";
  }

  revision "2015-11-09" {
    description
      "IOS XR 6.0 revision.";
  }

  typedef L2fib-g8032-aps-port-status {
    type enumeration {
      enum l2fib-aps-port-state-unknown {
        description "APS port state unknown";
      }
      enum l2fib-aps-port-state-unbound {
        description "APS port state unbound";
      }
      enum l2fib-aps-port-state-bound {
        description "APS port state bound";
      }
    }
    description "APS port status";
  }
  typedef L2fib-g8032-rpl {
    type enumeration {
      enum rpl-unknown {
        description "No RPL info";
      }
      enum port0-owner {
        description "Port 0 owner";
      }
      enum port0-neighbor {
        description "Port 0 neighbor";
      }
      enum port0-next-neighbor {
        description "Port 0 next neighbor";
      }
      enum port1-owner {
        description "Port 1 owner";
      }
      enum port1-neighbor {
        description "Port 1 neighbor";
      }
      enum port1-next-neighbor {
        description "Port 1 next neighbor";
      }
    }
    description "RPL types in g8032 ring";
  }
  typedef L2fib-l2tp-session {
    type enumeration {
      enum l2tpv3 {
        description "L2TPv3 session";
      }
      enum l2tpv2 {
        description "L2TPv2 session";
      }
    }
    description "L2TPv2 and L2TPv3 session type";
  }
  typedef L2fib-main-if-instance-state {
    type enumeration {
      enum forwarding {
        description "Forwarding state";
      }
      enum blocked {
        description "Blocked state";
      }
      enum mac-learning {
        description "Mac learning state";
      }
      enum nack {
        description "Nack state";
      }
      enum forwarning-not-useful {
        description "Forwarding not useful state";
      }
      enum blocked-not-useful {
        description "Blocked not useful state";
      }
      enum mac-learning-not-useful {
        description "Mac Learning not useful state";
      }
      enum blocked-data-only {
        description "Blocked data only state";
      }
      enum multicast-pe2ce-blocked {
        description "Multicast PE to CE blocked state";
      }
      enum multicast-blocked {
        description "Multicast blocked state";
      }
      enum port-state-unknown {
        description "Port state unknown";
      }
    }
    description "State of a main port instance";
  }
  typedef Mgmt-l2fib-bridge-mac-evpn-ctx {
    type enumeration {
      enum mgmt-l2fib-bridge-mac-evpn-ctx-none {
        description "mgmt l2fib bridge mac evpn ctx none";
      }
      enum mgmt-l2fib-bridge-mac-evpn-ctx-esi-id {
        description "mgmt l2fib bridge mac evpn ctx esi id";
      }
      enum mgmt-l2fib-bridge-mac-evpn-ctx-local-label {
        description "mgmt l2fib bridge mac evpn ctx local label";
      }
      enum mgmt-l2fib-bridge-mac-evpn-ctx-moi {
        description "mgmt l2fib bridge mac evpn ctx moi";
      }
      enum mgmt-l2fib-bridge-mac-evpn-ctx-bp-ifh {
        description "mgmt l2fib bridge mac evpn ctx bp ifh";
      }
    }
    description "Mgmt l2fib bridge mac evpn ctx";
  }
  typedef L2fib-ip-addr {
    type enumeration {
      enum ip-none {
        value 0;
        description "ip none";
      }
      enum v4 {
        value 4;
        description "v4";
      }
      enum v6 {
        value 6;
        description "v6";
      }
    }
    description "L2fib ip addr";
  }
  typedef Mgmt-l2fib-stats-data {
    type enumeration {
      enum mgmt-l2fib-stats-type-unknown {
        description "mgmt l2fib stats type unknown";
      }
      enum mgmt-l2fib-stats-type-mcast {
        description "mgmt l2fib stats type mcast";
      }
    }
    description "Mgmt l2fib stats data";
  }
  typedef L2vpn-ptree {
    type enumeration {
      enum none {
        value 0;
        description "No ptree type";
      }
      enum rsvp-te {
        value 1;
        description "RSVP_TE ptree type";
      }
      enum mldp {
        value 2;
        description "MLDP ptree type";
      }
    }
    description "ptree type";
  }
  typedef L2fib-feature {
    type enumeration {
      enum l2fib-feature-dhcp-snooping {
        description "l2fib feature dhcp snooping";
      }
      enum l2fib-feature-igmp-snooping {
        description "l2fib feature igmp snooping";
      }
      enum l2fib-feature-mld-snooping {
        description "l2fib feature mld snooping";
      }
      enum l2fib-feature-max {
        description "l2fib feature max";
      }
    }
    description "L2fib feature";
  }
  typedef L2fib-storm-control-rate-unit {
    type enumeration {
      enum pps {
        description "Packets Per Second";
      }
      enum kb-ps {
        description "Kilobits Per Second";
      }
    }
    description "Storm Control Rate Unit Type";
  }
  typedef Mgmt-l2fib-mac-sec-action {
    type enumeration {
      enum not-set {
        value 0;
        description "MAC Secure Action Not Set";
      }
      enum restrict {
        value 1;
        description "MAC Secure Action Restrict";
      }
      enum none {
        value 2;
        description "MAC Secure Action None";
      }
      enum shutdown {
        value 3;
        description "MAC Secure Action Shutdown";
      }
    }
    description "Mgmt l2fib mac sec action";
  }
  typedef Mgmt-l2fib-mac-limit-notify {
    type enumeration {
      enum mgmt-l2fib-mac-limit-notify-none {
        description "mgmt l2fib mac limit notify none";
      }
      enum mgmt-l2fib-mac-limit-notify-syslog {
        description "mgmt l2fib mac limit notify syslog";
      }
      enum mgmt-l2fib-mac-limit-notify-trap {
        description "mgmt l2fib mac limit notify trap";
      }
      enum mgmt-l2fib-mac-limit-notify-both {
        description "mgmt l2fib mac limit notify both";
      }
    }
    description "Mgmt l2fib mac limit notify";
  }
  typedef Mgmt-l2fib-mac-limit-action {
    type enumeration {
      enum mgmt-l2fib-mac-limit-action-type-none {
        description "mgmt l2fib mac limit action type none";
      }
      enum mgmt-l2fib-mac-limit-action-type-flood {
        description "mgmt l2fib mac limit action type flood";
      }
      enum mgmt-l2fib-mac-limit-action-type-no-flood {
        description "mgmt l2fib mac limit action type no flood";
      }
      enum mgmt-l2fib-mac-limit-action-type-shutdown {
        description "mgmt l2fib mac limit action type shutdown";
      }
    }
    description "Mgmt l2fib mac limit action";
  }
  typedef L2fib-load-bal {
    type enumeration {
      enum flow-undef {
        description "Load Balance Flow Undefined";
      }
      enum src-dst-mac {
        description "Load Balance Flow src-dst-mac";
      }
      enum src-dst-ip {
        description "Load Balance Flow src-dst-ip";
      }
      enum vc {
        description "Load Balance VC based";
      }
    }
    description "L2fib load bal";
  }
  typedef L2fib-group-state {
    type enumeration {
      enum up {
        description "Group State Up";
      }
      enum down {
        description "Group State Down";
      }
    }
    description "group state";
  }
  typedef L2fib-pw-redundancy-role {
    type enumeration {
      enum primary {
        description "Primary pseudowire";
      }
      enum backup {
        description "Backup pseudowire";
      }
    }
    description "Pseudowire redundancy role";
  }
  typedef L2fib-pw-id {
    type enumeration {
      enum default {
        value 0;
        description "Default value - not set";
      }
      enum manual {
        value 1;
        description "Manual pseudowire ID";
      }
      enum vpls {
        value 2;
        description "VPLS pseudowire ID";
      }
      enum vpws {
        value 3;
        description "VPWS pseudowire ID";
      }
      enum vpls-ldp {
        value 4;
        description "VPLS with LDP signaling pseudowire ID";
      }
      enum l2fib-pw-id-type-pwr {
        value 5;
        description "PW-routing ID";
      }
      enum l2fib-pw-id-type-evpn {
        value 6;
        description "EVPN pseudowire ID";
      }
    }
    description "Pseudowire ID type";
  }
  typedef Mgmt-l2fib-bridge {
    type enumeration {
      enum mgmt-l2fib-bridge-type-default {
        value 0;
        description "mgmt l2fib bridge type default";
      }
      enum mgmt-l2fib-bridge-type-pbb-edge {
        value 1;
        description "mgmt l2fib bridge type pbb edge";
      }
      enum mgmt-l2fib-bridge-type-pbb-core {
        value 2;
        description "mgmt l2fib bridge type pbb core";
      }
    }
    description "Mgmt l2fib bridge";
  }
  typedef Mgmt-l2fib-data {
    type enumeration {
      enum mgmt-l2fib-data-type-min {
        description "mgmt l2fib data type min";
      }
      enum mgmt-l2fib-data-type-xcon {
        description "mgmt l2fib data type xcon";
      }
      enum mgmt-l2fib-data-type-ac {
        description "mgmt l2fib data type ac";
      }
      enum mgmt-l2fib-data-type-span {
        description "mgmt l2fib data type span";
      }
      enum mgmt-l2fib-data-type-atom {
        description "mgmt l2fib data type atom";
      }
      enum mgmt-l2fib-data-type-pbb {
        description "mgmt l2fib data type pbb";
      }
      enum mgmt-l2fib-data-type-vni {
        description "mgmt l2fib data type vni";
      }
      enum mgmt-l2fib-data-type-n-hop {
        description "mgmt l2fib data type n hop";
      }
      enum mgmt-l2fib-data-type-l2tp {
        description "mgmt l2fib data type l2tp";
      }
      enum mgmt-l2fib-data-type-l2tpv2 {
        description "mgmt l2fib data type l2tpv2";
      }
      enum mgmt-l2fib-data-type-bridge {
        description "mgmt l2fib data type bridge";
      }
      enum mgmt-l2fib-data-type-bridge-shg {
        description "mgmt l2fib data type bridge shg";
      }
      enum mgmt-l2fib-data-type-bridge-port {
        description "mgmt l2fib data type bridge port";
      }
      enum mgmt-l2fib-data-type-bridge-mac {
        description "mgmt l2fib data type bridge mac";
      }
      enum mgmt-l2fib-data-type-mcast-table {
        description "mgmt l2fib data type mcast table";
      }
      enum mgmt-l2fib-data-type-mcast-leaf {
        description "mgmt l2fib data type mcast leaf";
      }
      enum mgmt-l2fib-data-type-mcast-xid {
        description "mgmt l2fib data type mcast xid";
      }
      enum mgmt-l2fib-data-type-dhcp {
        description "mgmt l2fib data type dhcp";
      }
      enum mgmt-l2fib-data-type-l2tp-ipv6-ts {
        description "mgmt l2fib data type l2tp ipv6 ts";
      }
      enum mgmt-l2fib-data-type-pwhe-mp {
        description "mgmt l2fib data type pwhe mp";
      }
      enum mgmt-l2fib-data-type-evpn {
        description "mgmt l2fib data type evpn";
      }
      enum mgmt-l2fib-data-type-fxs {
        description "mgmt l2fib data type fxs";
      }
      enum mgmt-l2fib-data-type-max {
        description "mgmt l2fib data type max";
      }
    }
    description "Mgmt l2fib data";
  }
  typedef Mgmt-l2fib-switching {
    type enumeration {
      enum mgmt-l2fib-switching-type-unknown {
        description "mgmt l2fib switching type unknown";
      }
      enum mgmt-l2fib-switching-type-ac-ac {
        description "mgmt l2fib switching type ac ac";
      }
      enum mgmt-l2fib-switching-type-ac-atom {
        description "mgmt l2fib switching type ac atom";
      }
      enum mgmt-l2fib-switching-type-ac-vfi {
        description "mgmt l2fib switching type ac vfi";
      }
      enum mgmt-l2fib-switching-type-ac-l2tp {
        description "mgmt l2fib switching type ac l2tp";
      }
      enum mgmt-l2fib-switching-type-atom-atom {
        description "mgmt l2fib switching type atom atom";
      }
      enum mgmt-l2fib-switching-type-vfi-atom {
        description "mgmt l2fib switching type vfi atom";
      }
      enum mgmt-l2fib-switching-type-vfi-l2tp {
        description "mgmt l2fib switching type vfi l2tp";
      }
      enum mgmt-l2fib-switching-type-l2tp-atom {
        description "mgmt l2fib switching type l2tp atom";
      }
      enum mgmt-l2fib-switching-type-l2tp-l2tp {
        description "mgmt l2fib switching type l2tp l2tp";
      }
      enum mgmt-l2fib-switching-type-max {
        description "mgmt l2fib switching type max";
      }
    }
    description "Mgmt l2fib switching";
  }

  grouping L2FIB-DHCP-BINDING-SUMMARY-INFO {
    description "L2FIB DHCP binding summary info";

    container port {
      description "Union of Port information";
      uses L2FIB-DHCP-BIND-UN;
    }
    leaf bindings {
      type uint32;
      description "DHCP binding count";
    }
  }

  grouping L2FIB-VTEP-INFO {
    description "L2FIB vtep info";
    leaf nve-if {
      type xr:Interface-name;
      description "Parent NVE IF Handle";
    }
    leaf vn-iid {
      type uint32;
      description "VNI ID";
    }
    leaf vte-pip {
      type inet:ipv4-address;
      description "Peer VTEP IP Address";
    }
  }

  grouping L2FIB-PWHE-MP-SUMMARY-INFO {
    description "L2VPN PWHE Main-port summary info";
    leaf total-count {
      type uint32;
      description "Number of PWHE Main-ports";
    }
  }

  grouping L2FIB-PWGROUP-SUMMARY-INFO {
    description "L2VPN PWGROUP summary info";
    leaf plat-grouping-supported {
      type boolean;
      description "Platform supports Grouping";
    }
    leaf total-pw-groups {
      type uint32;
      description "Total number of PWGROUP objects";
    }
    leaf pw-groups-down {
      type uint32;
      description "Number of PWGROUP objects down";
    }
  }

  grouping L2FIB-PTREE-SUMMARY-INFO {
    description "L2VPN PTree summary info";
    leaf total-ptree-count {
      type uint32;
      description "Number of PTree objects";
    }
    leaf mldp-enabled-ptree-count {
      type uint32;
      description "Number of MLDP enabled PTree objects";
    }
    leaf lmrib-mldp-ptree-count {
      type uint32;
      description "Number of MLDP PTree Objects owned by LMRIB";
    }
    leaf rsvp-te-enabled-ptree-count {
      type uint32;
      description "Number of RSVP-TE enabled PTree objects";
    }
    leaf lmrib-rsvp-te-ptree-count {
      type uint32;
      description "Number of RSVP-TE PTree Objects owned by LMRIB";
    }
  }

  grouping L2FIB-GLOBAL-CFG-INFO {
    description "L2VPN Global Configuration";

    container base {
      description "Base Information";
      uses L2FIB-BASE-INFO;
    }
    leaf load-balance-type {
      type L2fib-load-bal;
      description "Type of Load-Balancing";
    }
    leaf evpn-imc-label-block-base {
      type uint32;
      description "Base of label range in use for EVPN IMC PD";
    }
    leaf evpn-imc-label-block-size {
      type uint16;
      description "Size of label range in use for EVPN IMC PD";
    }
  }

  grouping L2FIB-EVPN-SUMMARY-INFO {
    description "L2VPN evpn summary info";
    leaf total-count {
      type uint32;
      description "Number of EVPN Multicast Replication lists";
    }
    leaf isid-count {
      type uint32;
      description "Number of ISID leaves";
    }
    leaf default-count {
      type uint32;
      description "Number of default leaves";
    }
    leaf stitching-count {
      type uint32;
      description "Number of stitching leaves";
    }
  }

  grouping L2FIB-OBJ-QUEUES-SUMMARY {
    description "L2FIB OBJ QUEUES SUMMARY";
    leaf inline-cnt {
      type uint32;
      description "number of objects in inline queue";
    }
    leaf retry-cnt {
      type uint32;
      description "number of objects in retry queue";
    }
    leaf update-cnt {
      type uint32;
      description "number of objects in update queues";
    }
    leaf del-cnt {
      type uint32;
      description "number of objects in delete queues";
    }
  }

  grouping L2FIB-MAC-SUMMARY-INFO {
    description "L2FIB bridge mac summary info";
    leaf local-mac-count {
      type uint32;
      description "number of locally learnt macs";
    }
    leaf remote-mac-count {
      type uint32;
      description "number of remotely learned macs";
    }
    leaf static-mac-count {
      type uint32;
      description "number of static macs";
    }
    leaf routed-mac-count {
      type uint32;
      description "number of routed macs";
    }
    leaf mac-count {
      type uint32;
      description "number of all macs";
    }
    leaf sbmac-count {
      type uint32;
      description "number of Source BMACs";
    }
    leaf bmac-count {
      type uint32;
      description "number of BMACs";
    }
  }

  grouping L2FIB-BD-SUMMARY-INFO {
    description "L2VPN bridge-domain summary info";
    leaf bridge-domain-count {
      type uint32;
      description "Number of bridge-domains";
    }
    leaf bridge-domain-drop-count {
      type uint32;
      description "Number of bridge-domain updates dropped";
    }
    leaf bridge-domain-with-bvi-count {
      type uint32;
      description "Number of bridge-domains with BVI";
    }
    leaf bridge-domain-with-p2mp-enabled {
      type uint32;
      description "Number of bridge-domains with P2MP enabled";
    }
    leaf bridge-domain-with-pbbevpn-enabled {
      type uint32;
      description "Number of bridge-domains with PBB EVPN enabled";
    }
    leaf bridge-domain-with-evpn-enabled {
      type uint32;
      description "Number of bridge-domains with EVPN enabled";
    }
  }

  grouping L2FIB-L2TP-DISP-SUMMARY-INFO {
    description "L2TP disposition session object summary";
    leaf l2tp-disposition-session-count {
      type uint32;
      description "number of l2tp disposition session objects";
    }
    leaf bound-l2tp-disposition-session-count {
      type uint32;
      description "number of bound l2tp dispostion objects";
    }
    leaf unbound-l2tp-disposition-session-count {
      type uint32;
      description "number of unbound l2tp disposition objects";
    }
  }

  grouping L2FIB-NH-SUMMARY-INFO2 {
    description "Specific nhop summary";
    leaf next-hop-count {
      type uint32;
      description "total number of nhops";
    }
    leaf bound-next-hop-count {
      type uint32;
      description "number of bound nhops";
    }
    leaf unbound-next-hop-count {
      type uint32;
      description "number of unbound nhops";
    }
    leaf next-hop-pending-registration-count {
      type uint32;
      description "number of nhops pending registration with fib ";
    }
  }

  grouping L2FIB-NH-SUMMARY-INFO {
    description "nhop db summary";

    container mpls-il {
      description "MPLS Internal Label nexthop summary";
      uses L2FIB-NH-SUMMARY-INFO2;
    }

    container mpls {
      description "MPLS nexthop summary";
      uses L2FIB-NH-SUMMARY-INFO2;
    }

    container l2tp {
      description "L2TP nexthop summary";
      uses L2FIB-NH-SUMMARY-INFO2;
    }

    container lsm {
      description "LSM nexthop summary";
      uses L2FIB-NH-SUMMARY-INFO2;
    }

    container p2mp-tunnels {
      description "P2MPtun nexthop summary";
      uses L2FIB-NH-SUMMARY-INFO2;
    }
  }

  grouping L2FIB-XC-SUMMARY-INFO {
    description "xconnect db summary";
    leaf xconnect-count {
      type uint32;
      description "total number of entries";
    }
    leaf xconnect-up-count {
      type uint32;
      description "number of up entries";
    }
    leaf xconnect-down-count {
      type uint32;
      description "number of down entries";
    }
    leaf ac-to-pw-count-mpls {
      type uint32;
      description "number of ac->pw-mpls entries";
    }
    leaf ac-to-pw-count-l2tp {
      type uint32;
      description "number of ac->pw-l2tp entries";
    }
    leaf ac-to-pw-count-l2tp-ip-v6 {
      type uint32;
      description "number of ac->pw-l2tp-ipv6 entries";
    }
    leaf ac-to-pw-count-l2tpv2 {
      type uint32;
      description "number of ac->pw-l2tpv2 entries";
    }
    leaf ac-to-ac-count {
      type uint32;
      description "number of ac->ac entries";
    }
    leaf ac-to-unknown-count {
      type uint32;
      description "number of ac->unknown type entries";
    }
    leaf mon-sess-to-pw-count {
      type uint32;
      description "number of monitor_session->pw entries";
    }
    leaf mon-sess-to-unknown-count {
      type uint32;
      description "number of monitor_session->unknown type entries";
    }
    leaf ac-to-bp-count {
      type uint32;
      description "number of ac->bp entries";
    }
    leaf pw-to-bp-count {
      type uint32;
      description "number of pw->bp entries";
    }
    leaf pw-to-unknown-count {
      type uint32;
      description "number of pw->unknown type entries";
    }
    leaf pbb-to-bp-count {
      type uint32;
      description "number of pbb->bp entries";
    }
    leaf pbb-to-unknown-count {
      type uint32;
      description "number of pbb->unknown type entries";
    }
    leaf vni-to-bp-count {
      type uint32;
      description "number of vni->bp entries";
    }
    leaf vni-to-unknown-count {
      type uint32;
      description "number of vni->unknown type entries";
    }
    leaf evpn-to-bp-count {
      type uint32;
      description "number of evpn->bp entries";
    }
    leaf evpn-to-unknown-count {
      type uint32;
      description "number of evpn->unknown type entries";
    }
    leaf ac-down-count-aib {
      type uint32;
      description "number of down acs with reason aib";
    }
    leaf ac-down-count-l2vpn {
      type uint32;
      description "number of down acs with reason l2vpn";
    }
    leaf ac-down-count-l3fib {
      type uint32;
      description "number of down acs with reason fib";
    }
    leaf ac-down-count-vpdn {
      type uint32;
      description "number of down acs with reason vpdn";
    }
    leaf vpws-pw-invalid-xid-drop-count {
      type uint32;
      description
        "number of xc updates dropped due to VPWS PW
        invalid xid";
    }
    leaf vpls-pw-invalid-xid-drop-count {
      type uint32;
      description
        "number of xc updates dropped due to VPLS PW
        invalid xid";
    }
    leaf virtual-ac-invalid-xid-drop-count {
      type uint32;
      description
        "number of xc updates dropped due to Virtual AC
        invalid xid";
    }
    leaf pbb-invalid-xid-drop-count {
      type uint32;
      description
        "number of xc updates dropped due to PBB invalid
        xid";
    }
    leaf vni-invalid-xid-drop-count {
      type uint32;
      description
        "number of xc updates dropped due to VNI invalid
        xid";
    }
    leaf evpn-invalid-xid-drop-count {
      type uint32;
      description
        "number of xc updates dropped due to EVPN invalid
        xid";
    }
    leaf vpls-pw-max-exceeded-drop-cnt {
      type uint32;
      description
        "number of xc updates dropped due to max VPLS PWs
        exceeded";
    }
    leaf bundle-ac-max-exceeded-drop-cnt {
      type uint32;
      description
        "number of xc updates dropped due to max Bundle
        ACs exceeded";
    }
    leaf p2p-count {
      type uint32;
      description "number of p2p xconnects";
    }
    leaf bp-count {
      type uint32;
      description "number of bridge-port xconnects";
    }
    leaf pwhe-l2-if-count {
      type uint32;
      description "number of PWHE L2IF xconnects";
    }
  }

  grouping L2FIB-SUMMARY-INFO {
    description "L2FIB summary info";

    container xconnect-summary {
      description "xconnect db summary info";
      uses L2FIB-XC-SUMMARY-INFO;
    }

    container next-hop-summary {
      description "nhop db summry info";
      uses L2FIB-NH-SUMMARY-INFO;
    }

    container l2tp-disposition-summary {
      description "L2TP disposition object summary";
      uses L2FIB-L2TP-DISP-SUMMARY-INFO;
    }

    container bridge-domain-summary {
      description "Bridge-domain summary info";
      uses L2FIB-BD-SUMMARY-INFO;
    }

    container mac-summary {
      description "mac summary info";
      uses L2FIB-MAC-SUMMARY-INFO;
    }

    container queue-summary {
      description "queue summary info";
      uses L2FIB-OBJ-QUEUES-SUMMARY;
    }

    container evpn-summary {
      description "evpn summary info";
      uses L2FIB-EVPN-SUMMARY-INFO;
    }

    container global-cfg {
      description "Global configuration";
      uses L2FIB-GLOBAL-CFG-INFO;
    }

    container ptree-summary {
      description "P2MP PTree summary info";
      uses L2FIB-PTREE-SUMMARY-INFO;
    }

    container pw-group-summary {
      description "PWGroup summary info";
      uses L2FIB-PWGROUP-SUMMARY-INFO;
    }

    container pwhe-mp-summary {
      description "PWHE Main-port summary info";
      uses L2FIB-PWHE-MP-SUMMARY-INFO;
    }
  }

  grouping L2FIB-MCAST-XID-INFO {
    description "L2fib xid info";

    container base-information {
      description "Base Information";
      uses L2FIB-BASE-INFO;
    }

    container forward-stats {
      description "Forwarding Statistics";
      uses L2FIB-PLATFORM-STATS-BAG;
    }

    container source-prefix {
      description "Source Prefix";
      uses L2FIB-PREFIX-INFO;
    }

    container destination-prefix {
      description "Destination Prefix";
      uses L2FIB-PREFIX-INFO;
    }
    leaf bridge-id {
      type uint32;
      description "Bridge Id";
    }
    leaf ac-interface-handle {
      type xr:Interface-name;
      description "AC If handle";
    }
    leaf leaf-pointer {
      type uint32;
      description "Leaf Ptr";
    }
    leaf pw-id {
      type string {
        length "0..40";
      }
      description "PW ID";
    }
    leaf next-hop-address {
      type inet:ipv4-address;
      description "NHOP IP Address";
    }
    leaf isid {
      type uint32;
      description "Isid Id";
    }
    leaf csfl {
      type uint32;
      description "Csfl Id";
    }
    leaf sat-id {
      type uint16;
      description "Sat Id";
    }
    leaf is-ole-offloaded {
      type boolean;
      description "Ole Offloaded";
    }
    leaf is-ole-master {
      type boolean;
      description "Ole Master";
    }
    leaf is-topo-hub-and-spoke {
      type boolean;
      description "Topo HubAndSpoke";
    }
  }

  grouping L2FIB-BRIDGE-SUMMARY-INFO {
    description "L2VPN bridge summary info";
    leaf bridge-id {
      type uint32;
      description "Bridge ID";
    }
    leaf bridge-name {
      type string;
      description "Bridge name";
    }
    leaf mac-limit {
      type uint32;
      description "MAC limit";
    }
    leaf mac-limit-action {
      type Mgmt-l2fib-mac-limit-action;
      description "MAC limit action";
    }
    leaf flood-disabled {
      type boolean;
      description "Is flooding disabled";
    }
    leaf mac-learning-disabled {
      type boolean;
      description "Is MAC learning disabled";
    }
    leaf mac-port-down-flush-disabled {
      type boolean;
      description "Is MAC port down flush disabled";
    }
    leaf admin-disabled {
      type boolean;
      description "Is administratively disabled";
    }
    leaf bridge-port-count {
      type uint32;
      description "Number of bridge ports";
    }
    leaf number-of-shg {
      type uint32;
      description "Number of split horizon groups";
    }
    leaf number-of-hwmac {
      type uint32;
      description "Number of HW MAC addresses";
    }
    leaf number-of-swmac {
      type uint32;
      description "Number of SW MAC addresses";
    }
    leaf mtu {
      type uint32;
      description "MTU";
    }
    leaf aging-time-out {
      type uint32;
      description "Aging timeout";
    }
    leaf msti {
      type uint32;
      description "multi-spanning tree instance";
    }
  }

  grouping L2FIB-BRIDGE-PORT-SEG-UN {
    description "L2FIB BRIDGE PORT SEG UN";

    container ac {
      when "../data-type = 'mgmt-l2fib-data-type-ac'" {
        description "../DataType = 'MGMT_L2FIB_DATA_TYPE_AC'";
      }
      description "ac";
      uses L2FIB-AC-INFO;
    }

    container pbb {
      when "../data-type = 'mgmt-l2fib-data-type-pbb'" {
        description "../DataType = 'MGMT_L2FIB_DATA_TYPE_PBB'";
      }
      description "pbb";
      uses L2FIB-PBB-INFO;
    }

    container vni {
      when "../data-type = 'mgmt-l2fib-data-type-vni'" {
        description "../DataType = 'MGMT_L2FIB_DATA_TYPE_VNI'";
      }
      description "vni";
      uses L2FIB-VNI-INFO;
    }

    container evpn {
      when "../data-type = 'mgmt-l2fib-data-type-evpn'" {
        description "../DataType = 'MGMT_L2FIB_DATA_TYPE_EVPN'";
      }
      description "evpn";
      uses L2FIB-EVPN-INFO;
    }

    container pw {
      when "../data-type != 'mgmt-l2fib-data-type-ac' and"+
        " ../data-type != 'mgmt-l2fib-data-type-pbb' and"+
        " ../data-type != 'mgmt-l2fib-data-type-vni' and"+
        " ../data-type != 'mgmt-l2fib-data-type-evpn'" {
          description
            "../DataType != 'MGMT_L2FIB_DATA_TYPE_AC' and .
            ./DataType != 'MGMT_L2FIB_DATA_TYPE_PBB' and .
            ./DataType != 'MGMT_L2FIB_DATA_TYPE_VNI' and .
            ./DataType != 'MGMT_L2FIB_DATA_TYPE_EVPN'";
      }
      description "pw";
      uses L2FIB-PW-INFO;
    }
    leaf data-type {
      type Mgmt-l2fib-data;
      description "DataType";
    }
  }

  grouping L2FIB-BRIDGE-PORT-DETAIL-INFO {
    description "L2VPN bridge port info";

    container segment {
      description "Segment";
      uses L2FIB-BRIDGE-PORT-SEG-UN;
    }

    container bridge-port-operational-info {
      description "Bridge port operational information";
      uses L2FIB-OPER-BRIDGE-PORT-INFO;
    }
    leaf bridge-id {
      type uint32;
      description "Bridge ID";
    }
    leaf shg-id {
      type uint32;
      description "Split horizon group ID";
    }
    leaf xc-id {
      type uint32;
      description "xconnect ID";
    }
    leaf number-of-hw-mac {
      type uint32;
      description "Number of HW MAC addresses";
    }
    leaf number-of-sw-mac {
      type uint32;
      description "Number of SW MAC addresses";
    }
    leaf mac-limit {
      type uint32;
      description "MAC limit";
    }
    leaf mac-limit-action {
      type Mgmt-l2fib-mac-limit-action;
      description "MAC limit action";
    }
    leaf flooding-disabled {
      type boolean;
      description "Is flooding disabled";
    }
    leaf mac-learning-disabled {
      type boolean;
      description "Is MAC learning disabled";
    }
    leaf mac-port-down-flush-disabled {
      type boolean;
      description "Is MAC port down flush disabled";
    }
    leaf mtu {
      type uint32;
      description "MTU";
    }
    leaf aging-time-out {
      type uint32;
      description "Aging timeout";
    }
  }

  grouping L2FIB-G8032-RING-INSTANCE-DETAIL-INFO {
    description "L2FIB ethernet ring instance info detail";
    leaf ring-instance {
      type uint32;
      description "Ring instance number";
    }
    leaf vlan-ids {
      type string;
      description "Vlan Ids";
    }
    leaf ring-profile {
      type string;
      description "Ring Profile";
    }
    leaf rpl {
      type L2fib-g8032-rpl;
      description "RPL";
    }
    leaf aps-port0 {
      type string;
      description "Port 0 of aps-channel";
    }
    leaf aps-port1 {
      type string;
      description "Port 1 of aps-channel";
    }
    leaf aps-port-status0 {
      type L2fib-g8032-aps-port-status;
      description "Status of Port 0";
    }
    leaf aps-port-status1 {
      type L2fib-g8032-aps-port-status;
      description "Status of Port 1";
    }
    leaf aps-channel-level {
      type uint32;
      description "APS channel level";
    }
  }

  grouping L2FIB-G8032-RING-INSTANCE-SUMMARY-INFO {
    description "L2FIB ethernet ring instance info summary";
    leaf ring-instance {
      type uint32;
      description "Ring instance number";
    }
    leaf aps-port0 {
      type string;
      description "Port 0 of aps-channel";
    }
    leaf aps-port1 {
      type string;
      description "Port 1 of aps-channel";
    }
  }

  grouping L2FIB-G8032-RING-SUMMARY-INFO {
    description "L2FIB ethernet ring info summary";
    leaf ring-name {
      type string;
      description "Name of the ring";
    }
    leaf port0 {
      type string;
      description "Port 0";
    }
    leaf port1 {
      type string;
      description "Port 1";
    }
  }

  grouping L2FIB-G8032-RING-DETAIL-INFO {
    description "L2FIB ethernet ring info detail";
    leaf ring-name {
      type string;
      description "Name of the ring";
    }
    leaf port0 {
      type string;
      description "Port 0";
    }
    leaf port1 {
      type string;
      description "Port 1";
    }
    leaf monitor0 {
      type string;
      description "Monitor port 0";
    }
    leaf monitor1 {
      type string;
      description "Monitor port 1";
    }
    leaf is-open-ring {
      type boolean;
      description "Open Ring";
    }
  }

  grouping L2FIB-L2TP-DISP-INFO {
    description "L2TP session disposition object";

    container base {
      description "Base information";
      uses L2FIB-BASE-INFO;
    }
    leaf session-id-xr {
      type uint32;
      description "Local Session Id";
    }
    leaf interface-handle {
      type xr:Interface-name;
      description "Interface handle of egress main interface";
    }
    leaf sub-interface-name {
      type xr:Interface-name;
      description "SubInterface Name";
    }
    leaf source-address {
      type inet:ipv4-address;
      description "Source/Local IP address of the tunnel";
    }
    leaf bound {
      type boolean;
      description "Bind status";
    }
    leaf tunnel-id-xr {
      type uint32;
      description "Tunnel ID, l2tpv2";
    }
    leaf ipv4-table-id {
      type uint32;
      description "IPv4 Table ID";
    }
    leaf ipv6-table-id {
      type uint32;
      description "IPv6 Table ID";
    }
    leaf nhop-ip-addr {
      type inet:ipv4-address;
      description "NHOP IP Address of the tunnel";
    }
    leaf session-type {
      type L2fib-l2tp-session;
      description "L2tp or L2tpv2 session";
    }
  }

  grouping L2FIB-MAIN-PORT-MSTP-DETAIL-INFO {
    description "L2FIB main port mstp detail info";

    container base {
      description "Base information";
      uses L2FIB-BASE-INFO;
    }
    leaf parent-interface-xr {
      type xr:Interface-name;
      description "main port ID";
    }
    leaf msti-xr {
      type uint32;
      description "multi-spanning tree instance configured value";
    }
    leaf internal-msti {
      type uint32;
      description "multi-spanning tree instance internal value";
    }
    leaf state {
      type uint32;
      description "MSTI state";
    }
    leaf learn-key {
      type uint8;
      description "Learn Key";
    }
    list bridge-port-array {
      description "Bridge port";
        leaf entry {
                  type xr:Interface-name;
        }
    }
  }

  grouping L2FIB-MAIN-INTERFACE-INSTANCE-BPORT-SUMMARY-INFO {
    description
      "L2VPN main interface instance bridge port info
      summary";
    leaf bridge-port-id {
      type xr:Interface-name;
      description "Bridge Port ID";
    }
    leaf bridge-id {
      type uint32;
      description "Bridge ID";
    }
    leaf main-interface {
      type xr:Interface-name;
      description "Main interface ID";
    }
    leaf main-if-type {
      type uint8;
      description "Main Interface Type";
    }
    leaf virtual-if-name {
      type string;
      description "Virtual Main IfName";
    }
    leaf bp-type {
      type uint8;
      description "Bridge Port Type";
    }
  }

  grouping L2FIB-MAIN-INTERFACE-INSTANCE-SUMMARY-INFO {
    description
      "L2FIB main interface instance summary info
      summary";
    leaf main-interface {
      type xr:Interface-name;
      description "Main interface ID";
    }
    leaf main-if-type {
      type uint8;
      description "Main Interface Type";
    }
    leaf virtual-if-name {
      type string;
      description "Virtual Main IfName";
    }
    leaf instance {
      type uint32;
      description "Interface instance";
    }
    leaf state {
      type L2fib-main-if-instance-state;
      description "Instance state";
    }
    leaf bridge-port-count {
      type uint32;
      description "Number of bridge ports";
    }
    leaf instance-provisioned {
      type boolean;
      description "Instances provisioned flag";
    }
  }

  grouping L2FIB-MAIN-INTERFACE-INSTANCE-BPORT-DETAIL-INFO {
    description
      "L2VPN main interface instance bridge port info
      detail";

    container oper {
      description "Operational information";
      uses L2FIB-OPER-BRIDGE-PORT-INFO;
    }
    leaf bridge-port-id {
      type xr:Interface-name;
      description "Bridge Port ID";
    }
    leaf bridge-id {
      type uint32;
      description "Bridge ID";
    }
    leaf state {
      type L2fib-main-if-instance-state;
      description "Instance state";
    }
    leaf main-interface {
      type xr:Interface-name;
      description "Main interface ID";
    }
    leaf main-if-type {
      type uint8;
      description "Main Interface Type";
    }
    leaf virtual-if-name {
      type string;
      description "Virtual Main IfName";
    }
    leaf bp-type {
      type uint8;
      description "Bridge Port Type";
    }
  }

  grouping L2FIB-MAIN-INTERFACE-INSTANCE-DETAIL-INFO {
    description "L2FIB main interface instance detail info detail";
    leaf main-interface {
      type xr:Interface-name;
      description "Main interface ID";
    }
    leaf main-if-type {
      type uint8;
      description "Main Interface Type";
    }
    leaf virtual-if-name {
      type string;
      description "Virtual Main IfName";
    }
    leaf instance {
      type uint32;
      description "Interface instance";
    }
    leaf state {
      type L2fib-main-if-instance-state;
      description "Instance state";
    }
    leaf bridge-port-count {
      type uint32;
      description "Number of bridge ports";
    }
    leaf instance-provisioned {
      type boolean;
      description "Instances provisioned flag";
    }
  }

  grouping L2FIB-MAIN-INTERFACE-SUMMARY-INFO {
    description "L2FIB main interface summary info summary";
    leaf main-interface {
      type xr:Interface-name;
      description "Main Interface ID";
    }
    leaf main-if-type {
      type uint8;
      description "Main Interface Type";
    }
    leaf virtual-if-name {
      type string;
      description "Virtual Main IfName";
    }
    list instance-id {
      description "Instance IDs";
        leaf entry {
                  type uint32;
        }
    }
    list instances-state {
      description "State for each instance";
        leaf entry {
                  type L2fib-main-if-instance-state;
        }
    }
    list instances-provisioned {
      description "Instances provisioned flag";
        leaf entry {
                  type boolean;
        }
    }
  }

  grouping L2FIB-EVPN-REMOTE-SHG-INFO {
    description "L2FIB EVPN Remote Split Horizon Group Info";

    container remote-split-horizon-group-label {
      description "Remote split horizon group label";
      uses L2VPN-EVPN-REMOTE-SHG-INFO;
    }
  }

  grouping L2FIB-MAIN-INTERFACE-DETAIL-INFO {
    description "L2FIB main interface detail info detail";
    leaf main-interface {
      type xr:Interface-name;
      description "Main Interface ID";
    }
    leaf main-if-type {
      type uint8;
      description "Main Interface Type";
    }
    leaf virtual-if-name {
      type string;
      description "Virtual Main IfName";
    }
    leaf mac {
      type string;
      description "MAC Address";
    }
    leaf esi-id {
      type uint16;
      description "Ethernet segment ID";
    }
    leaf evpn-shg-local-label {
      type uint32;
      description "EVPN split horizon group local label";
    }
    list instance-id {
      description "Instance IDs";
        leaf entry {
                  type uint32;
        }
    }
    list instances-state {
      description "State for each instance";
        leaf entry {
                  type L2fib-main-if-instance-state;
        }
    }
    list instances-provisioned {
      description "Instances provisioned flag";
        leaf entry {
                  type boolean;
        }
    }
    list bridge-port-count-instance {
      description "Number of bridge ports per instance";
        leaf entry {
                  type uint32;
        }
    }
    list ethernet-segment-identifier {
      description "Ethernet Segment Identifier";
        leaf entry {
                  type uint8;
        }
    }

    list evpn-shg-remote-info {
      description "EVPN split horizon group remote info";
      uses L2FIB-EVPN-REMOTE-SHG-INFO;
    }
  }

  grouping L2FIB-DHCP-BIND-UN {
    description "L2FIB DHCP BIND UN";

    container ac {
      when "../data-type = 'mgmt-l2fib-data-type-ac'" {
        description "../DataType = 'MGMT_L2FIB_DATA_TYPE_AC'";
      }
      description "ac";
      uses L2FIB-AC-KEY-INFO;
    }

    container pw {
      when "../data-type != 'mgmt-l2fib-data-type-ac'" {
        description "../DataType != 'MGMT_L2FIB_DATA_TYPE_AC'";
      }
      description "pw";
      uses L2FIB-PW-KEY-INFO;
    }
    leaf data-type {
      type Mgmt-l2fib-data;
      description "DataType";
    }
  }

  grouping L2FIB-DHCP-BINDING-DETAIL-INFO {
    description "L2FIB DHCP binding detail info";

    container base {
      description "Base information";
      uses L2FIB-BASE-INFO;
    }

    container port {
      description "Union of Port information";
      uses L2FIB-DHCP-BIND-UN;
    }
  }

  grouping L2FIB-PWGROUP-INFO {
    description "l2fib pwgroup info";
    leaf group-state {
      type L2fib-group-state;
      description "Group State";
    }
    leaf pw-list-count {
      type uint32;
      description "Dependent PW List Count";
    }
  }

  grouping L2FIB-RSRC-SHM-INFO {
    description "Shared memory availability";
    leaf oout-of-resource-mode {
      type uint32;
      description "OOR mode";
    }
    leaf maximum-available {
      type uint64;
      units "byte";
      description "Maximum bytes available";
    }
    leaf average-available {
      type uint64;
      units "byte";
      description "Average number of bytes available";
    }
    leaf average-utility {
      type uint64;
      description "Average utilization";
    }
  }

  grouping L2FIB-RSRC-INFO {
    description "L2FIB resource availability info";

    container shm-resource {
      description "Shared memory resource info";
      uses L2FIB-RSRC-SHM-INFO;
    }
    leaf overall-out-of-resource-mode {
      type uint32;
      description "Overall OOR mode";
    }
    leaf hardware-resource-mode-information {
      type yang:hex-string;
      description "Opaque hardware resource info";
    }
    list hardware-resource-mode {
      description "Hardware resource mode";
        leaf entry {
                  type uint32;
        }
    }
  }

  grouping L2FIB-MAIN-PORT-MSTP-SUMMARY-INFO {
    description "L2FIB main port mstp summary info";

    container base {
      description "Base information";
      uses L2FIB-BASE-INFO;
    }
    leaf parent-interface-xr {
      type xr:Interface-name;
      description "main port ID";
    }
    leaf msti-xr {
      type uint32;
      description "multi-spanning tree instance";
    }
    leaf state {
      type uint32;
      description "MSTI state";
    }
    leaf bridge-port-count {
      type uint32;
      description "Number of bridge ports";
    }
  }

  grouping L2FIB-BRIDGE-P2MP-PW-INFO {
    description "L2FIB BRIDGE P2MP PW INFO";

    container parent-next-hop {
      description "Parent Next Hop for P2MP PW";
      uses L2FIB-NHOP-INFO;
    }
    leaf ptree-type {
      type L2vpn-ptree;
      description "P2MP ptree type";
    }
    leaf lsm-id {
      type uint32;
      description "LSM id";
    }
    leaf p2mp-te-interface {
      type xr:Interface-name;
      description "P2MP TE ifh";
    }
    leaf parent-nh-valid {
      type boolean;
      description "Is Parent NH Valid";
    }
    leaf parent-nh-bound {
      type boolean;
      description "Is Parent NH Bound";
    }
    leaf local-label {
      type uint32;
      description "Local label";
    }
  }

  grouping L2FIB-BRIDGE-BVI-INFO {
    description "L2FIB BRIDGE BVI INFO";
    leaf bvi-ifh {
      type xr:Interface-name;
      description "BVI interface handle";
    }
    leaf bvi-xid {
      type uint32;
      description "BVI xconnect id";
    }
    leaf bvi-name {
      type string {
        length "0..65";
      }
      description "BVI name";
    }
    leaf bvi-shg-id {
      type uint32;
      description "BVI Split Horizon Group ID";
    }
    leaf irb-plat-data-len {
      type uint32;
      units "byte";
      description "Platform data bytes";
    }
    leaf irb-plat-data {
      type yang:hex-string;
      description "IRB platform data";
    }
  }

  grouping L2FIB-BRIDGE-PBB-CORE {
    description "L2FIB BRIDGE PBB CORE";
    leaf nber-edge-bd {
      type uint32;
      description "Number of associated pbb-edge Bds";
    }
  }

  grouping L2FIB-BRIDGE-PBB-EDGE {
    description "L2FIB BRIDGE PBB EDGE";
    leaf i-sid {
      type uint32;
      description "I SID";
    }
    leaf core-bd-name {
      type string;
      description "Core Bridge Domain name";
    }
    leaf mirp-lite-rx {
      type uint64;
      description "MIRP-lite Rx packet counter";
    }
    leaf mirp-lite-tx {
      type uint64;
      description "MIRP-lite Tx packet counter";
    }
  }

  grouping L2FIB-BRIDGE-PBB-UN {
    description "L2FIB BRIDGE PBB UN";

    container edge {
      when "../pbb-type = 'mgmt-l2fib-bridge-type-pbb-edge'" {
        description
          "../PbbType = 'MGMT_L2FIB_BRIDGE_TYPE_PBB_EDGE'";
      }
      description "edge";
      uses L2FIB-BRIDGE-PBB-EDGE;
    }

    container core {
      when "../pbb-type = 'mgmt-l2fib-bridge-type-pbb-core'" {
        description
          "../PbbType = 'MGMT_L2FIB_BRIDGE_TYPE_PBB_CORE'";
      }
      description "core";
      uses L2FIB-BRIDGE-PBB-CORE;
    }
    leaf pbb-type {
      type Mgmt-l2fib-bridge;
      description "PbbType";
    }
  }

  grouping L2FIB-OPER-BRIDGE-INFO {
    description "L2VPN bridge operational information";

    container operational-information {
      description "L2 operational information";
      uses L2FIB-OPER-INFO;
    }
    leaf unicast-storm-control-pps {
      type uint64;
      description "Unicast storm control pps";
    }
    leaf unicast-storm-control-kb-ps {
      type uint64;
      units "kbit/s";
      description "Unicast storm control kbps";
    }
    leaf broadcast-storm-control-pps {
      type uint64;
      description "Broadcast storm control pps";
    }
    leaf broadcast-storm-control-kb-ps {
      type uint64;
      units "kbit/s";
      description "Broadcast storm control kbps";
    }
    leaf multicast-storm-control-pps {
      type uint64;
      description "Multicast storm control pps";
    }
    leaf multicast-storm-control-kb-ps {
      type uint64;
      units "kbit/s";
      description "Multicast storm control kbps";
    }
  }

  grouping L2FIB-BRIDGE-INFO {
    description "L2VPN bridge detailed info";

    container base {
      description "Base information";
      uses L2FIB-BASE-INFO;
    }

    container oper {
      description "Operational information";
      uses L2FIB-OPER-BRIDGE-INFO;
    }

    container bd-pbb-union {
      description "Union of bridge Edge and Core info";
      uses L2FIB-BRIDGE-PBB-UN;
    }

    container bvi-info {
      description "BVI Information";
      uses L2FIB-BRIDGE-BVI-INFO;
    }

    container p2mppw-info {
      description "P2MP PW Information";
      uses L2FIB-BRIDGE-P2MP-PW-INFO;
    }
    leaf bridge-id {
      type uint32;
      description "Bridge ID";
    }
    leaf bridge-port-count {
      type uint32;
      description "Number of bridge ports";
    }
    leaf number-of-hwmac {
      type uint32;
      description "Number of HW MAC addresses";
    }
    leaf number-of-swmac {
      type uint32;
      description "Number of SW MAC addresses";
    }
    leaf bridge-name {
      type string;
      description "Bridge name";
    }
    leaf shg-count {
      type uint32;
      description "Number of split horizon groups";
    }
    leaf bridge-type {
      type Mgmt-l2fib-bridge;
      description "Bridge Type";
    }
    leaf learn-key {
      type uint8;
      description "Learn Key";
    }
  }

  grouping L2FIB-DHCP-BINDING-COUNT-INFO {
    description "L2FIB DHCP binding count info";
    leaf bindings {
      type uint32;
      description "DHCP binding count";
    }
  }

  grouping L2FIB-PWHE-MP-SHOW-INFO {
    description "L2FIB PWHE Main-port info";
    leaf next-hop-valid {
      type boolean;
      description "IS Next Hop Valid";
    }
    leaf next-hop-address {
      type inet:ipv4-address;
      description "Next Hop Address";
    }
    leaf pseudo-wire-type {
      type uint32;
      description "Pseudowire type";
    }
    leaf generic-interface-list-id {
      type uint32;
      description "Generic Interface List ID";
    }
    leaf internal-label {
      type uint32;
      description "Internal label";
    }
    leaf remote-label {
      type uint32;
      description "Remote label";
    }
    leaf control-word-enabled {
      type boolean;
      description "Control Word Enabled";
    }
  }

  grouping L2FIB-EVPN-IPMAC-INFO {
    description "L2FIB EVPN IP-MAC Info";

    container ip-address-xr {
      description "IP Address";
      uses L2FIB-IP-ADDR;
    }
    leaf bdid-xr {
      type uint32;
      description "BD ID";
    }
    leaf mac-address-xr {
      type yang:mac-address;
      description "MAC Address";
    }
    leaf arp-nd-sync-pending {
      type boolean;
      description "Sync to ARP/ND Process Pending";
    }
    leaf arp-nd-probe-pending {
      type boolean;
      description "Probe to ARP/ND Process Pending";
    }
    leaf arp-nd-delete-pending {
      type boolean;
      description "Delete to ARP/ND Process Pending";
    }
    leaf is-local-xr {
      type boolean;
      description "IP-MAC Route is locally learned";
    }
  }

  grouping L2FIB-BRIDGE-MAC-EVPN-CTX-UN {
    description "L2FIB BRIDGE MAC EVPN CTX UN";

    container mcast-ole {
      when "../data-type = 'mgmt-l2fib-bridge-mac-evpn-ctx-moi'" {
        description
          "../DataType =
          'MGMT_L2FIB_BRIDGE_MAC_EVPN_CTX_MOI'";
      }
      description "mcast ole";
      uses L2VPN-EVPN-MOI-INFO;
    }
    leaf data-type {
      type Mgmt-l2fib-bridge-mac-evpn-ctx;
      description "DataType";
    }
    leaf esi-id {
      when "../data-type ="+
        " 'mgmt-l2fib-bridge-mac-evpn-ctx-esi-id'" {
          description
            "../DataType =
            'MGMT_L2FIB_BRIDGE_MAC_EVPN_CTX_ESI_ID'";
      }
      type uint16;
      description "EsiID";
    }
    leaf local-label {
      when "../data-type ="+
        " 'mgmt-l2fib-bridge-mac-evpn-ctx-local-label'" {
          description
            "../DataType =
            'MGMT_L2FIB_BRIDGE_MAC_EVPN_CTX_LOCAL_LABEL'";
      }
      type uint32;
      description "LocalLabel";
    }
    leaf bp-ifh {
      when "../data-type ="+
        " 'mgmt-l2fib-bridge-mac-evpn-ctx-bp-ifh'" {
          description
            "../DataType =
            'MGMT_L2FIB_BRIDGE_MAC_EVPN_CTX_BP_IFH'";
      }
      type xr:Interface-name;
      description "BP IFH";
    }
  }

  grouping L2FIB-PW-KEY-INFO {
    description "L2FIB PW KEY INFO";
    leaf pw-id {
      type uint64;
      description "Pseudowire ID";
    }
    leaf next-hop-address {
      type inet:ipv4-address;
      description "Next Hop Address";
    }
    leaf pseudo-wire-id-type {
      type L2fib-pw-id;
      description "Pseudowire ID type";
    }
  }

  grouping L2FIB-EVPN-KEY-INFO {
    description "L2FIB EVPN KEY INFO";
    leaf xcid {
      type uint32;
      description "Xconnect ID";
    }
  }

  grouping L2FIB-VNI-KEY-INFO {
    description "L2FIB VNI KEY INFO";
    leaf xcid {
      type uint32;
      description "Xconnect ID";
    }
    leaf parent-if {
      type xr:Interface-name;
      description "Parent NVE Interface";
    }
  }

  grouping L2FIB-PBB-KEY-INFO {
    description "L2FIB PBB KEY INFO";
    leaf xcid {
      type uint32;
      description "Xconnect ID";
    }
  }

  grouping L2FIB-AC-KEY-INFO {
    description "L2FIB AC KEY INFO";
    leaf interface-handle {
      type xr:Interface-name;
      description "Interface Handle";
    }
  }

  grouping L2FIB-BRIDGE-PORT-SEG-KEY-UN {
    description "L2FIB BRIDGE PORT SEG KEY UN";

    container ac {
      when "../data-type = 'mgmt-l2fib-data-type-ac'" {
        description "../DataType = 'MGMT_L2FIB_DATA_TYPE_AC'";
      }
      description "ac";
      uses L2FIB-AC-KEY-INFO;
    }

    container pbb {
      when "../data-type = 'mgmt-l2fib-data-type-pbb'" {
        description "../DataType = 'MGMT_L2FIB_DATA_TYPE_PBB'";
      }
      description "pbb";
      uses L2FIB-PBB-KEY-INFO;
    }

    container vni {
      when "../data-type = 'mgmt-l2fib-data-type-vni'" {
        description "../DataType = 'MGMT_L2FIB_DATA_TYPE_VNI'";
      }
      description "vni";
      uses L2FIB-VNI-KEY-INFO;
    }

    container evpn {
      when "../data-type = 'mgmt-l2fib-data-type-evpn'" {
        description "../DataType = 'MGMT_L2FIB_DATA_TYPE_EVPN'";
      }
      description "evpn";
      uses L2FIB-EVPN-KEY-INFO;
    }

    container pw {
      when "../data-type != 'mgmt-l2fib-data-type-ac' and"+
        " ../data-type != 'mgmt-l2fib-data-type-pbb' and"+
        " ../data-type != 'mgmt-l2fib-data-type-vni' and"+
        " ../data-type != 'mgmt-l2fib-data-type-evpn'" {
          description
            "../DataType != 'MGMT_L2FIB_DATA_TYPE_AC' and .
            ./DataType != 'MGMT_L2FIB_DATA_TYPE_PBB' and .
            ./DataType != 'MGMT_L2FIB_DATA_TYPE_VNI' and .
            ./DataType != 'MGMT_L2FIB_DATA_TYPE_EVPN'";
      }
      description "pw";
      uses L2FIB-PW-KEY-INFO;
    }
    leaf data-type {
      type Mgmt-l2fib-data;
      description "DataType";
    }
  }

  grouping L2FIB-BRIDGE-MAC-INFO {
    description "L2VPN bridge MAC address info";

    container base {
      description "Base information";
      uses L2FIB-BASE-INFO;
    }

    container segment {
      description "Segment";
      uses L2FIB-BRIDGE-PORT-SEG-KEY-UN;
    }

    container evpn-ctx {
      description "Evpn Context";
      uses L2FIB-BRIDGE-MAC-EVPN-CTX-UN;
    }

    container next-hop {
      description "Next Hop";
      uses L2FIB-NHOP-INFO;
    }
    leaf platform-is-hw-learn {
      type uint8;
      description "Platform is HW Learn";
    }
    leaf node-id {
      type xr:Node-id;
      description "Nodeid list";
    }
    leaf bridge-domain-name {
      type string;
      description "Bridge name";
    }
    leaf bridge-id {
      type uint32;
      description "Bridge ID";
    }
    leaf bmac-configured {
      type boolean;
      description "Flag: Configured BMAC";
    }
    leaf vni-l3-flag {
      type boolean;
      description "Flag: L3 Vxlan";
    }
    leaf pbb-bmac {
      type yang:mac-address;
      description "Backbone MAC Address";
    }
    leaf l3-encapsulationvlan-id {
      type uint16;
      description "L3 encapsulation Vlan ID";
    }
    leaf next-hop-valid {
      type boolean;
      description "IS Next Hop Valid";
    }
    leaf peer-vtep-ip {
      type inet:ipv4-address;
      description "Peer VTEP IP for this MAC Address";
    }
    leaf flag-extension {
      type uint16;
      description "MAC Flag Extension";
    }
    leaf vni {
      type uint32;
      description "VNI Information";
    }
  }

  grouping L2VPN-EVPN-MOI-INFO {
    description "L2VPN EVPN MOI INFO";
    leaf next-hop-ipv6-addr {
      type inet:ipv6-address;
      description "Next Hop IPv6 address";
    }
    leaf mcast-label {
      type uint32;
      description "Inclusive mcast label";
    }
  }

  grouping L2FIB-EVPN-MCAST-OLE-INFO {
    description "L2FIB evpn mcast ole info";

    container mcast-ole {
      description "Mcast Ole Info";
      uses L2VPN-EVPN-MOI-INFO;
    }

    container next-hop {
      description "Next Hop";
      uses L2FIB-NHOP-INFO;
    }
    leaf is-bound {
      type boolean;
      description "Is bound";
    }
    leaf next-hop-valid {
      type boolean;
      description "IS Next Hop Valid";
    }
  }

  grouping L2FIB-EVPN-MCAST-LEAF-INFO {
    description "L2FIB evpn mcast leaf info";
    leaf bridge-domain-name {
      type string;
      description "Bridge-domain name";
    }
    leaf bridge-domain-id {
      type uint32;
      description "bdid value";
    }
    leaf xcid {
      type uint32;
      description "xcid value";
    }
    leaf is-bound {
      type boolean;
      description "Is bound";
    }
  }

  grouping L2FIB-P2MP-PTREE-INFO {
    description "l2fib p2mp ptree info";
    leaf lsm-id-xr {
      type uint32;
      description "MLDP Lsm Id";
    }
    leaf tunnel-id-xr {
      type uint32;
      description "RSVPTE Tunnel Id";
    }
    leaf p2mp-id-xr {
      type uint32;
      description "RSVPTE P2MP Id";
    }
    leaf extended-tunnel-id-xr {
      type inet:ipv4-address;
      description "RSVPTE Ext Tunnel Id";
    }
  }

  grouping L2FIB-IP-ADDR {
    description "L2FIB IP ADDR";
    leaf addr-type {
      type L2fib-ip-addr;
      description "addr type";
    }
    leaf ip {
      type inet:ipv6-address;
      description "ip";
    }
  }

  grouping L2FIB-MAC-DB-INFO {
    description "L2FIB MAC DB info";

    container addr {
      description "IP Address";
      uses L2FIB-IP-ADDR;
    }

    container nhaddr {
      description "IP Address";
      uses L2FIB-IP-ADDR;
    }
    leaf element-type {
      type uint8;
      description "Element Type";
    }
    leaf node-id {
      type xr:Node-id;
      description "Node ID";
    }
    leaf topology-id {
      type uint32;
      description "Topology ID";
    }
    leaf mac-address-xr {
      type yang:mac-address;
      description "MAC Address";
    }
    leaf interface-handle-xr {
      type uint32;
      description "Interface Handle";
    }
    leaf xcid {
      type uint32;
      description "Cross-connect Identifier";
    }
    leaf generation {
      type uint8;
      description "HW MAC generation";
    }
  }

  grouping L2FIB-PBB-BMAC-SA-INFO {
    description "L2FIB PBB BMAC SA INFO";
    leaf configured {
      type boolean;
      description "BMAC SA configured";
    }
    leaf mac {
      type yang:mac-address;
      description "Backbone Source Mac";
    }
    leaf chassis-mac {
      type yang:mac-address;
      description "Chassis Mac";
    }
  }

  grouping L2FIB-MCAST-IRB-INFO {
    description "L2FIB MCAST IRB INFO";
    leaf mxid-ac-interface-handle {
      type xr:Interface-name;
      description "Master XID AC If handle";
    }
    leaf mxid-pw-id {
      type uint32;
      description "Master XID PW ID";
    }
    leaf mxid-next-hop-address {
      type inet:ipv4-address;
      description "Master XID NHOP IP Address";
    }
    leaf irb-plat-data-len {
      type uint16;
      units "byte";
      description "Platform data bytes";
    }
    list irb-plat-data {
      max-elements "16";

      description "IRB platform data";
        leaf entry {
                  type uint32;
        }
    }
  }

  grouping L2FIB-MCAST-BAG-COUNTERS {
    description "L2FIB mcast statistics counters";
    leaf packets {
      type uint64;
      description "Number of packets";
    }
    leaf bytes {
      type uint64;
      units "byte";
      description "Number of bytes";
    }
  }

  grouping L2FIB-MCAST-STATS-BAG {
    description "L2FIB mcast forwarding statistics";

    container multicast-forward-stat {
      description "forwarded stats";
      uses L2FIB-MCAST-BAG-COUNTERS;
    }

    container received-stat {
      description "received stats";
      uses L2FIB-MCAST-BAG-COUNTERS;
    }

    container punt {
      description "punted stats";
      uses L2FIB-MCAST-BAG-COUNTERS;
    }

    container drop {
      description "dropped stats";
      uses L2FIB-MCAST-BAG-COUNTERS;
    }

    container multicast-core-forward-stat {
      description "core forwarded stats";
      uses L2FIB-MCAST-BAG-COUNTERS;
    }

    container core-received-stat {
      description "core received stats";
      uses L2FIB-MCAST-BAG-COUNTERS;
    }
  }

  grouping L2FIB-PLATFORM-STATS-UNION-BAG {
    description "L2FIB PLATFORM STATS UNION BAG";

    container mulicast {
      when "../data-type = 'mgmt-l2fib-stats-type-mcast'" {
        description "../DataType = 'MGMT_L2FIB_STATS_TYPE_MCAST'";
      }
      description "mulicast";
      uses L2FIB-MCAST-STATS-BAG;
    }
    leaf data-type {
      type Mgmt-l2fib-stats-data;
      description "DataType";
    }
  }

  grouping L2FIB-PLATFORM-STATS-BAG {
    description "L2FIB platform statistics";

    container forward-stat {
      description "fwd stats";
      uses L2FIB-PLATFORM-STATS-UNION-BAG;
    }
  }

  grouping L2FIB-PREFIX-INFO {
    description "L2FIB PREFIX INFO";
    leaf proto {
      type uint8;
      description "The prefix protocol";
    }
    leaf prefix-length {
      type uint16;
      description "The prefix length";
    }
    leaf prefix {
      type yang:hex-string;
      description "The prefix";
    }
  }

  grouping L2FIB-MCAST-LEAF-INFO {
    description "l2fib mcast leaf info";

    container multicast-base-information {
      description "Base Information";
      uses L2FIB-BASE-INFO;
    }

    container source-prefix {
      description "Source Prefix";
      uses L2FIB-PREFIX-INFO;
    }

    container destination-prefix {
      description "Destination Prefix";
      uses L2FIB-PREFIX-INFO;
    }

    container forward-stats {
      description "Forwarding Statistics";
      uses L2FIB-PLATFORM-STATS-BAG;
    }

    container irb-info {
      description "IRB Information";
      uses L2FIB-MCAST-IRB-INFO;
    }
    leaf bridge-id {
      type uint32;
      description "Bridge ID";
    }
    leaf xid-count {
      type uint16;
      description "Count of XIDs";
    }
    leaf platform-data-length {
      type uint8;
      description "The mcast platform data len";
    }
    leaf platform-data {
      type yang:hex-string;
      description "The mcast platform data";
    }
    leaf hardware-information {
      type yang:hex-string;
      description "Platform Hardware info";
    }
    leaf bridge-domain-name {
      type string {
        length "0..66";
      }
      description "Bridge Name";
    }
  }

  grouping L2FIB-GBL-RTD-ITEM {
    description "Round-trip delay for PD calls per action";
    leaf number-pd-update {
      type uint32;
      description "The number of time PD is called";
    }
    leaf number-pd-update-zero {
      type uint32;
      description "The number of time PD is called in 0 time";
    }
    leaf minimum-round-trip-delay {
      type uint64;
      description "The minimum round trip delay";
    }
    leaf maximum-round-trip-delay {
      type uint64;
      description "The maximum round trip delay";
    }
    leaf average-round-trip-delay {
      type uint64;
      description "The average round trip delay";
    }
  }

  grouping L2FIB-GBL-RTD {
    description "Round-trip delay measurement";

    container bdxc-rtd {
      description "bdxc rtd";
      uses L2FIB-GBL-RTD-ITEM;
    }

    container aging-rtd {
      description "aging rtd";
      uses L2FIB-GBL-RTD-ITEM;
    }

    container punt-rtd {
      description "punt rtd";
      uses L2FIB-GBL-RTD-ITEM;
    }

    container lock-rtd {
      description "lock rtd";
      uses L2FIB-GBL-RTD-ITEM;
    }

    container platform-init-rtd {
      description "platform init rtd";
      uses L2FIB-GBL-RTD-ITEM;
    }
    leaf rtd-max-obj-type {
      type uint32;
      description "RTD MAX OBJTYPE";
    }

    list create {
      max-elements "51";
      description "create";
      uses L2FIB-GBL-RTD-ITEM;
    }

    list modify {
      max-elements "51";
      description "modify";
      uses L2FIB-GBL-RTD-ITEM;
    }

    list delete {
      max-elements "51";
      description "delete";
      uses L2FIB-GBL-RTD-ITEM;
    }

    list bind {
      max-elements "51";
      description "bind";
      uses L2FIB-GBL-RTD-ITEM;
    }

    list unbind {
      max-elements "51";
      description "unbind";
      uses L2FIB-GBL-RTD-ITEM;
    }

    list mac-flush {
      max-elements "51";
      description "mac flush";
      uses L2FIB-GBL-RTD-ITEM;
    }

    list pirtd {
      max-elements "51";
      description "pirtd";
      uses L2FIB-GBL-RTD-ITEM;
    }
  }

  grouping L2FIB-EVT-ENTRY {
    description "L2FIB event item";
    leaf event-time {
      type string {
        length "0..32";
      }
      description "The real timestamp of the event";
    }
    leaf event-type {
      type uint8;
      description "Event type";
    }
    leaf event-many {
      type boolean;
      description "Multiple event instance flag";
    }
    leaf event-sticky {
      type boolean;
      description "Unwrittable flag";
    }
    leaf event-flags {
      type uint32;
      description "base flag object";
    }
  }

  grouping L2FIB-GBL-EVT-HISTORY {
    description "L2FIB global event history";
    leaf event-neighbor-entry {
      type uint16;
      description "number of item in the array";
    }
    list extra-information1 {
      max-elements "256";

      description "extra information1";
        leaf entry {
                  type uint32;
        }
    }
    list extra-information2 {
      max-elements "256";

      description "extra information2";
        leaf entry {
                  type uint32;
        }
    }

    list event-entry {
      max-elements "256";
      description "event entry";
      uses L2FIB-EVT-ENTRY;
    }
  }

  grouping L2FIB-EXT-MSG-SUMMARY-INFO {
    description "L2FIB message counters summary info";

    container event-history {
      description "Event history buffer";
      uses L2FIB-GBL-EVT-HISTORY;
    }

    container round-trip-delay {
      description "Round-Trip delay";
      uses L2FIB-GBL-RTD;
    }

    list message {
      max-elements "87";
      description "message";
      uses L2FIB-GBL-MSG-INFO;
    }
  }

  grouping L2FIB-GBL-MSG-INFO {
    description "L2FIB message counter item info";
    leaf messgae-count {
      type uint32;
      description "number of message";
    }
    leaf time {
      type string {
        length "0..32";
      }
      description "Time string";
    }
    leaf information1 {
      type uint32;
      description "Extra info 1";
    }
    leaf information2 {
      type uint32;
      description "Extra info 2";
    }
  }

  grouping L2FIB-MCAST-SUMMARY-INFO {
    description "l2fib mcast summary info";
    leaf bridge-domain-name {
      type string {
        length "0..66";
      }
      description "Bridge Name";
    }
    leaf bridge-domain-id {
      type uint32;
      description "Bridge ID";
    }
    leaf multicast-update {
      type uint32;
      description "Multicast Updates";
    }
    leaf multicast-update-dropped {
      type uint32;
      description "Multicast Updates";
    }
    leaf number-of-routes {
      type uint32;
      description "Number of Routes";
    }
    leaf number-of-routes-with-ole-offload {
      type uint32;
      description "Number of Routes with OleOffload";
    }
    leaf number-of-mroute-add {
      type uint32;
      description "Number of Mroutes Added";
    }
    leaf number-mroute-deleted {
      type uint32;
      description "Number of Mroutes Deleted";
    }
    leaf number-mroutes-deleted-all {
      type uint32;
      description "Number of Mroutes All Deleted";
    }
    leaf number-mroute-delete-drop {
      type uint32;
      description "Number of Mroutes Delete droped";
    }
    leaf number-mroute-all-delete-drop {
      type uint32;
      description "Number of Mroutes All Delete droped";
    }
    leaf number-xid-add {
      type uint32;
      description "Number of XID Added";
    }
    leaf number-xid-deleted {
      type uint32;
      description "Number of XID Deleted";
    }
    leaf number-of-xid {
      type uint32;
      description "Number of XIDs";
    }
    leaf stale-deleted {
      type uint32;
      description "Stale Deleted";
    }
    leaf stale-xid-deleted {
      type uint32;
      description "Stale XID Deleted";
    }

    list message {
      max-elements "15";
      description "Global Message Information";
      uses L2FIB-GBL-MSG-INFO;
    }
  }

  grouping L2FIB-FXS-INFO {
    description "L2VPN FXS info";

    container base {
      description "Base Information";
      uses L2FIB-BASE-INFO;
    }
    leaf fxs-id {
      type uint32;
      description "FXS ID";
    }
    leaf segment-type {
      type uint8;
      description "Segment type";
    }
  }

  grouping L2FIB-BRIDGE-PORT-P2MP-INFO {
    description "L2FIB BRIDGE PORT P2MP INFO";
    leaf ptree-type {
      type L2vpn-ptree;
      description "P2MP ptree type";
    }
    leaf lsm-id {
      type uint32;
      description "MLDP LSM id";
    }
    leaf tunnel-id {
      type uint16;
      description "TE Tunnel Id";
    }
    leaf p2mp-id {
      type uint16;
      description "TE P2MP Id";
    }
    leaf extended-tunnel-id {
      type inet:ipv4-address;
      description "TE Extended Tunnel Id";
    }
    leaf ptree-owner-lmrib {
      type boolean;
      description "PTree Owner LMRIB";
    }
  }

  grouping L2FIB-PROFILE-INFO {
    description "L2VPN feature profile information";
    leaf profile-name {
      type string;
      description "Feature profile name";
    }
  }

  grouping L2FIB-FEATURE-UN {
    description "L2FIB FEATURE UN";

    container dhcp {
      when "../feature-type = 'l2fib-feature-dhcp-snooping'" {
        description
          "../feature_type = 'L2FIB_FEATURE_DHCP_SNOOPING'";
      }
      description "dhcp";
      uses L2FIB-PROFILE-INFO;
    }

    container igmp {
      when "../feature-type = 'l2fib-feature-igmp-snooping'" {
        description
          "../feature_type = 'L2FIB_FEATURE_IGMP_SNOOPING'";
      }
      description "igmp";
      uses L2FIB-PROFILE-INFO;
    }

    container mld {
      when "../feature-type = 'l2fib-feature-mld-snooping'" {
        description
          "../feature_type = 'L2FIB_FEATURE_MLD_SNOOPING'";
      }
      description "mld";
      uses L2FIB-PROFILE-INFO;
    }
    leaf feature-type {
      type L2fib-feature;
      description "feature type";
    }
  }

  grouping L2FIB-OPER-INFO {
    description "L2VPN common operational information";
    leaf mtu {
      type uint32;
      description "MTU";
    }
    leaf mac-aging-time {
      type uint32;
      units "minute";
      description "MAC aging time in minutes";
    }
    leaf mac-limit {
      type uint32;
      description "MAC limit";
    }
    leaf number-of-macs {
      type uint32;
      description "numberOfMacs";
    }
    leaf admin-disabled {
      type boolean;
      description "Is administratively disabled";
    }
    leaf flooding-disabled {
      type boolean;
      description "Is flooding disabled";
    }
    leaf flood-unknown-unicast-enabled {
      type boolean;
      description "Is flooding unknown unicast disabled";
    }
    leaf mac-limit-action {
      type Mgmt-l2fib-mac-limit-action;
      description "MAC limit action";
    }
    leaf mac-limit-threshold {
      type uint32;
      units "percentage";
      description "MAC limit percentage recovery threshold";
    }
    leaf mac-learning-disabled {
      type boolean;
      description "Is MAC learning disabled";
    }
    leaf mac-port-down-flush-disabled {
      type boolean;
      description "Is MAC port down flush disabled";
    }
    leaf mac-limit-notification-type {
      type Mgmt-l2fib-mac-limit-notify;
      description "MAC limit notification";
    }
    leaf is-mac-secure-enabled {
      type boolean;
      description "Is MAC Secure Enabled";
    }
    leaf is-mac-secure-logging-enabled {
      type boolean;
      description "Is MAC Secure Logging Enabled";
    }
    leaf mac-secure-action {
      type Mgmt-l2fib-mac-sec-action;
      description "MAC secure action";
    }
    leaf is-mac-secure-accept-shutdown {
      type boolean;
      description "Is MAC secure accept shutdown (BP only)";
    }
    leaf is-mac-secure-threshold-enabled {
      type boolean;
      description "Is MAC Secure Threshold Enabled";
    }
    leaf mac-aging-type {
      type boolean;
      description "MAC aging type";
    }
    leaf storm-control-unicast-enabled {
      type boolean;
      description "Is unicast storm control enabled";
    }
    leaf storm-control-broadcast-enabled {
      type boolean;
      description "Is broadcast storm control enabled";
    }
    leaf storm-control-multicast-enabled {
      type boolean;
      description "Is multicast storm control enabled";
    }
    leaf storm-control-unicast-rate-unit {
      type L2fib-storm-control-rate-unit;
      description "Storm control unicast rate unit";
    }
    leaf storm-control-broadcast-rate-unit {
      type L2fib-storm-control-rate-unit;
      description "Storm control broadcast rate unit";
    }
    leaf storm-control-multicast-rate-unit {
      type L2fib-storm-control-rate-unit;
      description "Storm control multicast rate unit";
    }
    leaf dhcp-enabled {
      type boolean;
      description "Is DHCP snooping enabled";
    }
    leaf dhcp-trusted {
      type boolean;
      description "Is DHCP trusted";
    }
    leaf is-dai-enabled {
      type boolean;
      description "Is Dynamic ARP Inspection Enabled";
    }
    leaf is-dai-addr-validation-ipv4-enabled {
      type boolean;
      description "Is DAI IPv4 Address Validation Enabled";
    }
    leaf is-dai-addr-validation-source-mac-enabled {
      type boolean;
      description "Is DAI Source MAC Address Validation Enabled";
    }
    leaf is-dai-addr-validation-destination-mac-enabled {
      type boolean;
      description "Is DAI Destination MAC Validation enabled";
    }
    leaf is-dai-logging-enabled {
      type boolean;
      description "Is DAI Logging Enabled";
    }
    leaf is-ipsg-enabled {
      type boolean;
      description "Is IP Source Guard Enabled";
    }
    leaf is-ipsg-logging-enabled {
      type boolean;
      description "Is IP Source Guard Logging Enabled";
    }
    leaf is-vpls-flood-optimization-enabled {
      type boolean;
      description "Is MMRP  Flood Optimization Enabled";
    }
    leaf igmp-snoop-enabled {
      type boolean;
      description "Is IGMP snooping enabled";
    }
    leaf igmp-snoop-profile-enabled {
      type boolean;
      description "Is IGMP snooping profile enabled";
    }
    leaf igmp-flood-forward-enabled {
      type boolean;
      description "Is IGMP flood forwarding enabled";
    }
    leaf igmp-mroute-port-enabled {
      type boolean;
      description "Is mrouter port";
    }
    leaf igmp-route-guard-enabled {
      type boolean;
      description "Is router gurad enabled";
    }
    leaf mld-snoop-enabled {
      type boolean;
      description "Is MLD snooping enabled";
    }
    leaf mld-snoop-profile-enabled {
      type boolean;
      description "Is MLD snooping profile enabled";
    }
    leaf mld-flood-forward-enabled {
      type boolean;
      description "Is MLD flood forwarding enabled";
    }
    leaf mld-mroute-port-enabled {
      type boolean;
      description "Is mrouter port";
    }
    leaf mld-route-guard-enabled {
      type boolean;
      description "Is router gurad enabled";
    }
    leaf stp-participating {
      type boolean;
      description "Is Spanning Tree Protocol participating";
    }
    leaf bvi-configured {
      type boolean;
      description "Is BVI Interface configured";
    }
    leaf is-bvi-up {
      type boolean;
      description "Is BVI state UP";
    }
    leaf is-vni-enabled {
      type boolean;
      description "Is VNI enabled";
    }
    leaf is-evpn-enabled {
      type boolean;
      description "Is EVPN enabled";
    }
    leaf unknown-unicast-flooding-disabled {
      type boolean;
      description "Unknown Unicast Flooding is disabled";
    }
    leaf is-pbbevpn-enabled {
      type boolean;
      description "Is PBBEVPN enabled";
    }
    leaf is-swmac-learning {
      type boolean;
      description "Is SW MAC learning enabled";
    }
    leaf is-evpn-flow-label {
      type boolean;
      description "Is EVPN Flow Label enabled";
    }
    leaf is-evpn-cw-disable {
      type boolean;
      description "Is EVPN CW disabled";
    }
    leaf msti {
      type uint32;
      description "Multi-spanning tree instance";
    }
    leaf is-p2mp-pw-enabled {
      type boolean;
      description "Is P2MP PW enabled";
    }
    leaf is-igmp-snoop-enabled {
      type boolean;
      description "Is IGMP Snooping admin enabled";
    }
    leaf nv-satellite-offload-ipv4-multicast-disabled {
      type boolean;
      description "nV Satellite Offload IPv4 Multicast Disabled";
    }

    list feature {
      description "Feature information";
      uses L2FIB-FEATURE-UN;
    }
  }

  grouping L2FIB-OPER-BRIDGE-PORT-INFO {
    description "L2VPN bridge port operational information";

    container operational-information {
      description "L2 operational information";
      uses L2FIB-OPER-INFO;
    }
    leaf unicast-storm-control-pps {
      type uint64;
      description "Unicast storm control pps";
    }
    leaf unicast-storm-control-kb-ps {
      type uint64;
      units "kbit/s";
      description "Unicast storm control kbps";
    }
    leaf broadcast-storm-control-pps {
      type uint64;
      description "Broadcast storm control pps";
    }
    leaf broadcast-storm-control-kb-ps {
      type uint64;
      units "kbit/s";
      description "Broadcast storm control kbps";
    }
    leaf multicast-storm-control-pps {
      type uint64;
      description "Multicast storm control pps";
    }
    leaf multicast-storm-control-kb-ps {
      type uint64;
      units "kbit/s";
      description "Multicast storm control kbps";
    }
  }

  grouping L2FIB-BRIDGE-PORT-INFO {
    description "L2VPN bridge port info";

    container base {
      description "Base Information";
      uses L2FIB-BASE-INFO;
    }

    container oper {
      description "Operational information";
      uses L2FIB-OPER-BRIDGE-PORT-INFO;
    }

    container p2mp {
      description "BP P2MP PW Information";
      uses L2FIB-BRIDGE-PORT-P2MP-INFO;
    }
    leaf bridge-id {
      type uint32;
      description "Bridge ID";
    }
    leaf shg-id {
      type uint32;
      description "Split horizon group ID";
    }
    leaf msti-pointer {
      type uint32;
      description "MSTI Pointer";
    }
    leaf segment-type {
      type uint8;
      description "Segment type";
    }
    leaf mvrp-sequence-number {
      type uint16;
      description "MVRP Sequence Number";
    }
    leaf learn-key {
      type uint8;
      description "Learn Key";
    }
  }

  grouping L2FIB-SEG2-UN {
    description "L2FIB SEG2 UN";

    container ac {
      when "../data-type = 'mgmt-l2fib-data-type-ac'" {
        description "../DataType = 'MGMT_L2FIB_DATA_TYPE_AC'";
      }
      description "ac";
      uses L2FIB-AC-INFO;
    }

    container bp {
      when "../data-type = 'mgmt-l2fib-data-type-bridge-port'" {
        description
          "../DataType =
          'MGMT_L2FIB_DATA_TYPE_BRIDGE_PORT'";
      }
      description "bp";
      uses L2FIB-BRIDGE-PORT-INFO;
    }

    container fxs {
      when "../data-type = 'mgmt-l2fib-data-type-fxs'" {
        description "../DataType = 'MGMT_L2FIB_DATA_TYPE_FXS'";
      }
      description "fxs";
      uses L2FIB-FXS-INFO;
    }

    container pw {
      when "../data-type != 'mgmt-l2fib-data-type-ac' and"+
        " ../data-type != 'mgmt-l2fib-data-type-bridge-port' and"+
        " ../data-type != 'mgmt-l2fib-data-type-fxs'" {
          description
            "../DataType != 'MGMT_L2FIB_DATA_TYPE_AC' and .
            ./DataType !=
            'MGMT_L2FIB_DATA_TYPE_BRIDGE_PORT' and .
            ./DataType != 'MGMT_L2FIB_DATA_TYPE_FXS'";
      }
      description "pw";
      uses L2FIB-PW-INFO;
    }
    leaf data-type {
      type Mgmt-l2fib-data;
      description "DataType";
    }
  }

  grouping L2FIB-BACKUP-PW-INFO {
    description "L2FIB BACKUP PW INFO";

    container atom {
      description "atom";
      uses L2FIB-PW-MPLS-INFO;
    }
    leaf backup-next-hop {
      type inet:ipv4-address;
      description "Backup Next Hop";
    }
    leaf backup-pseudo-wire-id-type {
      type L2fib-pw-id;
      description "Pseudowire ID type";
    }
    leaf backup-pseudo-wire-id {
      type uint32;
      description "Backup Pseudowire ID";
    }
    leaf redundancy-role {
      type L2fib-pw-redundancy-role;
      description "Redundancy Role";
    }
    leaf active {
      type boolean;
      description "PW is active and forwarding";
    }
    leaf bound {
      type boolean;
      description "Bound";
    }
    leaf pw-flow-label-tx {
      type boolean;
      description "Pseudowire flow label TX enabled";
    }
    leaf grouping-supported {
      type boolean;
      description "Grouping supported";
    }
    leaf group-id {
      type uint32;
      description "PW Group Id";
    }
    leaf group-state {
      type L2fib-group-state;
      description "Group State";
    }
  }

  grouping L2FIB-PW-L2TP-IPV6-TS-SESS-INFO {
    description "L2FIB PW L2TP IPV6 TS SESS INFO";
    leaf cookie-size {
      type uint8;
      description "Cookie size";
    }
    leaf cookie-low-value {
      type uint32;
      description "Cookie low value";
    }
    leaf cookie-high-value {
      type uint32;
      description "Cookie high value";
    }
    leaf secondary-cookie-size {
      type uint8;
      description "Secondary Cookie size";
    }
    leaf secondary-cookie-low-value {
      type uint32;
      description "Secondary Cookie low value";
    }
    leaf secondary-cookie-high-value {
      type uint32;
      description "Secondary Cookie high value";
    }
    leaf session-id {
      type uint32;
      description "L2TP session ID";
    }
  }

  grouping L2FIB-PW-L2TP-IPV6-TS-INFO {
    description "L2FIB PW L2TP IPV6 TS INFO";

    container local {
      description "Local session info";
      uses L2FIB-PW-L2TP-IPV6-TS-SESS-INFO;
    }

    container remote {
      description "Remote session info";
      uses L2FIB-PW-L2TP-SESS-INFO;
    }
    leaf tos-val {
      type uint8;
      description "TOS val";
    }
    leaf ttl {
      type uint8;
      description "TTL";
    }
    leaf path-mtu {
      type uint16;
      description "Path MTU";
    }
    leaf sequence-number-sent {
      type uint32;
      description "Number of sequence sent";
    }
    leaf sequence-number-expected {
      type uint32;
      description "Number of sequence expected";
    }
    leaf local-address {
      type inet:ipv6-address;
      description "Local address";
    }
    leaf remote-address {
      type inet:ipv6-address;
      description "Remote address";
    }
  }

  grouping L2FIB-PW-L2TPV2-SESS-INFO {
    description "L2FIB PW L2TPV2 SESS INFO";
    leaf session-id {
      type uint32;
      description "L2TPv2 session ID";
    }
    leaf tunnel-id {
      type uint32;
      description "L2TPv2 tunnel ID";
    }
  }

  grouping L2FIB-PW-L2TPV2-INFO {
    description "L2FIB PW L2TPV2 INFO";

    container local {
      description "Local session info";
      uses L2FIB-PW-L2TPV2-SESS-INFO;
    }

    container remote {
      description "Remote session info";
      uses L2FIB-PW-L2TPV2-SESS-INFO;
    }
    leaf pw-flags {
      type uint8;
      description "L2TPv2 PW flags";
    }
    leaf tos-val {
      type uint8;
      description "TOS val";
    }
    leaf ttl {
      type uint8;
      description "TTL [Hops number]";
    }
    leaf path-mtu {
      type uint16;
      units "byte";
      description "Path MTU [Bytes]";
    }
    leaf protocol {
      type uint16;
      description "Protocol [UDP RFC-768]";
    }
    leaf rem-udp-port {
      type uint16;
      description "Remote UDP Port";
    }
    leaf xconnect-id {
      type uint32;
      description "Xconnect ID";
    }
    leaf next-hop-address {
      type inet:ipv4-address;
      description "Next Hop Address";
    }
    leaf source-address {
      type inet:ipv4-address;
      description "Source Address";
    }
  }

  grouping L2FIB-PW-L2TP-SESS-INFO {
    description "L2FIB PW L2TP SESS INFO";
    leaf session-id {
      type uint32;
      description "L2TP session ID";
    }
    leaf cookie-size {
      type uint8;
      description "Cookie size";
    }
    leaf cookie-low-value {
      type uint32;
      description "Cookie low value";
    }
    leaf cookie-high-value {
      type uint32;
      description "Cookie high value";
    }
  }

  grouping L2FIB-PW-L2TP-INFO {
    description "L2FIB PW L2TP INFO";

    container local {
      description "Local session info";
      uses L2FIB-PW-L2TP-SESS-INFO;
    }

    container remote {
      description "Remote session info";
      uses L2FIB-PW-L2TP-SESS-INFO;
    }
    leaf tos-val {
      type uint8;
      description "TOS val";
    }
    leaf ttl {
      type uint8;
      description "TTL";
    }
    leaf path-mtu {
      type uint16;
      description "Path MTU";
    }
    leaf sequence-number-sent {
      type uint32;
      description "Number of sequence sent";
    }
    leaf sequence-number-expected {
      type uint32;
      description "Number of sequence expected";
    }
  }

  grouping L2FIB-PW-MPLS-INFO {
    description "L2FIB PW MPLS INFO";
    leaf pw-label {
      type uint32;
      description "PW Label";
    }
    leaf pw-local-label {
      type uint32;
      description "Local PW Label";
    }
    leaf pw-tunnel-interface {
      type uint32;
      description "PW tunnel interface";
    }
    leaf pw-xcid {
      type uint32;
      description "PW XCID";
    }
  }

  grouping L2FIB-PW-UN {
    description "L2FIB PW UN";

    container mpls {
      when "../data-type = 'mgmt-l2fib-data-type-atom'" {
        description "../DataType = 'MGMT_L2FIB_DATA_TYPE_ATOM'";
      }
      description "mpls";
      uses L2FIB-PW-MPLS-INFO;
    }

    container l2tp {
      when "../data-type = 'mgmt-l2fib-data-type-l2tp'" {
        description "../DataType = 'MGMT_L2FIB_DATA_TYPE_L2TP'";
      }
      description "l2tp";
      uses L2FIB-PW-L2TP-INFO;
    }

    container l2tpv2 {
      when "../data-type = 'mgmt-l2fib-data-type-l2tpv2'" {
        description "../DataType = 'MGMT_L2FIB_DATA_TYPE_L2TPV2'";
      }
      description "l2tpv2";
      uses L2FIB-PW-L2TPV2-INFO;
    }

    container l2tp-ipv6-ts {
      when "../data-type = 'mgmt-l2fib-data-type-l2tp-ipv6-ts'" {
        description
          "../DataType =
          'MGMT_L2FIB_DATA_TYPE_L2TP_IPV6_TS'";
      }
      description "l2tp ipv6 ts";
      uses L2FIB-PW-L2TP-IPV6-TS-INFO;
    }
    leaf data-type {
      type Mgmt-l2fib-data;
      description "DataType";
    }
  }

  grouping L2FIB-PW-INFO {
    description "L2FIB PW INFO";

    container base {
      description "Base Information";
      uses L2FIB-BASE-INFO;
    }

    container next-hop {
      description "Next Hop";
      uses L2FIB-NHOP-INFO;
    }

    container pseudo-wire-union {
      description "Union of MPLS or L2TP";
      uses L2FIB-PW-UN;
    }

    container backup-pseudo-wire {
      description "Backup Pseudowire";
      uses L2FIB-BACKUP-PW-INFO;
    }
    leaf pw-id {
      type uint64;
      description "Pseudowire ID";
    }
    leaf signal-capability-flags {
      type uint32;
      description "Sig Capability flags";
    }
    leaf context {
      type uint16;
      description "Context";
    }
    leaf sequence-resync-threshold {
      type uint16;
      description "Sequence Resync Threshold";
    }
    leaf bound {
      type boolean;
      description "Bound";
    }
    leaf next-hop-valid {
      type boolean;
      description "IS Next Hop Valid";
    }
    leaf backup-configured {
      type boolean;
      description "Backup Pseudowire Configured";
    }
    leaf redundancy-role {
      type L2fib-pw-redundancy-role;
      description "Redundancy Role";
    }
    leaf active {
      type boolean;
      description "PW is active and forwarding";
    }
    leaf pseudo-wire-id-type {
      type L2fib-pw-id;
      description "Pseudowire ID type";
    }
    leaf pw-load-balance-type {
      type L2fib-load-bal;
      description "Type of load-balancing";
    }
    leaf pw-flow-label-tx {
      type boolean;
      description "Pseudowire flow label TX enabled";
    }
    leaf grouping-supported {
      type boolean;
      description "Grouping supported";
    }
    leaf group-id {
      type uint32;
      description "PW Group Id";
    }
    leaf group-state {
      type L2fib-group-state;
      description "Group State";
    }
    leaf global-id {
      type uint32;
      description "Global Id";
    }
    leaf ac-id {
      type uint32;
      description "Ac Id";
    }
    leaf forward-class {
      type uint8;
      description "Forward Class";
    }
    leaf next-hop-address {
      type inet:ipv4-address;
      description "Next Hop Address";
    }
  }

  grouping L2FIB-MONITOR-SESSION-INFO {
    description "L2FIB MONITOR SESSION INFO";

    container base {
      description "Base Information";
      uses L2FIB-BASE-INFO;
    }
    leaf xcid {
      type uint32;
      description "Xconnect ID";
    }
    leaf session-name {
      type string;
      description "Monitor Session Name";
    }
    leaf hardware-information {
      type yang:hex-string;
      description "hardware Information of Monitor Session";
    }
    leaf bound {
      type boolean;
      description "Bound";
    }
  }

  grouping L2FIB-EVPN-INFO {
    description "L2FIB EVPN INFO";

    container base {
      description "Base Information";
      uses L2FIB-BASE-INFO;
    }
    leaf bound {
      type boolean;
      description "Bound";
    }
    leaf evi {
      type uint32;
      description "EVPN ID";
    }
    leaf forward-class {
      type uint8;
      description "Forward Class";
    }
  }

  grouping L2FIB-VNI-INFO {
    description "L2FIB VNI INFO";

    container base {
      description "Base Information";
      uses L2FIB-BASE-INFO;
    }
    leaf srcip {
      type inet:ipv4-address;
      description "VNI Src IPv4 Address";
    }
    leaf mcastip {
      type inet:ipv4-address;
      description "VNI Mcast IP Address";
    }
    leaf bound {
      type boolean;
      description "Bound";
    }
    leaf parent-if {
      type xr:Interface-name;
      description "Parent NVE Interface";
    }
    leaf encap {
      type uint32;
      description "Encap type of VNI";
    }
    leaf udp-port {
      type uint32;
      description "UDP Port";
    }
    leaf source-vtep-if {
      type xr:Interface-name;
      description "Source IF Handle";
    }
    leaf any-cast-ip {
      type inet:ipv4-address;
      description "Anycast VTEP IP";
    }
    leaf anycast-mcast-ip {
      type inet:ipv4-address;
      description "Anycast Multicast IP";
    }
    leaf ingress-replication {
      type boolean;
      description "Ingress Replication supported on VNI";
    }
    leaf vx-lan-mode {
      type uint32;
      description "Vxlan mode";
    }
  }

  grouping L2FIB-PBB-CORE-INFO {
    description "L2FIB PBB CORE INFO";
    leaf vlan-id {
      type uint32;
      description "vlan id";
    }
  }

  grouping L2FIB-PBB-EDGE-INFO {
    description "L2FIB PBB EDGE INFO";
    leaf mac-configured {
      type boolean;
      description "Configured MAC";
    }
    leaf mac {
      type yang:mac-address;
      description "unknown unicast bmac";
    }
  }

  grouping L2FIB-PBB-UN {
    description "L2FIB PBB UN";

    container edge {
      when "../pbb-type = 'mgmt-l2fib-bridge-type-pbb-edge'" {
        description
          "../PbbType = 'MGMT_L2FIB_BRIDGE_TYPE_PBB_EDGE'";
      }
      description "edge";
      uses L2FIB-PBB-EDGE-INFO;
    }

    container core {
      when "../pbb-type = 'mgmt-l2fib-bridge-type-pbb-core'" {
        description
          "../PbbType = 'MGMT_L2FIB_BRIDGE_TYPE_PBB_CORE'";
      }
      description "core";
      uses L2FIB-PBB-CORE-INFO;
    }
    leaf pbb-type {
      type Mgmt-l2fib-bridge;
      description "PbbType";
    }
  }

  grouping L2FIB-PBB-INFO {
    description "L2FIB PBB INFO";

    container base {
      description "Base Information";
      uses L2FIB-BASE-INFO;
    }

    container pbb-union {
      description "Union of Edge and Core";
      uses L2FIB-PBB-UN;
    }
    leaf bound {
      type boolean;
      description "Bound";
    }
    leaf forward-class {
      type uint8;
      description "Forward Class";
    }
    leaf core-pbb-evpn-enabled {
      type boolean;
      description "Core PBB-EVPN enabled";
    }
  }

  grouping L2FIB-NHOP-INFO {
    description "L2FIB NHOP INFO";

    container base {
      description "Base Information";
      uses L2FIB-BASE-INFO;
    }
    leaf next-hop-address {
      type inet:ipv4-address;
      description "NHOP Address";
    }
    leaf next-hop-address-v6 {
      type inet:ipv6-address;
      description "NHOP Address V6";
    }
    leaf next-hop-internal-label {
      type uint32;
      description "NHOP Internal Label";
    }
    leaf ecd-plaformt-data-valid {
      type boolean;
      description "Is Platform ECD Data Valid";
    }
    leaf ecd-platform-data-length {
      type uint32;
      description "Platform ECD Data Length";
    }
    leaf children-count {
      type uint32;
      description "Children Count";
    }
  }

  grouping L2FIB-AC-INFO {
    description "L2FIB AC INFO";

    container base {
      description "Base Information";
      uses L2FIB-BASE-INFO;
    }

    container fxc-next-hop {
      description "Flexible XConnect Service Next Hop";
      uses L2FIB-NHOP-INFO;
    }
    leaf interface-handle {
      type xr:Interface-name;
      description "Interface Handle";
    }
    leaf sub-interface-handle {
      type xr:Interface-name;
      description "Sub Interface Handle";
    }
    leaf attachment-circuit-id {
      type uint32;
      description "Attachment Circuit ID";
    }
    leaf attachment-circuit-mtu {
      type uint16;
      description "MTU of Attachment Circuit";
    }
    leaf actype {
      type uint8;
      description "Attachment Circuit Type";
    }
    leaf inter-working-mode {
      type uint8;
      description "Interworking Mode";
    }
    leaf adjacency-valid {
      type boolean;
      description "Adjacency Valid";
    }
    leaf adjacency-address {
      type inet:ipv4-address;
      description "Adjacency Valid";
    }
    leaf bound {
      type boolean;
      description "Bound";
    }
    leaf ip-inter-working-mac {
      type string;
      description "IP Interworking MAC";
    }
    leaf redundancy-group-id {
      type uint32;
      description "ICCP Redundancy Group ID";
    }
    leaf redundancy-object-id {
      type uint64;
      description "ICCP Redundancy Object ID";
    }
    leaf evpn-internal-label {
      type uint32;
      description "EVPN Internal Label";
    }
    leaf fxc-next-hop-valid {
      type boolean;
      description "Is Flexible XConnect Service Next Hop Valid";
    }
  }

  grouping L2FIB-SEG1-UN {
    description "L2FIB SEG1 UN";

    container ac {
      when "../data-type = 'mgmt-l2fib-data-type-ac'" {
        description "../DataType = 'MGMT_L2FIB_DATA_TYPE_AC'";
      }
      description "ac";
      uses L2FIB-AC-INFO;
    }

    container pbb {
      when "../data-type = 'mgmt-l2fib-data-type-pbb'" {
        description "../DataType = 'MGMT_L2FIB_DATA_TYPE_PBB'";
      }
      description "pbb";
      uses L2FIB-PBB-INFO;
    }

    container vni {
      when "../data-type = 'mgmt-l2fib-data-type-vni'" {
        description "../DataType = 'MGMT_L2FIB_DATA_TYPE_VNI'";
      }
      description "vni";
      uses L2FIB-VNI-INFO;
    }

    container evpn {
      when "../data-type = 'mgmt-l2fib-data-type-evpn'" {
        description "../DataType = 'MGMT_L2FIB_DATA_TYPE_EVPN'";
      }
      description "evpn";
      uses L2FIB-EVPN-INFO;
    }

    container monitor-session {
      when "../data-type = 'mgmt-l2fib-data-type-span'" {
        description "../DataType = 'MGMT_L2FIB_DATA_TYPE_SPAN'";
      }
      description "monitor session";
      uses L2FIB-MONITOR-SESSION-INFO;
    }

    container pw {
      when "../data-type != 'mgmt-l2fib-data-type-ac' and"+
        " ../data-type != 'mgmt-l2fib-data-type-pbb' and"+
        " ../data-type != 'mgmt-l2fib-data-type-vni' and"+
        " ../data-type != 'mgmt-l2fib-data-type-evpn' and"+
        " ../data-type != 'mgmt-l2fib-data-type-span'" {
          description
            "../DataType != 'MGMT_L2FIB_DATA_TYPE_AC' and .
            ./DataType != 'MGMT_L2FIB_DATA_TYPE_PBB' and .
            ./DataType != 'MGMT_L2FIB_DATA_TYPE_VNI' and .
            ./DataType != 'MGMT_L2FIB_DATA_TYPE_EVPN' and 
            ../DataType != 'MGMT_L2FIB_DATA_TYPE_SPAN'";
      }
      description "pw";
      uses L2FIB-PW-INFO;
    }
    leaf data-type {
      type Mgmt-l2fib-data;
      description "DataType";
    }
  }

  grouping L2FIB-BASE-INFO {
    description "L2FIB BASE INFO";
  }

  grouping L2FIB-XCON-INFO {
    description "L2FIB XCON INFO";

    container base {
      description "Base Information";
      uses L2FIB-BASE-INFO;
    }

    container segment1 {
      description "Segment1 Information";
      uses L2FIB-SEG1-UN;
    }

    container segment2 {
      description "Segment2 Information";
      uses L2FIB-SEG2-UN;
    }
    leaf xcon-name {
      type string {
        length "0..72";
      }
      description "Xconnect name";
    }
    leaf bound {
      type boolean;
      description "Bound";
    }
    leaf switching-type {
      type Mgmt-l2fib-switching;
      description "SW Type";
    }
  }
}
