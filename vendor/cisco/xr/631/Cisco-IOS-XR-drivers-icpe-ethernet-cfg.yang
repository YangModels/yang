module Cisco-IOS-XR-drivers-icpe-ethernet-cfg {

  /*** NAMESPACE / PREFIX DEFINITION ***/

  namespace "http://cisco.com/ns/yang"+
    "/Cisco-IOS-XR-drivers-icpe-ethernet-cfg";


  prefix "drivers-icpe-ethernet-cfg";

  /*** LINKAGE (IMPORTS / INCLUDES) ***/

  import Cisco-IOS-XR-ifmgr-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR drivers-icpe-ethernet package configuration.

     This YANG module augments the
       Cisco-IOS-XR-ifmgr-cfg
     module with configuration data.

     Copyright (c) 2013-2017 by Cisco Systems, Inc.
     All rights reserved.";

  revision "2015-11-09" {
    description
      "IOS XR 6.0 revision.";
  }

  typedef Extended-ethernet-loopback {
    type enumeration {
      enum internal {
        value 1;
        description "Internal loopback";
      }
      enum line {
        value 2;
        description "Line loopback";
      }
    }
    description "Extended ethernet loopback";
  }

  augment "/a1:interface-configurations/a1:interface-configuration" {
    leaf laser-squelch {
      type empty;
      description "Configure Laser-Squelch";
    }
    description
      "This augment extends the configuration data of
      'Cisco-IOS-XR-ifmgr-cfg'";
  }

  augment "/a1:interface-configurations/a1:interface-configuration" {

    container loopbacks {
      description "Configure Extended loopback (diagnostics)";

      list loopback {
        key "level";
        description "Configure extended loopback mode";
        leaf level {
          type uint32 {
            range "1..3";
          }
          description "Level";
        }
        leaf loopback {
          type Extended-ethernet-loopback;
          mandatory true;
          description "Loopback";
        }
      }
    }
    description
      "This augment extends the configuration data of
      'Cisco-IOS-XR-ifmgr-cfg'";
  }

  augment "/a1:interface-configurations/a1:interface-configuration" {
    leaf perf-mon-disable {
      type empty;
      description "Configure Performance Monitoring ";
    }
    description
      "This augment extends the configuration data of
      'Cisco-IOS-XR-ifmgr-cfg'";
  }
}
