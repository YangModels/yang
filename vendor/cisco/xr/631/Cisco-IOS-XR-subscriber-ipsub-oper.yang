module Cisco-IOS-XR-subscriber-ipsub-oper {

  /*** NAMESPACE / PREFIX DEFINITION ***/

  namespace "http://cisco.com/ns/yang"+
    "/Cisco-IOS-XR-subscriber-ipsub-oper";


  prefix "subscriber-ipsub-oper";

  /*** LINKAGE (IMPORTS / INCLUDES) ***/

  import Cisco-IOS-XR-types { prefix "xr"; }

  include Cisco-IOS-XR-subscriber-ipsub-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR subscriber-ipsub package operational data.

     This module contains definitions
     for the following management objects:
       ip-subscriber: IP subscriber operational data

     Copyright (c) 2013-2017 by Cisco Systems, Inc.
     All rights reserved.";

  revision "2015-11-09" {
    description
      "IOS XR 6.0 revision.";
  }


  container ip-subscriber {
    config false;
    description "IP subscriber operational data";

    container nodes {
      description
        "IP subscriber operational data for a particular
        location";

      list node {
        key "node-name";
        description "Location. For eg., 0/1/CPU0";

        container summary {
          description "IP subscriber interface summary";
          uses IPSUB-MA-INTF-SUMMARY-DATA;
        }

        container interfaces {
          description "IP subscriber interface table";

          list interface {
            key "interface-name";
            description "IP subscriber interface entry";
            leaf interface-name {
              type xr:Interface-name;
              description "Interface name";
            }
            uses IPSUB-MA-INTF-DATA;
          }
        }

        container access-interfaces {
          description "IP subscriber access interface table";

          list access-interface {
            key "interface-name";
            description "IP subscriber access interface entry";
            leaf interface-name {
              type xr:Interface-name;
              description "Interface name";
            }
            uses IPSUB-MA-PARENT-INTF-DATA;
          }
        }
        leaf node-name {
          type xr:Node-id;
          description "The node ID to filter on. For eg., 0/1/CPU0";
        }
      }
    }
  }
}
