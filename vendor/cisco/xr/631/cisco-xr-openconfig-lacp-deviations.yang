module cisco-xr-openconfig-lacp-deviations {

  prefix  "lacpdevs";

  namespace "http://cisco.com/ns/yang/cisco-xr-openconfig-lacp-deviations";

  // import some basic types
  import openconfig-lacp { prefix oc-lacp; }

  organization "Cisco Systems, Inc.";

  contact
    "Cisco Systems, Inc.
     Customer Service

     Postal: 170 West Tasman Drive
     San Jose, CA 95134

     Tel: +1 800 553-NETS

     E-mail: cs-yang@cisco.com";

  description
    "This module contains a set of deviations for 
 
     openconfig-if-aggregate.yang@2015-11-20 

     on Cisco IOS-XR devices.

     Copyright (c) 2016-2017 by Cisco Systems, Inc.
     All rights reserved.";

  revision "2016-05-16" {
    description
      "Initial revision applicable to IOS-XR 6.1.1";
  }

  deviation /oc-lacp:lacp/oc-lacp:interfaces/oc-lacp:interface/oc-lacp:members/oc-lacp:member/oc-lacp:state/oc-lacp:counters/oc-lacp:lacp-tx-errors {
    deviate not-supported;
  }

}
//total deviations:1
