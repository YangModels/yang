module Cisco-IOS-XR-tunnel-nve-cfg {

  /*** NAMESPACE / PREFIX DEFINITION ***/

  namespace "http://cisco.com/ns/yang/Cisco-IOS-XR-tunnel-nve-cfg";


  prefix "tunnel-nve-cfg";

  /*** LINKAGE (IMPORTS / INCLUDES) ***/

  import ietf-inet-types { prefix "inet"; }

  import Cisco-IOS-XR-ifmgr-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR tunnel-nve package configuration.

     This YANG module augments the
       Cisco-IOS-XR-ifmgr-cfg
     module with configuration data.

     Copyright (c) 2013-2017 by Cisco Systems, Inc.
     All rights reserved.";

  revision "2016-08-30" {
    description
      "Initial Revision.";
  }

  revision "2015-11-09" {
    description
      "IOS XR 6.0 revision.";
  }

  typedef Host-reach-protocol {
    type enumeration {
      enum bgp {
        value 1;
        description
          "Use BGP EVPN for VxLAN tunnel endpoint
          reachability";
      }
    }
    description "Host reach protocol";
  }
  typedef Vni-range {
    type uint32 {
      range "1..16777215";
    }
    description "Vni range";
  }
  typedef Vxlan-udp-port-enum {
    type enumeration {
      enum ietf-udp-port {
        value 4789;
        description "IETF defined UDP port for VxLAN";
      }
      enum ivx-lan-udp-port {
        value 48879;
        description "UDP port for iVxLAN";
      }
    }
    description "Vxlan udp port enum";
  }
  typedef Overlay-encap-enum {
    type enumeration {
      enum vx-lan-encapsulation {
        value 0;
        description "VxLAN Encapsulation";
      }
      enum soft-gre-encapsulation {
        value 1;
        description "Soft GRE Encapsulation";
      }
    }
    description "Overlay encap enum";
  }
  typedef Unknown-unicast-flooding-enum {
    type enumeration {
      enum suppress-uuf {
        value 1;
        description "Suppress unknown unicast flooding";
      }
    }
    description "Unknown unicast flooding enum";
  }
  typedef Load-balance-enum {
    type enumeration {
      enum per-evi {
        value 1;
        description "Per evi load balance mode";
      }
    }
    description "Load balance enum";
  }
  typedef Ir-protocol-enum {
    type enumeration {
      enum bgp {
        value 1;
        description "Use BGP Protocol for Ingress-Replication";
      }
    }
    description "Ir protocol enum";
  }

  augment "/a1:interface-configurations/a1:interface-configuration" {

    container nve {
      description "NVE operational data";

      container anycast {
        description "Enable anycast mode for this NVE interface";
        leaf source-interface {
          type string;
          description "Name of the Anycast mode source interface";
        }
        leaf sync-group {
          type inet:ipv4-address-no-zone;
          description
            "MCast group for syncing between Anycast
            gateways";
        }
      }

      container redundancy {
        description "Redundancy configuration for this NVE";

        container backbone-vx-lan {
          description "VXLAN backbone";
          leaf enable {
            type empty;
            description "Enable Backbone VxLAN";
          }
          leaf backbone-vx-laniccp {
            type int32;
            description "VxLAN backbone ICCP group";
          }
        }

        container backbone-mpls {
          description "MPLS backbone";
          leaf backbone-mplsiccp {
            type int32;
            description "MPLS backbone ICCP group";
          }
          leaf enable {
            type empty;
            description "Enable Backbone MPLS";
          }
        }
        leaf enable {
          type empty;
          description "Enable Redundancy";
        }
      }

      container member-vnis {
        description "VNI configuration Table for this NVE";

        list member-vni {
          key "vni-start vni-end";
          description "VNI member attributes";

          container multicast {
            presence "enable multicast";
            description
              "Mulitcast core group range associated with
              the VxLAN segment(s)";
            leaf multicast-group-min {
              type inet:ipv4-address-no-zone;
              description "IPV4 group address of the tunnel source";
            }
            leaf multicast-group-max {
              type inet:ipv4-address-no-zone;
              description "IPV4 group address MAX";
            }
          }
          leaf host-reachability {
            type Host-reach-protocol;
            description
              "Control protocol for VxLAN tunnel endpoint
              reachability";
          }
          leaf vrf {
            type string;
            description "VRF associated with the VxLAN segment";
          }
          leaf unknown-unicast-flooding {
            type Unknown-unicast-flooding-enum;
            description "Suppression of unknown unicast flooding";
          }
          leaf load-balance-per-evi {
            type Load-balance-enum;
            description "Per-evi load balance mode";
          }
          leaf enable {
            type empty;
            description "Enable VNI";
          }
          leaf vni-start {
            type Vni-range;
            description "Single VNI or Range Start";
          }
          leaf vni-end {
            type Vni-range;
            description "Range End";
          }
        }
      }
      leaf vx-lan-udp-port {
        type Vxlan-udp-port-enum;
        default "ietf-udp-port";
        description "UDP port number in VxLAN encapsulation";
      }
      leaf overlay-encapsulation {
        type Overlay-encap-enum;
        default "vx-lan-encapsulation";
        description "The Overlay Encapsulation for this NVE";
      }
      leaf source-interface {
        type string;
        description "Source Interface for this NVE";
      }
      leaf ingress-replication-protocol {
        type Ir-protocol-enum;
        description "The Ingress Replication Protocol for this NVE";
      }
    }
    description
      "This augment extends the configuration data of
      'Cisco-IOS-XR-ifmgr-cfg'";
  }
}
