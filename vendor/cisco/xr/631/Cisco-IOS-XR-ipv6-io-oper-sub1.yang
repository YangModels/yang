submodule Cisco-IOS-XR-ipv6-io-oper-sub1 {

  belongs-to Cisco-IOS-XR-ipv6-io-oper {
    prefix Cisco-IOS-XR-ipv6-io-oper;
  }

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ipv6-io package operational data.

     Copyright (c) 2013-2017 by Cisco Systems, Inc.
     All rights reserved.";

  revision "2015-11-09" {
    description
      "IOS XR 6.0 revision.";
  }

  revision "2015-08-27" {
    description
      "IOS XR 6.0.0 revision.";
  }


  grouping IPV6-ND-TRAFFIC {
    description "IPV6 ND Traffic";
    leaf sent-router-solicitation-messages {
      type uint32;
      description "ICMP Router Solicitations Sent";
    }
    leaf sent-router-advertisement-messages {
      type uint32;
      description "ICMP Router Advertisements Sent";
    }
    leaf sent-neighbor-solicitation-messages {
      type uint32;
      description "ICMP Neighbor Solicitations Sent";
    }
    leaf sent-neighbor-advertisement-messages {
      type uint32;
      description "ICMP Neighbor Advertisements Sent";
    }
    leaf sent-redirect-messages {
      type uint32;
      description "ICMP Redirect Sent";
    }
    leaf received-router-solicitation-messages {
      type uint32;
      description "ICMP Router Solicitations Received";
    }
    leaf received-router-advertisement-messages {
      type uint32;
      description "ICMP Router Advertisements Received";
    }
    leaf received-neighbor-solicitation-messages {
      type uint32;
      description "ICMP Neighbor Solicitations Received";
    }
    leaf received-neighbor-advertisement-messages {
      type uint32;
      description "ICMP Neighbor Advertisements Received";
    }
    leaf received-redirect-messages {
      type uint32;
      description "ICMP Redirect Received";
    }
  }

  grouping IPV6-IO-ICMP-TRAFFIC {
    description "ICMPv6 Traffic Information";
    leaf total-messages {
      type uint32;
      description "ICMP Received";
    }
    leaf too-short-error-messages {
      type uint32;
      description "ICMP Too Short Errors";
    }
    leaf checksum-error-messages {
      type uint32;
      description "ICMP Checksum Errors";
    }
    leaf unknown-error-type-messages {
      type uint32;
      description "ICMP Unknown Error";
    }
    leaf output-messages {
      type uint32;
      description "ICMP Transmitted";
    }
    leaf sent-rate-limited-packets {
      type uint32;
      description "ICMP Sent Packets Ratelimited";
    }
    leaf sent-unreachable-routing-messages {
      type uint32;
      description "ICMP Route Unreachable Sent";
    }
    leaf sent-unreachable-admin-messages {
      type uint32;
      description "ICMP Admin Unreachable Sent";
    }
    leaf sent-unreachable-neighbor-messages {
      type uint32;
      description "ICMP Host Unreachable Sent";
    }
    leaf sent-unreachable-address-messages {
      type uint32;
      description "ICMP Addr Unreachable Sent";
    }
    leaf sent-unreachable-port-messages {
      type uint32;
      description "ICMP Port Unreachable Sent";
    }
    leaf received-unreachable-routing-messages {
      type uint32;
      description "ICMP Route Unreachable Received";
    }
    leaf received-unreachable-admin-messages {
      type uint32;
      description "ICMP Admin Unreachable Received";
    }
    leaf received-unreachable-neighbor-messages {
      type uint32;
      description "ICMP Host Unreachable Received";
    }
    leaf received-unreachable-address-messages {
      type uint32;
      description "ICMP Addr Unreachable Received";
    }
    leaf received-unreachable-port-messages {
      type uint32;
      description "ICMP Port Unreachable Received";
    }
    leaf sent-hop-count-expired-messages {
      type uint32;
      description "ICMP Hop Count Expired Sent";
    }
    leaf sent-reassembly-timeouts {
      type uint32;
      description "ICMP Reassembly Timeouts";
    }
    leaf received-hop-count-expired-messages {
      type uint32;
      description "ICMP Hop Count Expired Received";
    }
    leaf received-reassembly-timeouts {
      type uint32;
      description "ICMP Reassembly Timeouts";
    }
    leaf sent-too-big-messages {
      type uint32;
      description "ICMP Too Big Messages Sent";
    }
    leaf received-too-big-messages {
      type uint32;
      description "ICMP Too Big Messages Received";
    }
    leaf sent-parameter-error-messages {
      type uint32;
      description "ICMP Parameter Error Messages Sent";
    }
    leaf sent-parameter-header-messages {
      type uint32;
      description "ICMP Parameter Next Header Messages Sent";
    }
    leaf sent-parameter-option-messages {
      type uint32;
      description "ICMP Parameter Option Messages Sent";
    }
    leaf received-parameter-error-messages {
      type uint32;
      description "ICMP Parameter Error Messages Received";
    }
    leaf received-parameter-header-messages {
      type uint32;
      description "ICMP Parameter Next Header Messages Received";
    }
    leaf received-parameter-option-messages {
      type uint32;
      description "ICMP Parameter Option Problem Received";
    }
    leaf sent-echo-request-messages {
      type uint32;
      description "ICMP Echo Request Sent";
    }
    leaf sent-echo-reply-messages {
      type uint32;
      description "ICMP Echo Reply Sent";
    }
    leaf received-echo-request-messages {
      type uint32;
      description "ICMP Echo Request Received";
    }
    leaf received-echo-reply-messages {
      type uint32;
      description "ICMP Echo Reply Received";
    }
    leaf sent-unknown-timeout-messages {
      type uint32;
      description "ICMP Unknown Timeout Messages Sent";
    }
    leaf received-unknown-timeout-messages {
      type uint32;
      description "ICMP Unknown Timeout Messages Received";
    }
    leaf sent-parameter-unknown-type-messages {
      type uint32;
      description "ICMP Parameter Unknown Type Messages Sent";
    }
    leaf received-parameter-unknown-type-messages {
      type uint32;
      description "ICMP Parameter Unknown Type Messages Received";
    }
    leaf sent-unreachable-unknown-type-messages {
      type uint32;
      description "ICMP Unreachable Unknown Messages Sent";
    }
    leaf received-unreachable-unknown-type-messages {
      type uint32;
      description "ICMP Unreachable Unknown Messages Received";
    }
  }

  grouping IPV6-IO-TRAFFIC {
    description "IPv6 Traffic Information";
    leaf total-packets {
      type uint32;
      description "Total Packets";
    }
    leaf local-destination-packets {
      type uint32;
      description "Local Destination Packets";
    }
    leaf format-errors {
      type uint32;
      description "Format Errors";
    }
    leaf truncated-packets {
      type uint32;
      description "Truncated Packets";
    }
    leaf hop-count-exceeded-packets {
      type uint32;
      description "Hop Count Exceeded Packets";
    }
    leaf bad-source-address-packets {
      type uint32;
      description "Bad Source Address Packets";
    }
    leaf bad-header-packets {
      type uint32;
      description "Bad Header Packets";
    }
    leaf unknown-option-type-packets {
      type uint32;
      description "Unknown Option Type Packets";
    }
    leaf unknown-protocol-packets {
      type uint32;
      description "Unknown Protocol Packets";
    }
    leaf fragments {
      type uint32;
      description "Fragments";
    }
    leaf reassembled-packets {
      type uint32;
      description "Reassembled Packets";
    }
    leaf reassembly-timeouts {
      type uint32;
      description "Reassembly Timeouts";
    }
    leaf reassembly-failures {
      type uint32;
      description "Reassembly Failures";
    }
    leaf reassembly-maximum-drops {
      type uint32;
      description "Reassembly Reach Maximum Drop";
    }
    leaf generated-packets {
      type uint32;
      description "Packets Output";
    }
    leaf forwarded-packets {
      type uint32;
      description "Packets Forwarded";
    }
    leaf source-routed-packets {
      type uint32;
      description "Packets Source Routed";
    }
    leaf fragmented-packets {
      type uint32;
      description "Packets Fragmented";
    }
    leaf fragment-count {
      type uint32;
      description "Fragmented Packet Count";
    }
    leaf fragment-failures {
      type uint32;
      description "Fragment Failures";
    }
    leaf no-route-packets {
      type uint32;
      description "No Route Packets";
    }
    leaf too-big-packets {
      type uint32;
      description "Packet Too Big";
    }
    leaf received-multicast-packets {
      type uint32;
      description "Multicast In";
    }
    leaf sent-multicast-packets {
      type uint32;
      description "Multicast Out";
    }
    leaf miscellaneous-drops {
      type uint32;
      description "Misc. drops";
    }
    leaf lisp-v4-encap-packets {
      type uint32;
      description "Lisp IPv4 Encapped packets";
    }
    leaf lisp-v4-decap-packets {
      type uint32;
      description "Lisp IPv4 Decapped packets";
    }
    leaf lisp-v6-encap-packets {
      type uint32;
      description "Lisp IPv6 Encapped packets";
    }
    leaf lisp-v6-decap-packets {
      type uint32;
      description "Lisp IPv6 Decapped packets";
    }
    leaf lisp-encap-errors {
      type uint32;
      description "Lisp Encap errors";
    }
    leaf lisp-decap-errors {
      type uint32;
      description "Lisp Decap errors";
    }
  }

  grouping IPV6-TRAFFIC {
    description "IPv6 and ICMPv6 Traffic Information";

    container ipv6 {
      description "IPv6 Statistics";
      uses IPV6-IO-TRAFFIC;
    }

    container icmp {
      description "ICMP Statistics";
      uses IPV6-IO-ICMP-TRAFFIC;
    }

    container ipv6-node-discovery {
      description "IPv6 Node Discovery Statistics";
      uses IPV6-ND-TRAFFIC;
    }
  }
}
