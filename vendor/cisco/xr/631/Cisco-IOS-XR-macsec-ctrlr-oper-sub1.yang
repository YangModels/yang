submodule Cisco-IOS-XR-macsec-ctrlr-oper-sub1 {

  belongs-to Cisco-IOS-XR-macsec-ctrlr-oper {
    prefix Cisco-IOS-XR-macsec-ctrlr-oper;
  }

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR macsec-ctrlr package operational data.

     Copyright (c) 2013-2017 by Cisco Systems, Inc.
     All rights reserved.";

  revision "2015-11-09" {
    description
      "IOS XR 6.0 revision.";
  }

  typedef Macsec-ctrlr-ciphersuit {
    type enumeration {
      enum gcm-aes-256 {
        value 0;
        description "GCM AES 256";
      }
      enum gcm-aes-128 {
        value 1;
        description "GCM AES 128";
      }
      enum gcm-aes-xpn-256 {
        value 2;
        description "GCM AES XPN 256";
      }
    }
    description "Macsec ctrlr ciphersuit";
  }
  typedef Macsec-ctrlr-state {
    type enumeration {
      enum macsec-ctrlr-state-up {
        value 0;
        description "Up";
      }
      enum macsec-ctrlr-state-down {
        value 1;
        description "Down";
      }
      enum macsec-ctrlr-state-admin-down {
        value 2;
        description "Administratively Down";
      }
    }
    description "Macsec ctrlr state";
  }

  grouping MACSEC-CTRLR-AN-STATUS {
    description "AN status";
    leaf association-number {
      type uint8;
      description "Association Number";
    }
    leaf short-secure-channel-id {
      type uint32;
      description "Short secure channel id";
    }
  }

  grouping MACSEC-CTRLR-SC-STATUS {
    description "Secure Channel status";
    leaf protection-enabled {
      type boolean;
      description "Protection Enabled";
    }
    leaf secure-channel-id {
      type string;
      description "Secure Channel Id";
    }
    leaf confidentiality-offset {
      type uint32;
      description "Confidentiality offset";
    }
    leaf cipher-suite {
      type Macsec-ctrlr-ciphersuit;
      description "Cipher Suite";
    }
    leaf max-packet-number {
      type uint64;
      description "Max packet Number";
    }
    leaf recent-packet-number {
      type uint64;
      description "Recent Packet Number";
    }

    list active-association {
      description "Active Associations";
      uses MACSEC-CTRLR-AN-STATUS;
    }
  }

  grouping MACSEC-CTRLR-IF-STATUS {
    description "Interface Status details";

    container encrypt-sc-status {
      description "Encrypt Secure Channel Status";
      uses MACSEC-CTRLR-SC-STATUS;
    }

    container decrypt-sc-status {
      description "Decrypt Secure Channel Status";
      uses MACSEC-CTRLR-SC-STATUS;
    }
    leaf state {
      type Macsec-ctrlr-state;
      description "State";
    }
    leaf replay-window-size {
      type uint32;
      description "Replay Window Size";
    }
    leaf must-secure {
      type boolean;
      description "Must Secure";
    }
    leaf secure-mode {
      type uint32;
      description "Secure Mode";
    }
  }
}
