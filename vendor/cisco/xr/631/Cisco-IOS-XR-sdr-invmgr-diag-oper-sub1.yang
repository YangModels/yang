submodule Cisco-IOS-XR-sdr-invmgr-diag-oper-sub1 {

  belongs-to Cisco-IOS-XR-sdr-invmgr-diag-oper {
    prefix Cisco-IOS-XR-sdr-invmgr-diag-oper;
  }

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR sdr-invmgr-diag package operational data.

     Copyright (c) 2013-2017 by Cisco Systems, Inc.
     All rights reserved.";

  revision "2015-11-09" {
    description
      "IOS XR 6.0 revision.";
  }


  grouping DIAG-CARD {
    description "Card Instance";

    container card-instance {
      description "Card instance";
      uses DIAG-EEPROM;
    }
    leaf node-operational-state {
      type string {
        length "0..255";
      }
      description "Node operational state ";
    }
  }

  grouping RMA-DETAIL {
    description "EEPROM RMA data content";
    leaf test-history {
      type string {
        length "0..255";
      }
      description "Test history";
    }
    leaf rma-number {
      type string {
        length "0..255";
      }
      description "RMA tracking number format is N-N-N";
    }
    leaf rma-history {
      type string {
        length "0..255";
      }
      description "RMA history";
    }
  }

  grouping DIAG-EEPROM {
    description "Diag EEPROM data content";

    container rma {
      description "RMA Data";
      uses RMA-DETAIL;
    }
    leaf description {
      type string {
        length "0..255";
      }
      description "A textual description of physical entity";
    }
    leaf idprom-format-rev {
      type string {
        length "0..255";
      }
      description "IDPROM Format Revision";
    }
    leaf controller-family {
      type string {
        length "0..255";
      }
      description "Controller family";
    }
    leaf controller-type {
      type string {
        length "0..255";
      }
      description "Controller type";
    }
    leaf vid {
      type string {
        length "0..255";
      }
      description "Version ID";
    }
    leaf hwid {
      type string {
        length "0..255";
      }
      description "Hardware Revision";
    }
    leaf pid {
      type string {
        length "0..255";
      }
      description "Product ID";
    }
    leaf udi-description {
      type string {
        length "0..255";
      }
      description "UDI description";
    }
    leaf udi-name {
      type string {
        length "0..255";
      }
      description "UDI name";
    }
    leaf clei {
      type string {
        length "0..255";
      }
      description
        "Common Language Equipment Identifier (CLEI) code";
    }
    leaf eci {
      type string {
        length "0..255";
      }
      description "Equipment Catalog Item (ECI) number";
    }
    leaf top-assem-part-num {
      type string {
        length "0..255";
      }
      description "Top assembly part number";
    }
    leaf top-assem-vid {
      type string {
        length "0..255";
      }
      description "Top assembly revision number";
    }
    leaf pca-num {
      type string {
        length "0..255";
      }
      description "PCA number";
    }
    leaf pcavid {
      type string {
        length "0..255";
      }
      description "PCA revision ID";
    }
    leaf chassis-sid {
      type string {
        length "0..255";
      }
      description "Chassis serial number";
    }
    leaf dev-num1 {
      type string {
        length "0..255";
      }
      description "Deviation Number # 1";
    }
    leaf dev-num2 {
      type string {
        length "0..255";
      }
      description "Deviation Number # 2";
    }
    leaf dev-num3 {
      type string {
        length "0..255";
      }
      description "Deviation Number # 3";
    }
    leaf dev-num4 {
      type string {
        length "0..255";
      }
      description "Deviation Number # 4";
    }
    leaf dev-num5 {
      type string {
        length "0..255";
      }
      description "Deviation Number # 5";
    }
    leaf dev-num6 {
      type string {
        length "0..255";
      }
      description "Deviation Number # 6";
    }
    leaf dev-num7 {
      type string {
        length "0..255";
      }
      description "Deviation Number # 7";
    }
    leaf manu-test-data {
      type string {
        length "0..255";
      }
      description "Manufacturing Test Data";
    }
    leaf asset-id {
      type string {
        length "0..255";
      }
      description "Asset ID";
    }
    leaf asset-alias {
      type string {
        length "0..255";
      }
      description "Asset Alias";
    }
    leaf base-mac-address1 {
      type string {
        length "0..255";
      }
      description "Base Mac Address #1";
    }
    leaf mac-add-blk-size1 {
      type string {
        length "0..255";
      }
      description "Mac Address Block Size #1";
    }
    leaf base-mac-address2 {
      type string {
        length "0..255";
      }
      description "Base Mac Address #2";
    }
    leaf mac-add-blk-size2 {
      type string {
        length "0..255";
      }
      description "Mac Address Block Size #2";
    }
    leaf base-mac-address3 {
      type string {
        length "0..255";
      }
      description "Base Mac Address #3";
    }
    leaf mac-add-blk-size3 {
      type string {
        length "0..255";
      }
      description "Mac Address Block Size #3";
    }
    leaf base-mac-address4 {
      type string {
        length "0..255";
      }
      description "Base Mac Address #4";
    }
    leaf mac-add-blk-size4 {
      type string {
        length "0..255";
      }
      description "Mac Address Block Size #4";
    }
    leaf pcb-serial-num {
      type string {
        length "0..255";
      }
      description "PCB Serial Number";
    }
    leaf power-supply-type {
      type string {
        length "0..255";
      }
      description "Power Supply Type";
    }
    leaf power-consumption {
      type string {
        length "0..255";
      }
      description "Power Consumption";
    }
    leaf block-signature {
      type string {
        length "0..255";
      }
      description "Block Signature";
    }
    leaf block-version {
      type string {
        length "0..255";
      }
      description "Block Version";
    }
    leaf block-length {
      type string {
        length "0..255";
      }
      description "Block Length";
    }
    leaf block-checksum {
      type string {
        length "0..255";
      }
      description "Block Checksum";
    }
    leaf eeprom-size {
      type string {
        length "0..255";
      }
      description "EEPROM Size";
    }
    leaf block-count {
      type string {
        length "0..255";
      }
      description "Block Count";
    }
    leaf fru-major-type {
      type string {
        length "0..255";
      }
      description "FRU Major Type";
    }
    leaf fru-minor-type {
      type string {
        length "0..255";
      }
      description "FRU Minor Type";
    }
    leaf oem-string {
      type string {
        length "0..255";
      }
      description "OEM String";
    }
    leaf product-id {
      type string {
        length "0..255";
      }
      description "Product ID";
    }
    leaf serial-number {
      type string {
        length "0..255";
      }
      description "Serial Number";
    }
    leaf part-number {
      type string {
        length "0..255";
      }
      description "Part Number";
    }
    leaf part-revision {
      type string {
        length "0..255";
      }
      description "Part Revision";
    }
    leaf mfg-deviation {
      type string {
        length "0..255";
      }
      description "MFG Deviation";
    }
    leaf hw-version {
      type string {
        length "0..255";
      }
      description "Hardware Version";
    }
    leaf mfg-bits {
      type string {
        length "0..255";
      }
      description "MFG Bits";
    }
    leaf engineer-use {
      type string {
        length "0..255";
      }
      description "Engineer Use";
    }
    leaf snmpoid {
      type string {
        length "0..255";
      }
      description "SNMP OID";
    }
    leaf rma-code {
      type string {
        length "0..255";
      }
      description "RMA Code";
    }
  }
}
