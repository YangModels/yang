module Cisco-IOS-XR-config-cfgmgr-exec-oper {

  /*** NAMESPACE / PREFIX DEFINITION ***/

  namespace "http://cisco.com/ns/yang"+
    "/Cisco-IOS-XR-config-cfgmgr-exec-oper";


  prefix "config-cfgmgr-exec-oper";

  /*** LINKAGE (IMPORTS / INCLUDES) ***/

  import Cisco-IOS-XR-types { prefix "xr"; }

  include Cisco-IOS-XR-config-cfgmgr-exec-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR config-cfgmgr-exec package operational data.

     This module contains definitions
     for the following management objects:
       cfg-hist-gl: Configuration History Global path information

     Copyright (c) 2013-2017 by Cisco Systems, Inc.
     All rights reserved.";

  revision "2015-11-09" {
    description
      "IOS XR 6.0 revision.";
  }


  container cfg-hist-gl {
    config false;
    description "Configuration History Global path information";

    list record-type {
      key "record-type";
      description
        "History summary information for a specific type
        of history";
      leaf record-type {
        type xr:Cisco-ios-xr-string;
        description "Record type";
      }

      list record {
        key "record";
        description
          "History summary information for a specific type
          of history";
        leaf record {
          type int32;
          description "Record";
        }
        uses CONFIGURATIONHISTORY-ENTRY;
      }
    }
  }
}
