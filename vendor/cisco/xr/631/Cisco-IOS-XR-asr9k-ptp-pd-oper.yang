module Cisco-IOS-XR-asr9k-ptp-pd-oper {

  /*** NAMESPACE / PREFIX DEFINITION ***/

  namespace "http://cisco.com/ns"+
    "/yang/Cisco-IOS-XR-asr9k-ptp-pd-oper";


  prefix "asr9k-ptp-pd-oper";

  /*** LINKAGE (IMPORTS / INCLUDES) ***/

  include Cisco-IOS-XR-asr9k-ptp-pd-oper-sub1 {
    revision-date 2017-03-16;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR asr9k-ptp-pd package operational data.

     This module contains definitions
     for the following management objects:
       platform-ptp: PTP PD operational data

     Copyright (c) 2013-2017 by Cisco Systems, Inc.
     All rights reserved.";

  revision "2017-03-16" {
    description
      "IOS-XR 6.3.1 revision.";
  }

  revision "2015-11-09" {
    description
      "IOS XR 6.0 revision.";
  }


  container platform-ptp {
    config false;
    description "PTP PD operational data";

    container platform-ptp-servo {
      description "PTP PD Servo information";
      uses PTP-PD-SERVO-INFO;
    }
  }
}
