module Cisco-IOS-XR-dot1x-cfg {

  /*** NAMESPACE / PREFIX DEFINITION ***/

  namespace "http://cisco.com/ns/yang/Cisco-IOS-XR-dot1x-cfg";


  prefix "dot1x-cfg";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR dot1x package configuration.

     This module contains definitions
     for the following management objects:
       dot1x: Global Dot1x Configuration
       eap: eap

     Copyright (c) 2013-2017 by Cisco Systems, Inc.
     All rights reserved.";

  revision "2015-11-09" {
    description
      "IOS XR 6.0 revision.";
  }

  typedef Dot1xpae {
    type string {
      pattern "(supplicant)|(authenticator)|(both)";
    }
    description
      "supplicant:PAE Type as Supplicant, authenticator:
      PAE type as Authenticator, both: PAE type as
      Supplicant & Authenticator";
  }
  typedef Dot1x-reauth-local-interval {
    type uint32 {
      range "60..5184000";
    }
    description "Dot1x reauth local interval";
  }

  container dot1x {
    description "Global Dot1x Configuration";

    list dot1x-profile {
      key "profile-name";
      description "Global Dot1x Profile Name";

      container supplicant {
        description "Dot1x Supplicant Related Configuration";
        leaf eap-profile {
          type string;
          description "EAP Profile for Supplicant";
        }
      }

      container authenticator {
        description "Dot1x Authenticator Related Configuration";

        container timers {
          description "Timers for Authenticator";

          container reauth-time {
            description
              "After this time ReAuthentication will be
              trigerred";
            leaf server {
              type boolean;
              description
                "Reauth will be triggerred based on the EAP
                server configuration";
            }
            leaf local {
              type Dot1x-reauth-local-interval;
              units "second";
              description
                "Reauth will be triggerred based on the
                configuration in box";
            }
          }
        }
      }
      leaf pae {
        type Dot1xpae;
        description "Dot1x PAE (Port Access Entity) Role";
      }
      leaf profile-name {
        type xr:Cisco-ios-xr-string;
        description "Name of the Dot1x Profile";
      }
    }
  }

  container eap {
    description "eap";

    list eap-profile {
      key "profile-name";
      description "Global EAP Profile Configuration";

      container eaptls {
        description "EAP TLS Configuration";
        leaf pki-trustpoint {
          type string;
          description "Configure PKI Trustpoint";
        }
      }
      leaf identity {
        type string;
        description "Configure EAP Identity/UserName";
      }
      leaf profile-name {
        type xr:Cisco-ios-xr-string;
        description "Name of the EAP Profile";
      }
    }
  }
}
