module Cisco-IOS-XR-pppoe-ea-oper {

  /*** NAMESPACE / PREFIX DEFINITION ***/

  namespace "http://cisco.com/ns/yang/Cisco-IOS-XR-pppoe-ea-oper";


  prefix "pppoe-ea-oper";

  /*** LINKAGE (IMPORTS / INCLUDES) ***/

  import Cisco-IOS-XR-types { prefix "xr"; }

  include Cisco-IOS-XR-pppoe-ea-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR pppoe-ea package operational data.

     This module contains definitions
     for the following management objects:
       pppoe-ea: PPPoE Ea data

     Copyright (c) 2013-2017 by Cisco Systems, Inc.
     All rights reserved.";

  revision "2015-11-09" {
    description
      "IOS XR 6.0 revision.";
  }


  container pppoe-ea {
    config false;
    description "PPPoE Ea data";

    container nodes {
      description "PPPOE_EA list of nodes";

      list node {
        key "node-name";
        description
          "PPPOE-EA operational data for a particular node";

        container parent-interface-ids {
          description "PPPoE parent interface info";

          list parent-interface-id {
            key "parent-interface-name";
            description "PPPoE parent interface info";
            leaf parent-interface-name {
              type xr:Interface-name;
              description "Interface Name";
            }
            uses PPPOE-EA-PARENT-INTERFACE-INFO;
          }
        }

        container interface-ids {
          description "PPPoE interface info";

          list interface-id {
            key "interface-name";
            description "PPPoE interface info";
            leaf interface-name {
              type xr:Interface-name;
              description "Interface Name";
            }
            uses PPPOE-EA-INTERFACE-INFO;
          }
        }
        leaf node-name {
          type xr:Node-id;
          description "Node name";
        }
      }
    }
  }
}
