module Cisco-IOS-XR-freqsync-datatypes {

  /*** NAMESPACE / PREFIX DEFINITION ***/

  namespace "http://cisco.com/ns"+
    "/yang/Cisco-IOS-XR-freqsync-datatypes";


  prefix "freqsync-datatypes";

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of generally useful
     derived YANG data types.

     Copyright (c) 2013-2017 by Cisco Systems, Inc.
     All rights reserved.";

  revision "2015-11-09" {
    description
      "IOS XR 6.0 revision.";
  }

  typedef Fsync-ql-option {
    type enumeration {
      enum option-1 {
        value 1;
        description "ITU-T Option 1";
      }
      enum option-2,-generation-1 {
        value 2;
        description "ITU-T Option 2, Generation 1";
      }
      enum option-2,-generation-2 {
        value 3;
        description "ITU-T Option 2, Generation 2";
      }
    }
    description "Fsync ql option";
  }
  typedef Fsync-clock {
    type enumeration {
      enum sync {
        value 3;
        description "Synchronous clock";
      }
      enum internal {
        value 4;
        description "Internal clock";
      }
    }
    description "Fsync clock";
  }
  typedef Fsync-ql-value {
    type enumeration {
      enum dnu {
        value 1;
        description
          "This signal should not be used for
          synchronization";
      }
      enum o1-prc {
        value 10;
        description "ITU-T Option 1: Primary reference clock";
      }
      enum o1-ssu-a {
        value 11;
        description "ITU-T Option 1: Type I or V slave clock";
      }
      enum o1-ssu-b {
        value 12;
        description "ITU-T Option 1: Type IV slave clock";
      }
      enum o1-sec {
        value 13;
        description "ITU-T Option 1: SONET equipment clock";
      }
      enum o2-g1-prs {
        value 20;
        description
          "ITU-T Option 2, Generation 1: Primary reference
          source";
      }
      enum o2-g1-stu {
        value 21;
        description
          "ITU-T Option 2, Generation 1: Synchronized -
          traceability unknown";
      }
      enum o2-g1-st2 {
        value 22;
        description "ITU-T Option 2, Generation 1: Stratum 2";
      }
      enum o2-g1-st3 {
        value 23;
        description "ITU-T Option 2, Generation 1: Stratum 3";
      }
      enum o2-g1-smc {
        value 24;
        description
          "ITU-T Option 2, Generation 1: SONET clock self
          timed";
      }
      enum o2-g1-st4 {
        value 25;
        description
          "ITU-T Option 2, Generation 1: Stratum 4 freerun";
      }
      enum o2-g2-prs {
        value 30;
        description
          "ITU-T Option 2, Generation 2: Primary reference
          source";
      }
      enum o2-g2-stu {
        value 31;
        description
          "ITU-T Option 2, Generation 2: Synchronized -
          traceability unknown";
      }
      enum o2-g2-st2 {
        value 32;
        description "ITU-T Option 2, Generation 2: Stratum 2";
      }
      enum o2-g2-st3 {
        value 33;
        description "ITU-T Option 2, Generation 2: Stratum 3";
      }
      enum o2-g2-tnc {
        value 34;
        description
          "ITU-T Option 2, Generation 2: Transit node
          clock";
      }
      enum o2-g2-st3e {
        value 35;
        description "ITU-T Option 2, Generation 2: Stratum 3E";
      }
      enum o2-g2-smc {
        value 36;
        description
          "ITU-T Option 2, Generation 2: SONET clock self
          timed";
      }
      enum o2-g2-st4 {
        value 37;
        description
          "ITU-T Option 2, Generation 2: Stratum 4 freerun";
      }
    }
    description "Fsync ql value";
  }
}
