module Cisco-IOS-XR-iedge4710-cfg {

  /*** NAMESPACE / PREFIX DEFINITION ***/

  namespace "http://cisco.com/ns/yang/Cisco-IOS-XR-iedge4710-cfg";


  prefix "iedge4710-cfg";

  /*** LINKAGE (IMPORTS / INCLUDES) ***/

  import Cisco-IOS-XR-types { prefix "xr"; }

  import Cisco-IOS-XR-ifmgr-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR iedge4710 package configuration.

     This module contains definitions
     for the following management objects:
       subscriber-manager: iEdge subscriber manager configuration
       subscriber-featurette: subscriber featurette
       iedge-license-manager: iedge license manager
       sub-manager: sub manager

     This YANG module augments the
       Cisco-IOS-XR-ifmgr-cfg
     module with configuration data.

     Copyright (c) 2013-2017 by Cisco Systems, Inc.
     All rights reserved.";

  revision "2015-11-09" {
    description
      "IOS XR 6.0 revision.";
  }


  container subscriber-manager {
    description "iEdge subscriber manager configuration";

    container accounting {
      description "iEdge accounting feature";

      container send-stop {
        description "Accounting send stop feature";

        container setup-failure {
          description "Setup failure feature";
          leaf method-list-name {
            type string;
            description
              "AAA List name either default or preconfigured";
          }
        }
      }

      container interim {
        description "interim accounting related";

        container variation {
          description
            "variation of first session or service interim
            record from configured timeout";
          leaf maximum-percentage-variation {
            type uint32 {
              range "0..50";
            }
            units "percentage";
            description
              "maximum percentage variation (maximum
              absolute variation is 15 minutes)";
          }
        }
      }
    }

    container srg {
      description "SRG specific config";
      leaf sync-account-session-id {
        type empty;
        description "sync account session id from master to slave";
      }
    }
  }

  container subscriber-featurette {
    description "subscriber featurette";

    list identity-change {
      key "identity-change";
      description "enable identity change processing";
      leaf enable {
        type int32;
        description "instance of identity-change";
      }
      leaf identity-change {
        type xr:Cisco-ios-xr-string;
        description "identity change";
      }
    }
  }

  container iedge-license-manager {
    description "iedge license manager";

    list node {
      key "node-name";
      description "Location. For eg., 0/1/CPU0";
      leaf session-limit {
        type int32;
        description "Session limit configured on linecard";
      }
      leaf session-threshold {
        type int32;
        description "Session threshold configured on linecard";
      }
      leaf node-name {
        type xr:Cisco-ios-xr-string;
        description "The node id to filter on. For eg., 0/1/CPU0";
      }
    }
  }

  container sub-manager {
    description "sub manager";

    list location {
      key "location1";
      description "Select location";

      container trace {
        description "Subscriber manager trace";
        leaf trace-level {
          type int32;
          description "Subscriber manager trace level";
        }
      }
      leaf history {
        type empty;
        description "Disable history for subscriber manager";
      }
      leaf location1 {
        type xr:Cisco-ios-xr-string;
        description "Specify location";
      }
    }
  }

  augment "/a1:interface-configurations/a1:interface-configuration" {

    container service-policies {
      description
        "Interface control subscriber policy
        configuration";

      list service-policy {
        key "service-policy-name";
        description
          "Service policy to be applied to access
          interface  for subscribers";
        leaf service-policy-name {
          type string {
            length "1..63";
          }
          description "Name of policy-map";
        }
      }
    }
    description
      "This augment extends the configuration data of
      'Cisco-IOS-XR-ifmgr-cfg'";
  }
}
