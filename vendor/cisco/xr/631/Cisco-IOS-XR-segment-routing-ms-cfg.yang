module Cisco-IOS-XR-segment-routing-ms-cfg {

  /*** NAMESPACE / PREFIX DEFINITION ***/

  namespace "http://cisco.com/ns/yang"+
    "/Cisco-IOS-XR-segment-routing-ms-cfg";


  prefix "segment-routing-ms-cfg";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR segment-routing-ms package configuration.

     This module contains definitions
     for the following management objects:
       sr: Segment Routing

     Copyright (c) 2013-2017 by Cisco Systems, Inc.
     All rights reserved.";

  revision "2015-11-09" {
    description
      "IOS XR 6.0 revision.";
  }

  typedef Srms-mi-flag {
    type enumeration {
      enum disable {
        value 0;
        description "Disable flag";
      }
      enum enable {
        value 1;
        description "Enable flag";
      }
    }
    description "Srms mi flag";
  }

  container sr {
    description "Segment Routing";

    container global-block {
      presence "Indicates a global-block node is configured.";
      description "Global Block Segment Routing";
      leaf lower-bound {
        type uint32 {
          range "16000..1048574";
        }
        mandatory true;
        description "SRGB Lower Bound";
      }
      leaf upper-bound {
        type uint32 {
          range "16001..1048575";
        }
        mandatory true;
        description "SRGB Upper Bound";
      }
    }

    container local-block {
      presence "Indicates a local-block node is configured.";
      description "Segment Routing Local Block of Labels";
      leaf lower-bound {
        type uint32 {
          range "15000..1048574";
        }
        mandatory true;
        description "SRLB Lower Bound";
      }
      leaf upper-bound {
        type uint32 {
          range "15001..1048575";
        }
        mandatory true;
        description "SRLB Upper Bound";
      }
    }

    container mappings {
      description "Mapping Server";

      list mapping {
        key "af ip mask";
        description "IP prefix to SID mapping";
        leaf af {
          type xr:Cisco-ios-xr-string;
          description "Address Family";
        }
        leaf ip {
          type xr:Cisco-ios-xr-string;
          description "IP prefix";
        }
        leaf mask {
          type int32;
          description "Mask";
        }
        leaf sid-start {
          type uint32 {
            range "0..1048575";
          }
          description "Start of SID index range";
        }
        leaf sid-range {
          type int32;
          description "Range (number of SIDs)";
        }
        leaf flag-attached {
          type Srms-mi-flag;
          description "Enable/Disable Attached flag";
        }
      }
    }
    leaf enable {
      type empty;
      description "enable SR";
    }
  }
}
