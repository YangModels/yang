submodule Cisco-IOS-XR-infra-dumper-exception-oper-sub1 {

  belongs-to Cisco-IOS-XR-infra-dumper-exception-oper {
    prefix Cisco-IOS-XR-infra-dumper-exception-oper;
  }

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR infra-dumper-exception package operational data.

     Copyright (c) 2013-2017 by Cisco Systems, Inc.
     All rights reserved.";

  revision "2017-05-05" {
    description
      "Fix comp-mdata.pl for adding sub1 yang file to /pkg/yang";
  }

  revision "2015-11-09" {
    description
      "IOS XR 6.0 revision.";
  }


  grouping DISPLAY-SIZE-ST {
    description "displayConfiguration";
    leaf string {
      type string;
      description "String  ";
    }
  }

  grouping DISPLAY-KERNEL-TFTP-ROUTE-CONFIG-ST {
    description "displayConfiguration";
    leaf slot {
      type uint32;
      description "Slot ";
    }
    leaf port {
      type uint32;
      description "Port ";
    }
    leaf ip-addr {
      type string;
      description "IP Address";
    }
    leaf mask {
      type string;
      description "Mask";
    }
    leaf destination {
      type string;
      description "Destination ";
    }
    leaf next-hop {
      type string;
      description "NextHop ";
    }
  }

  grouping DISPLAY-KERNEL-CONFIGURATION-ST {
    description "displayFallback Configuration";
    leaf choice-fall-back {
      type string;
      description "Choice ";
    }
    leaf path {
      type string;
      description "Path ";
    }
    leaf file-name {
      type string;
      description "Name of the File ";
    }
    leaf memory {
      type string;
      description "Memory ";
    }
  }

  grouping DISPLAY-FALLBACK-CONFIGURATION-ST {
    description "displayFallback Configuration";
    leaf choice-fall-back {
      type string;
      description "Choice ";
    }
    leaf path {
      type string;
      description "Path ";
    }
    leaf compress {
      type string;
      description "Compress on/off ";
    }
    leaf file-name {
      type string;
      description "Name of the File ";
    }
    leaf boot-device-str {
      type string;
      description "Boot Device String ";
    }
    leaf range-low {
      type uint32;
      description "Range Low ";
    }
    leaf range-high {
      type uint32;
      description "Range High ";
    }
  }

  grouping DISPLAY-CONFIGURATION-ST {
    description "display Configuration";
    leaf choice {
      type string;
      description "Choice ";
    }
    leaf path {
      type string;
      description "Path ";
    }
    leaf compress {
      type string;
      description "Compress on/off ";
    }
    leaf file-name {
      type string;
      description "Name of the File ";
    }
    leaf range-low {
      type uint32;
      description "Range Low ";
    }
    leaf range-high {
      type uint32;
      description "Range High ";
    }
  }

  grouping DUMPER-EXCEPTION-CONFIG-XML {
    description "Exception Information";

    container display-config1 {
      description "Display Configuration";
      uses DISPLAY-CONFIGURATION-ST;
    }

    container display-config2 {
      description "Display Configuration";
      uses DISPLAY-CONFIGURATION-ST;
    }

    container display-config3 {
      description "Display Configuration";
      uses DISPLAY-CONFIGURATION-ST;
    }

    container display-fall-back-config1 {
      description "Display fallback Configuration";
      uses DISPLAY-FALLBACK-CONFIGURATION-ST;
    }

    container display-fall-back-config2 {
      description "Display fallback Configuration";
      uses DISPLAY-FALLBACK-CONFIGURATION-ST;
    }

    container display-fall-back-config3 {
      description "Display fallback Configuration";
      uses DISPLAY-FALLBACK-CONFIGURATION-ST;
    }

    container kernel-config {
      description "Kernel Configuration";
      uses DISPLAY-KERNEL-CONFIGURATION-ST;
    }

    container kernel-route-config {
      description "Kernel Route Configuration";
      uses DISPLAY-KERNEL-TFTP-ROUTE-CONFIG-ST;
    }

    container core-size {
      description "Core Size";
      uses DISPLAY-SIZE-ST;
    }

    container memory-threshold {
      description "Memory Threshold ";
      uses DISPLAY-SIZE-ST;
    }

    container proc-size {
      description "Proc Size";
      uses DISPLAY-SIZE-ST;
    }

    container qsize {
      description "QSIZE ";
      uses DISPLAY-SIZE-ST;
    }
    leaf pak-mem {
      type string;
      description "Pak MEM";
    }
    leaf sparse {
      type string;
      description "Sparse ";
    }
    leaf spr-size {
      type string;
      description "Spr Size";
    }
    leaf core-verification {
      type string;
      description "Core Verification ";
    }
    leaf dump-time-out {
      type string;
      description "Dump Timeout ";
    }
  }
}
