module Cisco-IOS-XR-ipv4-igmp-cfg {

  /*** NAMESPACE / PREFIX DEFINITION ***/

  namespace "http://cisco.com/ns/yang/Cisco-IOS-XR-ipv4-igmp-cfg";


  prefix "ipv4-igmp-cfg";

  /*** LINKAGE (IMPORTS / INCLUDES) ***/

  import ietf-inet-types { prefix "inet"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ipv4-igmp package configuration.

     This module contains definitions
     for the following management objects:
       igmp: IGMPconfiguration
       amt: amt
       mld: mld

     Copyright (c) 2013-2017 by Cisco Systems, Inc.
     All rights reserved.";

  revision "2016-10-10" {
    description
      "Removed invalid configs from VRF container";
  }

  revision "2015-11-09" {
    description
      "IOS XR 6.0 revision.";
  }

  typedef Igmp-filter {
    type enumeration {
      enum include {
        value 0;
        description "Include";
      }
      enum exclude {
        value 1;
        description "Exclude";
      }
      enum star-g {
        value 2;
        description "StarG";
      }
    }
    description "Igmp filter";
  }

  grouping MAXIMUM-GROUPS-PER-INTERFACE-OOR {
    description "Common node of inheritable-defaults, interface";

    container maximum-groups-per-interface-oor {
      presence "Indicates a maximum-groups-per-interface-oor node"+
        " is configured.";
      description
        "Configure maximum number of groups accepted per
        interface by this router";
      leaf maximum-groups {
        type uint32 {
          range "1..40000";
        }
        mandatory true;
        description
          "Maximum number of groups accepted per interface
          by this router";
      }
      leaf warning-threshold {
        type uint32 {
          range "1..40000";
        }
        default "25000";
        description
          " WarningThreshold for number of groups accepted
          per interface by this router";
      }
      leaf access-list-name {
        type xr:Cisco-ios-xr-string {
          length "1..64";
        }
        description "Access-list to account for";
      }
    }
  }

  grouping VRF-TABLE {
    description "Common node of mld, igmp";

    container vrfs {
      description "VRF related configuration";

      list vrf {
        key "vrf-name";
        description "Configuration for a particular vrf";
        leaf vrf-name {
          type xr:Cisco-ios-xr-string {
            length "1..32";
          }
          description "Name for this vrf";
        }
        uses TRAFFIC;
        uses INHERITABLE-DEFAULTS;
        uses SSM-ACCESS-GROUP-TABLE;
        uses MAXIMUM;
        uses SSMDNS-QUERY-GROUP;
        uses INTERFACE-TABLE;
        uses ROBUSTNESS;
      }
    }
  }

  grouping TRAFFIC {
    description "Common node of vrf, default-context";

    container traffic {
      description "Configure IGMP Traffic variables";
      leaf profile {
        type xr:Cisco-ios-xr-string {
          length "1..64";
        }
        description "Configure the route-policy profile";
      }
    }
  }

  grouping INHERITABLE-DEFAULTS {
    description "Common node of vrf, default-context";

    container inheritable-defaults {
      description "Inheritable Defaults";
      uses MAXIMUM-GROUPS-PER-INTERFACE-OOR;
      uses QUERY-TIMEOUT;
      uses ACCESS-GROUP;
      uses QUERY-MAX-RESPONSE-TIME;
      uses VERSION;
      uses ROUTER-ENABLE;
      uses QUERY-INTERVAL;
      uses EXPLICIT-TRACKING;
    }
  }

  grouping ROBUSTNESS {
    description "Common node of vrf, default-context";
    leaf robustness {
      type uint32 {
        range "2..10";
      }
      default "2";
      description "Configure IGMP Robustness variable";
    }
  }

  grouping VERSION {
    description "Common node of inheritable-defaults, interface";
    leaf version {
      type uint32 {
        range "1..3";
      }
      default "3";
      description "Version number";
    }
  }

  grouping MAXIMUM {
    description "Common node of vrf, default-context";

    container maximum {
      description "Configure IGMP State Limits";
      leaf maximum-groups {
        type uint32 {
          range "1..75000";
        }
        default "50000";
        description
          "Configure maximum number of groups accepted by
          this router";
      }
    }
  }

  grouping INTERFACE-TABLE {
    description "Common node of vrf, default-context";

    container interfaces {
      description "Interface-level configuration";

      list interface {
        key "interface-name";
        description "The name of the interface";

        container join-groups {

          grouping JOIN-GROUP-CONTENT {
            description "JOIN GROUP CONTENT";
            leaf mode {
              type Igmp-filter;
              mandatory true;
              description "Filter mode";
            }
          }

          list join-group {
            key "group-address";
            description
              "IP group address and optional source address
              to include";
            leaf group-address {
              type inet:ip-address-no-zone;
              description "IP group address";
            }
            uses JOIN-GROUP-CONTENT;
          }


          list join-group-source-address {
            key "group-address source-address";
            description
              "IP group address and optional source address
              to include";
            leaf group-address {
              type inet:ip-address-no-zone;
              description "IP group address";
            }
            leaf source-address {
              type inet:ip-address-no-zone;
              description "Optional IP source address";
            }
            uses JOIN-GROUP-CONTENT;
          }

          presence "Indicates a join-groups node is configured.";
          description "IGMP join multicast group";
        }

        container static-group-group-addresses {
          description "IGMP static multicast group";

          grouping STATIC-GROUP-CONTENT {
            description "STATIC GROUP CONTENT";
            leaf group-count {
              type uint32 {
                range "1..512";
              }
              default "1";
              description
                "Number of groups to join (do not set without
                GroupAddressMask)";
            }
            leaf source-count {
              type uint32 {
                range "1..512";
              }
              default "1";
              description
                "Number of sources to join (do not set
                without SourceAddressMask)";
            }
            leaf suppress-report {
              type boolean;
              default "false";
              description "Suppress reports";
            }
          }

          list static-group-group-address {
            key "group-address";
            description
              "IP group address and optional source address
              to include";
            leaf group-address {
              type inet:ip-address-no-zone;
              description "IP group address";
            }
            uses STATIC-GROUP-CONTENT;
          }

          list static-group-group-address-source-address {
            key "group-address source-address";
            description
              "IP group address and optional source address
              to include";
            leaf group-address {
              type inet:ip-address-no-zone;
              description "IP group address";
            }
            leaf source-address {
              type inet:ip-address-no-zone;
              description "IP source address";
            }
            uses STATIC-GROUP-CONTENT;
          }

          list "static-group-group-address-source-address-source"+
            "-address-mask" {
            key "group-address source-address source-address-mask";
            description
              "IP group address and optional source address
              to include";
            leaf group-address {
              type inet:ip-address-no-zone;
              description "IP group address";
            }
            leaf source-address {
              type inet:ip-address-no-zone;
              description "IP source address";
            }
            leaf source-address-mask {
              type inet:ip-address-no-zone;
              description "Mask for Source Address";
            }
            uses STATIC-GROUP-CONTENT;
          }

          list static-group-group-address-group-address-mask {
            key "group-address group-address-mask";
            description
              "IP group address and optional source address
              to include";
            leaf group-address {
              type inet:ip-address-no-zone;
              description "IP group address";
            }
            leaf group-address-mask {
              type inet:ip-address-no-zone;
              description "Mask for Group Address";
            }
            uses STATIC-GROUP-CONTENT;
          }

          list "static-group-group-address-group-address-mask"+
            "-source-address" {
            key "group-address group-address-mask source-address";
            description
              "IP group address and optional source address
              to include";
            leaf group-address {
              type inet:ip-address-no-zone;
              description "IP group address";
            }
            leaf group-address-mask {
              type inet:ip-address-no-zone;
              description "Mask for Group Address";
            }
            leaf source-address {
              type inet:ip-address-no-zone;
              description "IP source address";
            }
            uses STATIC-GROUP-CONTENT;
          }

          list "static-group-group-address-group-address-mask"+
            "-source-address-source-address-mask" {
            key "group-address group-address-mask source-address"+
              " source-address-mask";
            description
              "IP group address and optional source address
              to include";
            leaf group-address {
              type inet:ip-address-no-zone;
              description "IP group address";
            }
            leaf group-address-mask {
              type inet:ip-address-no-zone;
              description "Mask for Group Address";
            }
            leaf source-address {
              type inet:ip-address-no-zone;
              description "IP source address";
            }
            leaf source-address-mask {
              type inet:ip-address-no-zone;
              description "Mask for Source Address";
            }
            uses STATIC-GROUP-CONTENT;
          }
        }
        leaf interface-name {
          type xr:Interface-name;
          description "Name of the interface";
        }
        uses MAXIMUM-GROUPS-PER-INTERFACE-OOR;
        uses QUERY-TIMEOUT;
        uses ACCESS-GROUP;
        uses QUERY-MAX-RESPONSE-TIME;
        uses VERSION;
        uses ROUTER-ENABLE;
        uses QUERY-INTERVAL;
        uses EXPLICIT-TRACKING;
      }
    }
  }

  grouping ACCESS-GROUP {
    description "Common node of inheritable-defaults, interface";
    leaf access-group {
      type xr:Cisco-ios-xr-string {
        length "1..64";
      }
      description "Access list specifying access group range";
    }
  }

  grouping SSM-ACCESS-GROUP-TABLE {
    description "Common node of vrf, default-context";

    container ssm-access-groups {
      description "IGMP Source specific mode";

      list ssm-access-group {
        key "source-address";
        description "SSM static Access Group";
        leaf source-address {
          type inet:ip-address-no-zone;
          description "IP source address";
        }
        leaf access-list-name {
          type xr:Cisco-ios-xr-string {
            length "1..64";
          }
          mandatory true;
          description "Access list specifying access group";
        }
      }
    }
  }

  grouping QUERY-MAX-RESPONSE-TIME {
    description "Common node of inheritable-defaults, interface";
    leaf query-max-response-time {
      type uint32 {
        range "1..12";
      }
      units "second";
      default "10";
      description "Query response value in seconds";
    }
  }

  grouping DEFAULT-CONTEXT {
    description "Common node of igmp, mld";

    container default-context {
      presence "Indicates a default-context node is configured.";
      description "Default Context";

      container nsf {
        description "Configure NSF specific options";
        leaf lifetime {
          type uint32 {
            range "10..3600";
          }
          units "second";
          default "60";
          description "Maximum time for IGMP NSF mode in seconds";
        }
      }

      container unicast-qos-adjust {
        description
          "Configure IGMP QoS shapers for subscriber
          interfaces";
        leaf download-interval {
          type uint32 {
            range "10..500";
          }
          units "millisecond";
          default "100";
          description
            "Configure the QoS download interval (in
            milliseconds)";
        }
        leaf adjustment-delay {
          type uint32 {
            range "0..10";
          }
          units "second";
          default "1";
          description
            "Configure the QoS delay before programming (in
            seconds)";
        }
        leaf hold-off {
          type uint32 {
            range "5..1800";
          }
          units "second";
          default "180";
          description
            "Configure the QoS hold off time (in seconds)";
        }
      }

      container accounting {
        description
          "Configure IGMP accounting for logging
          join/leave records";
        leaf max-history {
          type uint32 {
            range "0..365";
          }
          units "day";
          default "0";
          description
            "Configure IGMP accounting Maximum History
            setting";
        }
      }
      uses TRAFFIC;
      uses INHERITABLE-DEFAULTS;
      uses SSM-ACCESS-GROUP-TABLE;
      uses MAXIMUM;
      uses SSMDNS-QUERY-GROUP;
      uses INTERFACE-TABLE;
      uses ROBUSTNESS;
    }
  }

  grouping QUERY-INTERVAL {
    description "Common node of inheritable-defaults, interface";
    leaf query-interval {
      type uint32 {
        range "1..3600";
      }
      units "second";
      default "60";
      description "Query interval in seconds";
    }
  }

  grouping ROUTER-ENABLE {
    description "Common node of inheritable-defaults, interface";
    leaf router-enable {
      type boolean;
      default "true";
      description
        "Enabled or disabled, when value is TRUE or FALSE
        respectively";
    }
  }

  grouping SSMDNS-QUERY-GROUP {
    description "Common node of vrf, default-context";
    leaf ssmdns-query-group {
      type empty;
      description "Enable SSM mapping using DNS Query";
    }
  }

  grouping QUERY-TIMEOUT {
    description "Common node of inheritable-defaults, interface";
    leaf query-timeout {
      type uint32 {
        range "60..300";
      }
      units "second";
      description "IGMP previous querier timeout";
    }
  }

  grouping EXPLICIT-TRACKING {
    description "Common node of inheritable-defaults, interface";

    container explicit-tracking {
      presence "Indicates a explicit-tracking node is configured.";
      description "IGMPv3 explicit host tracking";
      leaf enable {
        type boolean;
        mandatory true;
        description
          "Enabled or disabled, when value is TRUE or
          FALSE respectively";
      }
      leaf access-list-name {
        type xr:Cisco-ios-xr-string {
          length "1..64";
        }
        description "Access list specifying tracking group range";
      }
    }
  }

  container igmp {
    presence "Indicates a igmp node is configured.";
    description "IGMPconfiguration";
    uses VRF-TABLE;
    uses DEFAULT-CONTEXT;
  }

  container amt {
    description "amt";

    container relay-adv-add {
      presence "Indicates a relay-adv-add node is configured.";
      description "Configure AMT Relay IPv4 Advertisement Address";
      leaf address {
        type inet:ipv4-address-no-zone;
        mandatory true;
        description "AMT Relay IPv4 Advertisement Address";
      }
      leaf interface {
        type xr:Interface-name;
        description "Relay Advertisement Interface";
      }
    }

    container relay-anycast-prefix {
      presence "Indicates a relay-anycast-prefix node is"+
        " configured.";
      description "Configure AMT Relay IPv4 Anycast-Prefix";
      leaf address {
        type inet:ipv4-address-no-zone;
        mandatory true;
        description "Anycast-Prefix Address";
      }
      leaf prefix-length {
        type uint32 {
          range "1..32";
        }
        description "Mask Length for Anycast Prefix";
      }
    }
    leaf maximum-v4-route-gateway {
      type uint32 {
        range "1..4294967295";
      }
      description
        "Configure Maximum number of IPv4 route-gateways
        (Tunnels)";
    }
    leaf gateway-filter {
      type xr:Cisco-ios-xr-string {
        length "1..64";
      }
      description "Access list for Gateway Filter";
    }
    leaf maximum-v4-routes {
      type uint32 {
        range "1..4294967295";
      }
      description "Configure Maximum number of IPv4 Routes";
    }
    leaf amttos {
      type uint32 {
        range "1..255";
      }
      description "Configure AMT Relay TOS";
    }
    leaf amtttl {
      type uint32 {
        range "1..255";
      }
      description "Configure AMT Relay TTL";
    }
    leaf maximum-v6-route-gateway {
      type uint32 {
        range "1..4294967295";
      }
      description
        "Configure Maximum number of IPv6 route-gateways
        (Tunnels)";
    }
    leaf maximum-gateway {
      type uint32 {
        range "1..4294967295";
      }
      description "Configure AMT maximum number of Gateways";
    }
    leaf maximum-v6-routes {
      type uint32 {
        range "1..4294967295";
      }
      description "Configure Maximum number of IPv6 Routes";
    }
    leaf amtqqic {
      type uint32 {
        range "1..4294967295";
      }
      description "Configure AMT QQIC value";
    }
    leaf amtmtu {
      type uint32 {
        range "100..65535";
      }
      description "Configure AMT Relay MTU";
    }
  }

  container mld {
    presence "Indicates a mld node is configured.";
    description "mld";
    uses VRF-TABLE;
    uses DEFAULT-CONTEXT;
  }
}
