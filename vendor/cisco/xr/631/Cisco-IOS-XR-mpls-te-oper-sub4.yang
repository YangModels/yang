submodule Cisco-IOS-XR-mpls-te-oper-sub4 {

  belongs-to Cisco-IOS-XR-mpls-te-oper {
    prefix Cisco-IOS-XR-mpls-te-oper;
  }

  /*** LINKAGE (IMPORTS / INCLUDES) ***/

  import ietf-inet-types { prefix "inet"; }

  include Cisco-IOS-XR-mpls-te-oper-sub6 {
    revision-date 2017-05-01;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR mpls-te package operational data.

     Copyright (c) 2013-2017 by Cisco Systems, Inc.
     All rights reserved.";

  revision "2017-05-01" {
    description
      "Fixing backward compatibility error in module.";
  }

  revision "2015-11-09" {
    description
      "IOS XR 6.0 revision.";
  }

  typedef Pce-tunnel-state {
    type enumeration {
      enum tunnel-state-none {
        description "None";
      }
      enum tunnel-state-admin-down {
        description "AdminDown";
      }
      enum tunnel-state-down {
        description "Down";
      }
      enum tunnel-state-up {
        description "Up";
      }
    }
    description "PCE Tunnel State";
  }
  typedef Pce-tun-path-state {
    type enumeration {
      enum state-none {
        description "None";
      }
      enum state-pending {
        description "Request Pending";
      }
      enum state-received-path {
        description "Path Received";
      }
      enum state-no-peer {
        description "No peer to forward";
      }
      enum state-pcep-down {
        description "PCEP to the peer is down";
      }
      enum state-received-no-path {
        description "Path Received No Path";
      }
    }
    description "PCE Request State";
  }
  typedef Pce-state {
    type enumeration {
      enum tcp-close {
        description "TCP close";
      }
      enum tcp-listen {
        description "TCP listen";
      }
      enum tcp-connect {
        description "TCP connect";
      }
      enum pcep-closed {
        description "PCEP closed";
      }
      enum pcep-opening {
        description "PCEP opening";
      }
      enum pcep-open {
        description "PCEP open";
      }
    }
    description "PCE State";
  }
  typedef Pce-lsp-autoroute-metric {
    type enumeration {
      enum none {
        description "None";
      }
      enum relative {
        description "Relative";
      }
      enum absolute {
        description "Absolute";
      }
    }
    description "Autoroute Metric Type";
  }
  typedef Pce-sr-sid {
    type enumeration {
      enum unknown-segment-id {
        description "Unknown type";
      }
      enum ipv4-node-segment-id {
        description "IPv4 Node ID";
      }
      enum ipv4-adjacency-segment-id {
        description "IPv4 Adjacency ID";
      }
    }
    description "PCE SID type";
  }
  typedef Pce-lsp-oper-state {
    type enumeration {
      enum down {
        description "Down";
      }
      enum up {
        description "Up";
      }
      enum active {
        description "Active";
      }
      enum going-down {
        description "Going down";
      }
      enum going-up {
        description "Going Up";
      }
    }
    description "LSP Operational state";
  }

  grouping PCE-TUNNEL-BAG {
    description "PCE Tunnel Summary Information";
    leaf source-address {
      type inet:ipv4-address;
      description "Source Address";
    }
    leaf destination-address {
      type inet:ipv4-address;
      description "Destination Address";
    }
    leaf is-curr-path-option-pce {
      type boolean;
      description "True if current path option is PCE based";
    }
    leaf curr-path-option-index {
      type uint32;
      description "Path Option Index of the current path";
    }
    leaf configured-pce-address {
      type inet:ipv4-address;
      description "Configured PCE Address";
    }
    leaf sender-pce-address {
      type inet:ipv4-address;
      description "Sender PCE Address";
    }
    leaf path-state {
      type Pce-tun-path-state;
      description "Path Request State";
    }
    leaf tunnel-state {
      type Pce-tunnel-state;
      description "Tunnel State";
    }
    leaf admin-weight {
      type uint32;
      description "Path metric";
    }
    leaf hop-count {
      type uint32;
      description "Hop Count";
    }
  }

  grouping PCE-NODE-BAG {
    description "PCE Node Information";
    leaf router-id {
      type inet:ipv4-address;
      description "Router ID";
    }
    leaf igp-area-id {
      type uint32;
      description "IGP Area number";
    }
    leaf igp-area-format {
      type Igp-ospf-area-format;
      description "IGP Area Format";
    }
    leaf pce-cost {
      type uint32;
      description "PCE cost";
    }
    leaf node-id {
      type inet:ipv4-address;
      description "Node ID";
    }
    leaf is-pce-border-node {
      type boolean;
      description "PCE border node";
    }
  }

  grouping PCE-TOPOLOGY-GLOBAL-INFO-BAG {
    description "PCE Topology Information";

    list nodes {
      description "Node information";
      uses PCE-NODE-BAG;
    }
  }

  grouping PCEERR-BAG {
    description "PCE Error information";
    leaf pce-err-type {
      type uint32;
      description "PCE Error Type";
    }
    leaf pce-err-value {
      type uint32;
      description "PCE Error Value";
    }
    leaf has-open-object {
      type boolean;
      description "Has Open object";
    }
    leaf openversion {
      type uint32;
      description "Open Version";
    }
    leaf open-keepalive {
      type uint32;
      units "second";
      description "Open Keepalive (seconds)";
    }
    leaf open-dead-time {
      type uint32;
      units "second";
      description "Open Deadtime (seconds)";
    }
    leaf has-rp-object {
      type boolean;
      description "Has RP object";
    }
    leaf rp-request-id {
      type uint32;
      description "RP request ID";
    }
  }

  grouping PCE-PEER-IGP-BAG {
    description "PCE IGP information";
    leaf igp-type {
      type Igp-protocol;
      description "Type";
    }
    leaf igp-instance-id {
      type string;
      description "Instance ID";
    }
  }

  grouping PCE-NEIGHBOR-BAG {
    description "PCE Neighbor Information";

    container last-tx-pce-err {
      description "Last sent PCEErr";
      uses PCEERR-BAG;
    }

    container last-rx-pce-err {
      description "Last received PCEErr";
      uses PCEERR-BAG;
    }
    leaf error {
      type string;
      description "Error (for display only)";
    }
    leaf pce-state {
      type Pce-state;
      description "PCE State";
    }
    leaf precedence {
      type uint32;
      description "PCE Precedence";
    }
    leaf stateful {
      type boolean;
      description "Stateful";
    }
    leaf capability-update {
      type boolean;
      description "Update capability";
    }
    leaf capability-instantiate {
      type boolean;
      description "Instantiation capability";
    }
    leaf capability-segment-routing {
      type boolean;
      description "Segment Routing capability";
    }
    leaf triggered-sync-capability {
      type boolean;
      description "Triggered Synchronization capability";
    }
    leaf capability-db-version {
      type boolean;
      description "DB version capability";
    }
    leaf delta-sync-capability {
      type boolean;
      description "Delta Synchronization capability";
    }
    leaf pcep-up-time {
      type uint32;
      description "PCEP Up Time";
    }
    leaf keepalives {
      type uint32;
      description "Keepalive count";
    }
    leaf candidate {
      type boolean;
      description "Candidate";
    }
    leaf statically-configured {
      type boolean;
      description "Statically Configured";
    }
    leaf md5-enabled {
      type boolean;
      description "MD5 Authentication Enabled";
    }
    leaf keychain-enabled {
      type boolean;
      description "Keychain based Authentication Enabled";
    }
    leaf negotiated-keepalive {
      type uint32;
      description "Negotiated KA";
    }
    leaf negotated-dead-time {
      type uint32;
      description "Negotiated DT";
    }
    leaf pce-req-rx {
      type uint32;
      description "PCEReq Rx";
    }
    leaf pce-req-tx {
      type uint32;
      description "PCEReq Tx";
    }
    leaf pce-rep-rx {
      type uint32;
      description "PCERep Rx";
    }
    leaf pce-rep-tx {
      type uint32;
      description "PCERep Tx";
    }
    leaf pce-err-rx {
      type uint32;
      description "PCEErr Rx";
    }
    leaf pce-err-tx {
      type uint32;
      description "PCEErr Tx";
    }
    leaf pce-open-tx {
      type uint32;
      description "PCEOpen Tx";
    }
    leaf pce-open-rx {
      type uint32;
      description "PCEOpen Rx";
    }
    leaf pce-rpt-rx {
      type uint32;
      description "PCERpt Rx";
    }
    leaf pce-rpt-tx {
      type uint32;
      description "PCERpt Tx";
    }
    leaf pce-upd-rx {
      type uint32;
      description "PCEUpd Rx";
    }
    leaf pce-upd-tx {
      type uint32;
      description "PCEUpd Tx";
    }
    leaf pce-init-rx {
      type uint32;
      description "PCEInit Rx";
    }
    leaf pce-init-tx {
      type uint32;
      description "PCEInit Tx";
    }
    leaf pce-keepalive-tx {
      type uint64;
      description "PCE Keepalive Tx";
    }
    leaf pce-keepalive-rx {
      type uint64;
      description "PCE Keepalive Rx";
    }
    leaf req-reply-min {
      type uint64;
      description "Mininum reply time from peer in ms";
    }
    leaf req-reply-max {
      type uint64;
      description "Maximum reply time from peer in ms";
    }
    leaf req-reply-avg {
      type uint64;
      description "Average reply time from peer in ms";
    }
    leaf request-timeouts {
      type uint64;
      description "Request timeout count";
    }
    leaf local-sid {
      type uint8;
      description "Local PCEP session ID";
    }
    leaf remote-sid {
      type uint8;
      description "Remote PCEP session ID";
    }
    leaf min-keepalive-interval {
      type uint8;
      description "Minimum keepalive interval for the peer";
    }
    leaf max-dead-interval {
      type uint8;
      description "Maximum dead interval for the peer";
    }

    list ig-ps {
      description "IGPs";
      uses PCE-PEER-IGP-BAG;
    }
  }

  grouping PCE-IGP-STATS-BAG {
    description "PCE IGP Stats";
    leaf abr-lookup-min {
      type uint64;
      description "ABR Lookup Min";
    }
    leaf abr-lookup-max {
      type uint64;
      description "ABR Lookup Max";
    }
    leaf abr-lookup-avg {
      type uint64;
      description "ABR Lookup Avg";
    }
    leaf abr-lookup-timeout {
      type uint64;
      description "ABR Lookup Timeout";
    }
    leaf abr-lookup-complete {
      type uint64;
      description "ABR Lookup Complete";
    }
  }

  grouping PCE-STATS-BAG {
    description "PCE Stats Information";

    container igp-statistics {
      description "IGP Statistics";
      uses PCE-IGP-STATS-BAG;
    }
    leaf neighbors {
      type uint32;
      description "Neighbor Count";
    }
    leaf tunnels {
      type uint32;
      description "Tunnel Count";
    }
    leaf pce-req-total {
      type uint32;
      description "Total number of PCEReq";
    }
    leaf pce-req-pending {
      type uint32;
      description "Number of pending req";
    }
    leaf pce-req-timed-out {
      type uint32;
      description "Number of timedout req";
    }
    leaf max-file-descriptors {
      type uint32;
      description "Maximum number of TCP file descriptors used";
    }
    leaf current-file-descriptors {
      type uint32;
      description "Number of TCP file descriptors currently in use";
    }
    leaf current-pceq-length {
      type uint32;
      description "Current PCE queue length";
    }
    leaf current-teq-length {
      type uint32;
      description "Current TE queue length";
    }
    leaf max-pceq-length {
      type uint32;
      description "Max PCE queue length";
    }
    leaf max-teq-length {
      type uint32;
      description "Max TE queue length";
    }
    leaf-list maximum-in-queue-depth {
      type uint32;
      max-elements "3";
      description "Max Input Queue Depth";
    }
    leaf-list average-in-queue-depth {
      type uint32;
      max-elements "3";
      description "Average Input Queue Depth";
    }
  }

  grouping PCE-LSP-AUTOROUTE-BAG {
    description "LSP Autoroute Information";
    leaf is-used {
      type boolean;
      description "Autoroute used flag";
    }
    leaf announced {
      type boolean;
      description "Autoroute announced";
    }
    leaf metric-type {
      type Pce-lsp-autoroute-metric;
      description "Metric Type";
    }
    leaf metric {
      type uint32;
      description "Metric Value";
    }
    leaf-list destination {
      type inet:ipv4-address;
      description "Destinations";
    }
  }

  grouping PCE-LSP-METRIC-BAG {
    description "PCE LSP Metric Object";
    leaf type {
      type uint8;
      description "Type";
    }
    leaf cost {
      type uint32;
      description "Cost";
    }
  }

  grouping PCE-LSP-LSPA-BAG {
    description "PCE LSP Attributes Object";
    leaf is-used {
      type boolean;
      description "LSPA used flag";
    }
    leaf exlude-any {
      type uint32;
      description "Exclude Any";
    }
    leaf include-any {
      type uint32;
      description "Include Any";
    }
    leaf include-all {
      type uint32;
      description "Include All";
    }
    leaf setup {
      type uint8;
      description "Setup";
    }
    leaf hold {
      type uint8;
      description "Hold";
    }
    leaf lbit {
      type boolean;
      description "L flag";
    }
  }

  grouping PCE-LSP-ROUTE-HOP-BAG {
    description "PCE LSP Route Subobject";
    leaf subobj-type {
      type uint8;
      description "Route Subobject Type";
    }
    leaf ipv4-address {
      type inet:ipv4-address;
      description "IPv4 address";
    }
    leaf ipv4-prefix-len {
      type uint32;
      description "IPv4 Address Prefix Length";
    }
    leaf strict {
      type boolean;
      description "Strict";
    }
    leaf global {
      type boolean;
      description "Global";
    }
    leaf mpls-label {
      type uint32;
      description "MPLS Label in case Segment ID type is MPLS";
    }
    leaf segment-id-type {
      type Pce-sr-sid;
      description "Segment ID Type";
    }
    leaf only-valid-mpls-label {
      type boolean;
      description
        "If this flag is true, SID has only MPLS label
        value. TC, S, and TTL fields are considered
        invalid";
    }
    leaf complete-mpls-label-entry {
      type boolean;
      description
        "If this flag is true, all fields of MPLS labe
        entry are valid";
    }
    leaf missing-segment-id {
      type boolean;
      description
        "If this flag is true, ERO subobject does not
        have SegmentID";
    }
    leaf missing-node-adjcency-id {
      type boolean;
      description
        "If this flag is true, ERO subobject does not
        have NodeAdjacencyID";
    }
    leaf segment-id-exists {
      type boolean;
      description
        "If this field is true, the bag contains
        SegmentID value";
    }
    leaf segment-id-value {
      type uint32;
      description
        "Contains a SegmentID value in case SegmentID is
        valid";
    }
    leaf node-adjacency-id-exists {
      type boolean;
      description
        "If this flag is true, the bag contains
        NodeAdjacencyID information";
    }
    leaf node-id {
      type inet:ipv4-address;
      description
        "Address of the node corresponding the node
        SegmentID";
    }
    leaf local-address {
      type inet:ipv4-address;
      description
        "Address of the local address corresponding the
        adjacency SegmentID";
    }
    leaf remote-address {
      type inet:ipv4-address;
      description
        "Address of the remote address corresponding the
        adjacency SegmentID";
    }
  }

  grouping PCE-LSP-ROUTE-BAG {
    description "PCE LSP Route Object)";
    leaf is-used {
      type boolean;
      description "Route Object used flag";
    }
    leaf cost {
      type uint32;
      description "Cost";
    }
    leaf-list address {
      type inet:ipv4-address;
      description "List of Addresses";
    }

    list subobject {
      description "List of Route Subobjects";
      uses PCE-LSP-ROUTE-HOP-BAG;
    }
  }

  grouping PCE-LSP-PATH-BAG {
    description "PCE LSP Path";

    container ero {
      description "Explicit Router Object";
      uses PCE-LSP-ROUTE-BAG;
    }

    container lspa {
      description "LSP Attributes Object";
      uses PCE-LSP-LSPA-BAG;
    }

    container rro {
      description "Reported Route Object";
      uses PCE-LSP-ROUTE-BAG;
    }
    leaf bw {
      type uint32;
      description "Bandwidth";
    }
    leaf is-bw-used {
      type boolean;
      description "Bandwidth used flag";
    }
    leaf reopt-bw {
      type uint32;
      description "Reoptimize bandwidth";
    }
    leaf is-reopt-bw-used {
      type boolean;
      description "Reoptimize bandwidth used flag";
    }
    leaf applied-bw {
      type uint32;
      description "Applied bandwidth";
    }
    leaf is-applied-bw-used {
      type boolean;
      description "Applied bandwidth used flag";
    }

    list metric {
      description "List of Metrics";
      uses PCE-LSP-METRIC-BAG;
    }
  }

  grouping PCE-LSP-IDENTIFIERS-BAG {
    description "PCE LSP Identifiers TLV Information";
    leaf is-used {
      type boolean;
      description "LSP Identifier used flag";
    }
    leaf sender {
      type inet:ipv4-address;
      description "Sender Address";
    }
    leaf te-lsp-id {
      type uint16;
      description "TE LSP ID";
    }
    leaf tunnel-id {
      type uint16;
      description "LSPO Tunnel ID";
    }
    leaf ext-tunnel-id {
      type uint32;
      description "External Tunnel ID";
    }
  }

  grouping PCE-LSP-PEER-BAG {
    description "PCE LSP Peer";
    leaf node-identifier {
      type string;
      description "Peer Node Identifier";
    }
    leaf address {
      type inet:ipv4-address;
      description "Peer Ip Address";
    }
  }

  grouping PCE-LSP-BAG {
    description "PCE LSP from LSP Database";

    container creator {
      description "Creator Peer of the LSP";
      uses PCE-LSP-PEER-BAG;
    }

    container delegated {
      description "Owner Peer of the LSP";
      uses PCE-LSP-PEER-BAG;
    }

    container identifiers {
      description "LSP Identifiers";
      uses PCE-LSP-IDENTIFIERS-BAG;
    }

    container autoroute {
      description "Auto Route";
      uses PCE-LSP-AUTOROUTE-BAG;
    }
    leaf source-address {
      type inet:ipv4-address;
      description "Source IP Address";
    }
    leaf destination-address {
      type inet:ipv4-address;
      description "Destination IP Address";
    }
    leaf symbolic-name-xr {
      type string;
      description "Symbolic Name";
    }
    leaf session-internal-lsp-id {
      type uint32;
      description "Session internal ID";
    }
    leaf stateful-request-parameter-id {
      type uint32;
      description "SRP ID";
    }
    leaf request-queue-size {
      type uint8;
      description "Request queue size";
    }
    leaf delegatable {
      type boolean;
      description "LSP delegatable";
    }
    leaf operational {
      type Pce-lsp-oper-state;
      description "LSP operational status";
    }
    leaf administrative {
      type boolean;
      description "LSP administrative status";
    }
    leaf cleanup-timer-exp {
      type int32;
      description "Deprecated";
    }
    leaf delegation-timer-exp {
      type int32;
      description "LSP delegation timer expiration in sec";
    }
    leaf create {
      type boolean;
      description "LSPO create flag";
    }
    leaf state-timer-exp {
      type int32;
      description "LSP state-timeout time expiration";
    }
    leaf lspo-is-used {
      type boolean;
      description "LSP Object used flag";
    }
    leaf forward-class-id {
      type uint32;
      description "Forward Class ID";
    }
    leaf load-share {
      type uint32;
      description "Load share factor";
    }
    leaf path-setup-type {
      type uint8;
      description "Path setup type";
    }
    leaf binding-sid {
      type uint32;
      description "Binding SID";
    }
    leaf-list backup-path {
      type inet:ipv4-address;
      description "Backup Path";
    }

    list paths {
      description "Array of paths";
      uses PCE-LSP-PATH-BAG;
    }
  }
}
