submodule Cisco-IOS-XR-ip-sbfd-oper-sub1 {

  belongs-to Cisco-IOS-XR-ip-sbfd-oper {
    prefix Cisco-IOS-XR-ip-sbfd-oper;
  }

  /*** LINKAGE (IMPORTS / INCLUDES) ***/

  import ietf-inet-types { prefix "inet"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ip-sbfd package operational data.

     Copyright (c) 2013-2017 by Cisco Systems, Inc.
     All rights reserved.";

  revision "2015-11-09" {
    description
      "IOS XR 6.0 revision.";
  }

  typedef Bfd-discr {
    type uint32;
    description "Bfd discr";
  }
  typedef Bfd-in6-addr {
    type inet:ipv6-address;
    description "Bfd in6 addr";
  }
  typedef Bfd-in-addr {
    type inet:ipv4-address;
    description "Bfd in addr";
  }
  typedef Bfd-af-id {
    type enumeration {
      enum bfd-af-id-none {
        value 0;
        description "No Address";
      }
      enum bfd-af-id-ipv4 {
        value 2;
        description "IPv4 AFI";
      }
      enum bfd-af-id-ipv6 {
        value 10;
        description "IPv6 AFI";
      }
    }
    description "Bfd af id";
  }
  typedef Sbfd-address-family {
    type enumeration {
      enum ipv4 {
        value 1;
        description "ipv4";
      }
      enum ipv6 {
        value 2;
        description "ipv6";
      }
    }
    description "Sbfd address family";
  }

  grouping BFD-MGMT-TGT-IDENTIFIER-LOCAL {
    description "SBFD Target Identifier Table";
    leaf discr {
      type uint32;
      description "Local discriminator";
    }
    leaf vrf-name-xr {
      type string;
      description "VRF Name";
    }
    leaf flags {
      type string;
      description "MODE name";
    }
    leaf status {
      type string;
      description "Status";
    }
    leaf discr-src {
      type string;
      description "Discriminator source name";
    }
  }

  grouping IP-ADDR-T-UNION {
    description "IP ADDR T UNION";
    leaf afi {
      type Bfd-af-id;
      description "AFI";
    }
    leaf dummy {
      when "../afi = 'bfd-af-id-none'" {
        description "../AFI = 'BFD_AF_ID_NONE'";
      }
      type uint8;
      description "No Address";
    }
    leaf ipv4 {
      when "../afi = 'bfd-af-id-ipv4'" {
        description "../AFI = 'BFD_AF_ID_IPV4'";
      }
      type Bfd-in-addr;
      description "IPv4 address type";
    }
    leaf ipv6 {
      when "../afi = 'bfd-af-id-ipv6'" {
        description "../AFI = 'BFD_AF_ID_IPV6'";
      }
      type Bfd-in6-addr;
      description "IPv6 address type";
    }
  }

  grouping BFD-MGMT-TGT-IDENTIFIER-REMOTE {
    description "SBFD Target Identifier Table";

    container ip-address {
      description "IP address";
      uses IP-ADDR-T-UNION;
    }
    leaf tid-type {
      type Sbfd-address-family;
      description "Target identifier for sbfd";
    }
    leaf discr {
      type Bfd-discr;
      description "Remote discriminator";
    }
    leaf vrf-name-xr {
      type string;
      description "VRF Name";
    }
    leaf status {
      type string;
      description "Status";
    }
    leaf discr-src {
      type string;
      description "Discriminator source name";
    }
  }
}
