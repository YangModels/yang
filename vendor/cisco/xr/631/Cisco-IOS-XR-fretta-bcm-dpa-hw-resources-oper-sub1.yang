submodule Cisco-IOS-XR-fretta-bcm-dpa-hw-resources-oper-sub1 {

  belongs-to Cisco-IOS-XR-fretta-bcm-dpa-hw-resources-oper {
    prefix Cisco-IOS-XR-fretta-bcm-dpa-hw-resources-oper;
  }

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR fretta-bcm-dpa-hw-resources package operational data.

     Copyright (c) 2013-2017 by Cisco Systems, Inc.
     All rights reserved.";

  revision "2015-11-09" {
    description
      "IOS XR 6.0 revision.";
  }


  grouping DPA-SYSDB-STATS-APP-USAGE {
    description "DPA SYSDB STATS APP USAGE";
    leaf app-type {
      type string;
      description "app type";
    }
    leaf num-cntrs-for-app {
      type uint32;
      description "num cntrs for app";
    }
    leaf num-cntrs-used {
      type uint32;
      description "num cntrs used";
    }
  }

  grouping DPA-SYSDB-STATS-CNTR-ENG {
    description "DPA SYSDB STATS CNTR ENG";
    leaf state {
      type string;
      description "state";
    }
    leaf core-id {
      type uint32;
      description "core id";
    }

    list apps-info {
      description "apps info";
      uses DPA-SYSDB-STATS-APP-USAGE;
    }
  }

  grouping DPA-SYSDB-STATS-HW-RESOURCE {
    description "DPA SYSDB STATS HW RESOURCE";
    leaf sys-cp-cnfg-prof {
      type uint32;
      description "sys cp cnfg prof";
    }
    leaf next-avail-cp-id {
      type uint32;
      description "next avail cp id";
    }
    leaf num-cntr-engines {
      type uint32;
      description "num cntr engines";
    }

    list cntr-engine {
      description "cntr engine";
      uses DPA-SYSDB-STATS-CNTR-ENG;
    }
  }

  grouping DPA-SYSDB-LT-HW-RESOURCE {
    description "DPA SYSDB LT HW RESOURCE";
    leaf lt-id {
      type uint32;
      description "lt id";
    }
    leaf name {
      type string;
      description "name";
    }
    leaf hw-entries {
      type uint32;
      description "hw entries";
    }
    leaf sw-entries {
      type uint32;
      description "sw entries";
    }
  }

  grouping DPA-SYSDB-NPU-HW-RESOURCE {
    description "DPA SYSDB NPU HW RESOURCE";
    leaf max-allowed {
      type uint32;
      description "max allowed";
    }
    leaf npu-id {
      type uint32;
      description "npu id";
    }
    leaf max-entries {
      type uint32;
      description "max entries";
    }
    leaf red-oor-threshold {
      type uint32;
      description "red oor threshold";
    }
    leaf red-oor-threshold-percent {
      type uint32;
      description "red oor threshold percent";
    }
    leaf yellow-oor-threshold {
      type uint32;
      description "yellow oor threshold";
    }
    leaf yellow-oor-threshold-percent {
      type uint32;
      description "yellow oor threshold percent";
    }
    leaf inuse-objects {
      type uint32;
      description "inuse objects";
    }
    leaf num-lt {
      type uint32;
      description "num lt";
    }
    leaf oor-change-count {
      type uint32;
      description "oor change count";
    }
    leaf oor-state-change-time1 {
      type string;
      description "oor state change time1";
    }
    leaf oor-state-change-time2 {
      type string;
      description "oor state change time2";
    }
    leaf oor-state {
      type string;
      description "oor state";
    }

    list lt-hwr {
      description "lt hwr";
      uses DPA-SYSDB-LT-HW-RESOURCE;
    }
  }

  grouping DPA-SYSDB-HW-RESOURCE {
    description "DPA SYSDB HW RESOURCE";
    leaf resource-id {
      type uint32;
      description "resource id";
    }
    leaf name {
      type string;
      description "name";
    }
    leaf num-npus {
      type uint32;
      description "num npus";
    }

    list npu-hwr {
      description "npu hwr";
      uses DPA-SYSDB-NPU-HW-RESOURCE;
    }
  }
}
