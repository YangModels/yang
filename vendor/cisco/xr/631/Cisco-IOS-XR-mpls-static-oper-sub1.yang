submodule Cisco-IOS-XR-mpls-static-oper-sub1 {

  belongs-to Cisco-IOS-XR-mpls-static-oper {
    prefix Cisco-IOS-XR-mpls-static-oper;
  }

  /*** LINKAGE (IMPORTS / INCLUDES) ***/

  import ietf-inet-types { prefix "inet"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR mpls-static package operational data.

     Copyright (c) 2013-2017 by Cisco Systems, Inc.
     All rights reserved.";

  revision "2017-05-01" {
    description
      "Fixing backward compatibility error in module.";
  }

  revision "2015-11-09" {
    description
      "IOS XR 6.0 revision.";
  }

  typedef Mgmt-mpls-static-path-status {
    type enumeration {
      enum path-next-hop-none {
        description "Path NextHop No Status";
      }
      enum path-next-hop-interface-down {
        description "Path NextHop Interface Down ";
      }
      enum path-next-hop-valid {
        description "Path NextHop Valid";
      }
      enum resolve-failed {
        description "Path NextHop Resolve Failed";
      }
      enum frr-backup {
        description "FRR Backup";
      }
      enum backup {
        description "Backup";
      }
    }
    description "Mgmt mpls static path status";
  }
  typedef Mpls-static-path-role {
    type enumeration {
      enum primary {
        description "Path is only for primary traffic";
      }
      enum backup {
        description "Path is only for backup traffic";
      }
      enum primary-and-backup {
        description "Path is for primary and backup traffic";
      }
    }
    description "Mpls static path role";
  }
  typedef Mgmt-static-path {
    type enumeration {
      enum cross-connect-path {
        description "Crossconnect Path";
      }
      enum pop-lookup-path {
        description "Pop and Lookup Path";
      }
    }
    description "Mgmt static path";
  }
  typedef Static-ipv6-address {
    type inet:ipv6-address;
    description "Static ipv6 address";
  }
  typedef Mgmt-static-addr {
    type enumeration {
      enum not-applicable {
        value 0;
        description "Not Applicable";
      }
      enum ipv4 {
        value 1;
        description "IPv4";
      }
      enum ipv6 {
        value 2;
        description "IPv6";
      }
    }
    description "Mgmt static addr";
  }
  typedef Mgmt-mpls-static-label-status {
    type enumeration {
      enum not-created {
        description "Label Not Created";
      }
      enum vrf-down {
        description "Label without active VRF";
      }
      enum rewrite-vrf-down {
        description "Rewrite without active VRF";
      }
      enum lsd-disconnected {
        description "LSD is disconnected";
      }
      enum lsd-failed {
        description "LSD operation failed";
      }
      enum wait-for-lsd-reply {
        description "Waiting for LSD operation";
      }
      enum label-created {
        description "Label Created";
      }
      enum label-create-failed {
        description "Label Creation Failed";
      }
      enum label-rewrite-failed {
        description "Rewrite Creation Failed";
      }
      enum rewrite-next-hop-interface-down {
        description "Rewrite NextHop Down ";
      }
      enum label-discrepancy {
        description "Label Discrepancy ";
      }
      enum rewrite-discrepancy {
        description "Rewrite Discrepancy ";
      }
      enum label-status-unknown {
        description "Label Status Unknown";
      }
    }
    description "Mgmt mpls static label status";
  }
  typedef Mgmt-mpls-static-label-mode {
    type enumeration {
      enum none {
        description "No Label Mode";
      }
      enum per-prefix {
        description "Per-prefix Label";
      }
      enum per-vrf {
        description "Per-VRF label";
      }
      enum cross-connect {
        description "Label with crossconnect";
      }
    }
    description "Mgmt mpls static label mode";
  }

  grouping MPLS-STATIC-SUMMARY {
    description "Summary Information";
    leaf label-count {
      type uint32;
      description "Total Number of Labels";
    }
    leaf label-error-count {
      type uint32;
      description "Total Number of Labels with Errors";
    }
    leaf label-discrepancy-count {
      type uint32;
      description "Total Number of Labels with Discrepancies";
    }
    leaf vrf-count {
      type uint32;
      description "Total Number of VRF configured";
    }
    leaf active-vrf-count {
      type uint32;
      description "Total Number of Active VRF Active";
    }
    leaf interface-count {
      type uint32;
      description "Total Number of Interface";
    }
    leaf interface-foward-reference-count {
      type uint32;
      description "Total Number of Active Interface";
    }
    leaf mpls-enabled-interface-count {
      type uint32;
      description "Total Number of MPLS enabled Interface";
    }
    leaf ipv4-route-count {
      type uint32;
      description "Total Number of IPv4 Routes";
    }
    leaf ipv6-route-count {
      type uint32;
      description "Total Number of IPv6 Routes";
    }
    leaf lsd-connected {
      type boolean;
      description "LSD connection is up";
    }
    leaf im-connected {
      type boolean;
      description "IM is connected";
    }
    leaf rsi-connected {
      type boolean;
      description "RSI is connected";
    }
    leaf ribv4-connected {
      type boolean;
      description "RIBv4 is connected";
    }
    leaf ribv6-connected {
      type boolean;
      description "RIBv6 is connected";
    }
  }

  grouping MPLS-STATIC-LSP-PATH-NH-INFO {
    description "Path Nexthop Info";

    container address {
      description "Next-Hop IP Address";
      uses MPLS-STATIC-CTX-PREFIX-BAG;
    }
    leaf label {
      type uint32;
      description "Next-Hop Label";
    }
    leaf interface-name {
      type string;
      description "Next-Hop Interface Name";
    }
    leaf afi {
      type uint32;
      description "Next-Hop AFI";
    }
  }

  grouping MPLS-STATIC-LSP-PATH-INFO {
    description "Path Info";

    container nexthop {
      description "Nexthop information";
      uses MPLS-STATIC-LSP-PATH-NH-INFO;
    }
    leaf path-number {
      type uint32;
      description "Path Number";
    }
    leaf type {
      type Mgmt-static-path;
      description "Path Type";
    }
    leaf path-role {
      type Mpls-static-path-role;
      description "Path Role";
    }
    leaf path-id {
      type uint8;
      description "Path Id";
    }
    leaf backup-id {
      type uint8;
      description "Path Backup Id";
    }
    leaf status {
      type Mgmt-mpls-static-path-status;
      description "Path Status";
    }
  }

  grouping MPLS-STATIC-CTX-PREFIX-BAG {
    description "MPLS STATIC CTX PREFIX BAG";
    leaf af-name {
      type Mgmt-static-addr;
      description "AFName";
    }
    leaf ipv4-prefix {
      when "../af-name = 'ipv4'" {
        description "../AFName = 'IPv4'";
      }
      type inet:ipv4-address;
      description "IPv4 context";
    }
    leaf ipv6-prefix {
      when "../af-name = 'ipv6'" {
        description "../AFName = 'IPv6'";
      }
      type Static-ipv6-address;
      description "IPv6 context";
    }
  }

  grouping MPLS-STATIC-LBL-PREFIX-INFO {
    description "Prefix Information";

    container prefix {
      description "Prefix";
      uses MPLS-STATIC-CTX-PREFIX-BAG;
    }
    leaf prefix-length {
      type uint8;
      description "Prefix length";
    }
  }

  grouping MPLS-STATIC-LBL-INFO {
    description "Static Label and Prefix information";

    container prefix {
      description "Prefix Information";
      uses MPLS-STATIC-LBL-PREFIX-INFO;
    }

    container pathset-resolve-nh {
      description "Primary pathset resolve-nexthop IP Address";
      uses MPLS-STATIC-CTX-PREFIX-BAG;
    }

    container backup-pathset-resolve-nh {
      description "Backup pathset resolve-nexthop IP Address";
      uses MPLS-STATIC-CTX-PREFIX-BAG;
    }
    leaf label {
      type uint32;
      description "Label value";
    }
    leaf label-mode {
      type Mgmt-mpls-static-label-mode;
      description "Label Mode";
    }
    leaf label-status {
      type Mgmt-mpls-static-label-status;
      description "Label Status";
    }
    leaf vrf-name {
      type string;
      description "VRF name";
    }
    leaf pathset-via-resolve {
      type boolean;
      description "Primary Pathset as a result of resolve";
    }
    leaf backup-pathset-via-resolve {
      type boolean;
      description "Backup Pathset as a result of resolve";
    }
    leaf address-family {
      type Mgmt-static-addr;
      description "Address Family";
    }

    list path-info {
      description "Path Information";
      uses MPLS-STATIC-LSP-PATH-INFO;
    }

    list backup-path-info {
      description "Backup Path Information";
      uses MPLS-STATIC-LSP-PATH-INFO;
    }
  }

  grouping MPLS-STATIC-LSP-INFO {
    description "Static LSP information";

    container label {
      description "Label Information";
      uses MPLS-STATIC-LBL-INFO;
    }
    leaf lsp-name-xr {
      type string;
      description "LSP Name";
    }
  }
}
