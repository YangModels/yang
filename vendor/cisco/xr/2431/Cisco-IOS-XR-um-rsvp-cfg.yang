module Cisco-IOS-XR-um-rsvp-cfg {
  namespace "http://cisco.com/ns/yang/Cisco-IOS-XR-um-rsvp-cfg";
  prefix um-rsvp-cfg;

  import cisco-semver {
    prefix semver;
  }
  import Cisco-IOS-XR-types {
    prefix xr;
  }
  import ietf-inet-types {
    prefix inet;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR rsvp package configuration.
     
     This YANG module augments the
     modules with configuration data.
     
     Copyright (c) 2019-2023 by Cisco Systems, Inc.
     All rights reserved.";

  revision 2022-09-20 {
    description
      "Added missing CLI config for CLI keyword nodeid-subobject to nodes
       2022-08-10
         Added missing CLI config for CLI keyword retransmit-queue-depth to nodes
       2022-07-11
         Added missing description statement to nodes";
    semver:module-version "2.1.0";
  }
  revision 2021-01-28 {
    description
      "Added cisco-support task yang nodes";
    semver:module-version "2.0.0";
  }
  revision 2019-06-10 {
    description
      "- Added 'default' container under bandwidth which corredsponds to
         empty CLI keyword 'bandwidth'
       - Added necessary 'must' statement within bandwidth block
       - Established semantic version baseline.";
    semver:module-version "1.0.0";
  }
  revision 2019-03-30 {
    description
      "Initial version";
  }

  container rsvp {
    description
      "Global RSVP configuration commands";
    container interfaces {
      description
        "Enable RSVP on an interface";
      list interface {
        key "interface-name";
        description
          "Enable RSVP on an interface";
        leaf interface-name {
          type xr:Interface-name;
          description
            "Enable RSVP on an interface";
        }
        container bandwidth {
          description
            "Configure RSVP bandwidth parameters";
          container default {
            must "not(../rdm or ../percentage or ../global-pool or ../bc0 or ../total-reservable-bandwidth)";
            presence "Indicates a default node is configured.";
            description
              "Configure RSVP default bandwidth";
          }
          container rdm {
            must "not(../default or ../percentage or ../global-pool or ../bc0 or ../total-reservable-bandwidth) and ((percentage and not(total-reservable-bandwidth or global-pool or bc0)) or (total-reservable-bandwidth and not(percentage or global-pool or bc0)) or (global-pool and not(percentage or total-reservable-bandwidth or bc0)) or (bc0 and not(percentage or total-reservable-bandwidth or global-pool)))";
            presence "Indicates a rdm node is configured.";
            description
              "Configure bandwidth as Russian Doll Model";
            container percentage {
              must "((total-reservable-bandwidth and not(global-pool or bc0)) or (global-pool and not(total-reservable-bandwidth or bc0)) or (bc0 and not(total-reservable-bandwidth or global-pool)))";
              presence "Indicates a percentage node is configured.";
              description
                "Supply bandwidths as percentages of physical link bandwidth";
              leaf total-reservable-bandwidth {
                type uint32 {
                  range "0..10000" {
                    description
                      "Total reservable bandwidth as percentage of physical link bandwidth";
                  }
                }
                description
                  "Total reservable bandwidth as percentage of physical link bandwidth";
              }
              leaf largest-reservable-flow {
                type uint32 {
                  range "0..10000" {
                    description
                      "Largest reservable flow as percentage of physical link bandwidth";
                  }
                }
                must "../total-reservable-bandwidth";
                description
                  "Largest reservable flow as percentage of physical link bandwidth";
              }
              container global-pool {
                presence "Indicates a global-pool node is configured.";
                description
                  "Configure bandwidth in global pool";
                leaf total-reservable-bandwidth {
                  type uint32 {
                    range "0..10000" {
                      description
                        "Total reservable bandwidth as percentage of physical link bandwidth";
                    }
                  }
                  mandatory true;
                  description
                    "Total reservable bandwidth as percentage of physical link bandwidth";
                }
                leaf largest-reservable-flow {
                  type uint32 {
                    range "0..10000" {
                      description
                        "Largest reservable flow as percentage of physical link bandwidth";
                    }
                  }
                  description
                    "Largest reservable flow as percentage of physical link bandwidth";
                }
              }
              container sub-pool {
                must "../total-reservable-bandwidth or ../global-pool";
                presence "Indicates a sub-pool node is configured.";
                description
                  "Configure bandwidth in sub-pool";
                leaf reservable-bandwidth {
                  type uint32 {
                    range "0..10000" {
                      description
                        "Reservable bandwidth in sub-pool as percentage of physical link bandwidth";
                    }
                  }
                  mandatory true;
                  description
                    "Reservable bandwidth in sub-pool";
                }
              }
              container bc0 {
                presence "Indicates a bc0 node is configured.";
                description
                  "Configure bandwidth in BC0 pool";
                leaf total-reservable-bandwidth {
                  type uint32 {
                    range "0..10000" {
                      description
                        "Total reservable bandwidth as percentage of physical link bandwidth";
                    }
                  }
                  mandatory true;
                  description
                    "Total reservable bandwidth as percentage of physical link bandwidth";
                }
                leaf largest-reservable-flow {
                  type uint32 {
                    range "0..10000" {
                      description
                        "Largest reservable flow as percentage of physical link bandwidth";
                    }
                  }
                  description
                    "Largest reservable flow as percentage of physical link bandwidth";
                }
                container bc1 {
                  presence "Indicates a bc1 node is configured.";
                  description
                    "Configure bandwidth in BC1 pool";
                  leaf reservable-bandwidth {
                    type uint32 {
                      range "0..10000" {
                        description
                          "Reservable bandwidth in sub-pool as percentage of physical link bandwidth";
                      }
                    }
                    mandatory true;
                    description
                      "Reservable bandwidth in sub-pool";
                  }
                }
              }
            }
            leaf total-reservable-bandwidth {
              type uint32 {
                range "0..4294967295" {
                  description
                    "Total reservable bandwidth (in Kbps)";
                }
              }
              description
                "Total reservable bandwidth as percentage of physical link bandwidth";
            }
            leaf largest-reservable-flow {
              type uint32 {
                range "0..4294967295" {
                  description
                    "Largest reservable flow (in Kbps)";
                }
              }
              must "../total-reservable-bandwidth";
              description
                "Largest reservable flow as percentage of physical link bandwidth";
            }
            container global-pool {
              presence "Indicates a global-pool node is configured.";
              description
                "Configure bandwidth in global pool";
              leaf total-reservable-bandwidth {
                type uint32 {
                  range "0..4294967295" {
                    description
                      "Total reservable bandwidth (in Kbps)";
                  }
                }
                mandatory true;
                description
                  "Total reservable bandwidth as percentage of physical link bandwidth";
              }
              leaf largest-reservable-flow {
                type uint32 {
                  range "0..4294967295" {
                    description
                      "Largest reservable flow (in Kbps)";
                  }
                }
                description
                  "Largest reservable flow as percentage of physical link bandwidth";
              }
            }
            container sub-pool {
              must "../total-reservable-bandwidth or ../global-pool";
              presence "Indicates a sub-pool node is configured.";
              description
                "Configure bandwidth in sub-pool";
              leaf reservable-bandwidth {
                type uint32 {
                  range "0..4294967295" {
                    description
                      "Reservable bandwidth in sub-pool (in Kbps)";
                  }
                }
                mandatory true;
                description
                  "Reservable bandwidth in sub-pool";
              }
            }
            container bc0 {
              presence "Indicates a bc0 node is configured.";
              description
                "Configure bandwidth in BC0 pool";
              leaf total-reservable-bandwidth {
                type uint32 {
                  range "0..4294967295" {
                    description
                      "Total reservable bandwidth (in Kbps)";
                  }
                }
                mandatory true;
                description
                  "Total reservable bandwidth as percentage of physical link bandwidth";
              }
              leaf largest-reservable-flow {
                type uint32 {
                  range "0..4294967295" {
                    description
                      "Largest reservable flow (in Kbps)";
                  }
                }
                description
                  "Largest reservable flow as percentage of physical link bandwidth";
              }
              container bc1 {
                presence "Indicates a bc1 node is configured.";
                description
                  "COnfigure bandwidth in BC1 pool";
                leaf reservable-bandwidth {
                  type uint32 {
                    range "0..4294967295" {
                      description
                        "Reservable bandwidth in sub-pool (in Kbps)";
                    }
                  }
                  mandatory true;
                  description
                    "Reservable bandwidth in sub-pool";
                }
              }
            }
          }
          container percentage {
            must "not(../default or ../rdm or ../global-pool or ../bc0 or ../total-reservable-bandwidth) and ((total-reservable-bandwidth and not(global-pool or bc0)) or (global-pool and not(total-reservable-bandwidth or bc0)) or (bc0 and not(total-reservable-bandwidth or global-pool)))";
            presence "Indicates a percentage node is configured.";
            description
              "Supply bandwidths as percentages of physical link bandwidth";
            leaf total-reservable-bandwidth {
              type uint32 {
                range "0..10000" {
                  description
                    "Total reservable bandwidth as percentage of physical link bandwidth";
                }
              }
              description
                "Total reservable bandwidth as percentage of physical link bandwidth";
            }
            leaf largest-reservable-flow {
              type uint32 {
                range "0..10000" {
                  description
                    "Largest reservable flow as percentage of physical link bandwidth";
                }
              }
              must "../total-reservable-bandwidth";
              description
                "Largest reservable flow as percentage of physical link bandwidth";
            }
            container global-pool {
              presence "Indicates a global-pool node is configured.";
              description
                "Configure bandwidth in global pool";
              leaf total-reservable-bandwidth {
                type uint32 {
                  range "0..10000" {
                    description
                      "Total reservable bandwidth as percentage of physical link bandwidth";
                  }
                }
                mandatory true;
                description
                  "Total reservable bandwidth as percentage of physical link bandwidth";
              }
              leaf largest-reservable-flow {
                type uint32 {
                  range "0..10000" {
                    description
                      "Largest reservable flow as percentage of physical link bandwidth";
                  }
                }
                description
                  "Largest reservable flow as percentage of physical link bandwidth";
              }
            }
            container sub-pool {
              must "../total-reservable-bandwidth or ../global-pool";
              presence "Indicates a sub-pool node is configured.";
              description
                "Configure bandwidth in sub-pool";
              leaf reservable-bandwidth {
                type uint32 {
                  range "0..10000" {
                    description
                      "Reservable bandwidth in sub-pool as percentage of physical link bandwidth";
                  }
                }
                mandatory true;
                description
                  "Reservable bandwidth in sub-pool";
              }
            }
            container bc0 {
              presence "Indicates a bc0 node is configured.";
              description
                "Configure bandwidth in BC0 pool";
              leaf total-reservable-bandwidth {
                type uint32 {
                  range "0..10000" {
                    description
                      "Total reservable bandwidth as percentage of physical link bandwidth";
                  }
                }
                mandatory true;
                description
                  "Total reservable bandwidth as percentage of physical link bandwidth";
              }
              leaf largest-reservable-flow {
                type uint32 {
                  range "0..10000" {
                    description
                      "Largest reservable flow as percentage of physical link bandwidth";
                  }
                }
                description
                  "Largest reservable flow as percentage of physical link bandwidth";
              }
              container bc1 {
                presence "Indicates a bc1 node is configured.";
                description
                  "Configure bandwidth in BC1 pool";
                leaf reservable-bandwidth {
                  type uint32 {
                    range "0..10000" {
                      description
                        "Reservable bandwidth in sub-pool as percentage of physical link bandwidth";
                    }
                  }
                  mandatory true;
                  description
                    "Reservable bandwidth in sub-pool";
                }
              }
            }
          }
          container global-pool {
            must "not(../default or ../rdm or ../percentage or ../bc0 or ../total-reservable-bandwidth)";
            presence "Indicates a global-pool node is configured.";
            description
              "Configure bandwidth in global pool";
            leaf total-reservable-bandwidth {
              type uint32 {
                range "0..4294967295" {
                  description
                    "Total reservable bandwidth (in Kbps)";
                }
              }
              mandatory true;
              description
                "Total reservable bandwidth as percentage of physical link bandwidth";
            }
            leaf largest-reservable-flow {
              type uint32 {
                range "0..4294967295" {
                  description
                    "Largest reservable flow (in Kbps)";
                }
              }
              description
                "Largest reservable flow as percentage of physical link bandwidth";
            }
          }
          container sub-pool {
            must "../total-reservable-bandwidth or ../global-pool";
            presence "Indicates a sub-pool node is configured.";
            description
              "Configure bandwidth in sub-pool";
            leaf reservable-bandwidth {
              type uint32 {
                range "0..4294967295" {
                  description
                    "Reservable bandwidth in sub-pool (in Kbps)";
                }
              }
              mandatory true;
              description
                "Reservable bandwidth in sub-pool";
            }
          }
          container bc0 {
            must "not(../default or ../rdm or ../percentage or ../global-pool or ../total-reservable-bandwidth)";
            presence "Indicates a bc0 node is configured.";
            description
              "Configure bandwidth in BC0 pool";
            leaf total-reservable-bandwidth {
              type uint32 {
                range "0..4294967295" {
                  description
                    "Total reservable bandwidth (in Kbps)";
                }
              }
              mandatory true;
              description
                "Total reservable bandwidth as percentage of physical link bandwidth";
            }
            leaf largest-reservable-flow {
              type uint32 {
                range "0..4294967295" {
                  description
                    "Largest reservable flow (in Kbps)";
                }
              }
              description
                "Largest reservable flow as percentage of physical link bandwidth";
            }
            container bc1 {
              presence "Indicates a bc1 node is configured.";
              description
                "Configure bandwidth in BC1 pool";
              leaf reservable-bandwidth {
                type uint32 {
                  range "0..4294967295" {
                    description
                      "Reservable bandwidth in sub-pool (in Kbps)";
                  }
                }
                mandatory true;
                description
                  "Reservable bandwidth in sub-pool";
              }
            }
          }
          leaf total-reservable-bandwidth {
            type uint32 {
              range "0..4294967295" {
                description
                  "Total reservable bandwidth (in Kbps)";
              }
            }
            must "not(../default or ../rdm or ../percentage or ../global-pool or ../bc0)";
            description
              "Total reservable bandwidth as percentage of physical link bandwidth";
          }
          leaf largest-reservable-flow {
            type uint32 {
              range "0..4294967295" {
                description
                  "Largest reservable flow (in Kbps)";
              }
            }
            must "../total-reservable-bandwidth";
            description
              "Largest reservable flow as percentage of physical link bandwidth";
          }
          container mam {
            description
              "Maximum Allocation Model";
            container percentage {
              description
                "Supply bandwidths as percentages of physical link bandwidth";
              container max-reservable-bw {
                presence "Indicates a max-reservable-bw node is configured.";
                description
                  "Maximum reservable bandwidth";
                leaf total-reservable-bandwidth {
                  type uint32 {
                    range "0..10000" {
                      description
                        "Total reservable bandwidth as percentage of physical link bandwidth";
                    }
                  }
                  description
                    "Total reservable bandwidth as percentage of physical link bandwidth";
                }
                leaf largest-reservable-flow {
                  type uint32 {
                    range "0..10000" {
                      description
                        "Largest reservable flow as percentage of physical link bandwidth";
                    }
                  }
                  must "../total-reservable-bandwidth";
                  description
                    "Largest reservable flow as percentage of physical link bandwidth";
                }
                leaf bc0 {
                  type uint32 {
                    range "0..10000" {
                      description
                        "Reservable bandwidth in bc0 as percentage of physical link bandwidth";
                    }
                  }
                  description
                    "Reservable bandwidth in bc0";
                }
                leaf bc1 {
                  type uint32 {
                    range "0..10000" {
                      description
                        "Reservable bandwidth in bc1 as percentage of physical link bandwidth";
                    }
                  }
                  must "../bc0";
                  description
                    "Reservable bandwidth in bc1";
                }
              }
            }
            container max-reservable-bw {
              presence "Indicates a max-reservable-bw node is configured.";
              description
                "Maximum reservable bandwidth";
              leaf total-reservable-bandwidth {
                type uint32 {
                  range "0..4294967295" {
                    description
                      "Total reservable bandwidth (in Kbps)";
                  }
                }
                description
                  "Total reservable bandwidth as percentage of physical link bandwidth";
              }
              leaf largest-reservable-flow {
                type uint32 {
                  range "0..4294967295" {
                    description
                      "Largest reservable flow (in Kbps)";
                  }
                }
                must "../total-reservable-bandwidth";
                description
                  "Largest reservable flow as percentage of physical link bandwidth";
              }
              leaf bc0 {
                type uint32 {
                  range "0..4294967295" {
                    description
                      "Reservable bandwidth in bc0 (in Kbps)";
                  }
                }
                description
                  "Reservable bandwidth in bc0";
              }
              leaf bc1 {
                type uint32 {
                  range "0..4294967295" {
                    description
                      "Reservable bandwidth in bc1 (in Kbps, Mbps or Gbps)";
                  }
                }
                must "../bc0";
                description
                  "Reservable bandwidth in bc1";
              }
            }
          }
        }
        container signalling {
          description
            "Configure RSVP signalling parameters";
          leaf dscp {
            type uint32 {
              range "0..63" {
                description
                  "Differentiated Services Code Point (DSCP)";
              }
            }
            description
              "Set DSCP for RSVP signalling messages";
          }
          container rate-limit {
            description
              "Configure message rate limit (pacing) options";
            container enable {
              presence "Indicates a enable node is configured.";
              description
                "Enable message rate limit";
            }
            leaf rate {
              type uint32 {
                range "1..500" {
                  description
                    "Number of messages to be sent per interval";
                }
              }
              must "../interval";
              description
                "Set message rate";
            }
            leaf interval {
              type uint32 {
                range "250..2000" {
                  description
                    "Size of an interval (milliseconds)";
                }
              }
              description
                "Set scheduling interval";
            }
          }
          container refresh {
            description
              "Configure refresh options";
            leaf interval {
              type uint32 {
                range "10..180" {
                  description
                    "Refresh interval (seconds)";
                }
              }
              description
                "Set interval between successive refreshes";
            }
            leaf missed {
              type uint32 {
                range "1..8" {
                  description
                    "Number of Messages";
                }
              }
              description
                "Set max number of consecutive missed messages for state expiry";
            }
            container out-of-band {
              description
                "Configure refresh options for out-of-band tunnels";
              leaf interval {
                type uint32 {
                  range "180..86400" {
                    description
                      "Refresh interval (seconds)";
                  }
                }
                description
                  "Set interval between successive refreshes";
              }
              leaf missed {
                type uint32 {
                  range "1..110000" {
                    description
                      "Number of Messages";
                  }
                }
                description
                  "Set max number of consecutive missed messages for state expiry";
              }
            }
            container reduction {
              description
                "Configure refresh reduction options";
              container disable {
                presence "Indicates a disable node is configured.";
                description
                  "Disable refresh reduction";
              }
              container reliable {
                description
                  "Configure refresh reduction reliability options";
                leaf ack-hold-time {
                  type uint32 {
                    range "100..5000" {
                      description
                        "ACK message hold time (milliseconds)";
                    }
                  }
                  description
                    "Set hold time for sending RSVP ACK message(s)";
                }
                leaf ack-max-size {
                  type uint32 {
                    range "20..65000" {
                      description
                        "Max size of an ACK message (bytes)";
                    }
                  }
                  description
                    "Set max size of a single RSVP ACK message";
                }
                leaf retransmit-time {
                  type uint32 {
                    range "100..10000" {
                      description
                        "Min time before RSVP messages retransmit (milliseconds)";
                    }
                  }
                  description
                    "Set min delay to wait for an ACK before a retransmit";
                }
                leaf retransmit-queue-depth {
                  type uint32 {
                    range "0..100000" {
                      description
                        "Number of sub-msgs queued for Rapid Retransmit";
                    }
                  }
                  description
                    "Set rapid retransmit queue depth";
                }
                container summary-refresh {
                  presence "Indicates a summary-refresh node is configured.";
                  description
                    "Configure use of reliable messaging for summary refresh";
                }
              }
              container summary {
                description
                  "Configure refresh reduction summary options";
                leaf max-size {
                  type uint32 {
                    range "20..65000" {
                      description
                        "Max size (bytes)";
                    }
                  }
                  description
                    "Set max size of a single RSVP summary refresh message";
                }
              }
              leaf bundle-max-size {
                type uint32 {
                  range "512..65000" {
                    description
                      "Max size (bytes)";
                  }
                }
                description
                  "Set max size of a single RSVP bundle message";
              }
            }
          }
          container hello {
            description
              "Configure Hello parameters";
            container graceful-restart {
              description
                "Configure Graceful-Restart Hello parameters";
              container interface-based {
                presence "Indicates a interface-based node is configured.";
                description
                  "Configure Interface-based Hello";
              }
            }
          }
        }
        container authentication {
          description
            "Configure RSVP authentication parameters";
          container key-source {
            description
              "Specify key-source for authenticating RSVP signalling messages";
            leaf key-chain {
              type xr:Cisco-ios-xr-string {
                length "1..32" {
                  description
                    "Name of key-chain";
                }
              }
              description
                "Use key-chain to authenticate RSVP signalling messages";
            }
          }
          leaf window-size {
            type uint32 {
              range "1..64" {
                description
                  "Window-size to restrict out of order messages";
              }
            }
            description
              "Use window-size to limit number of out-of-order messages";
          }
          leaf life-time {
            type uint32 {
              range "30..86400" {
                description
                  "Life-time (in seconds) for each security association";
              }
            }
            description
              "Use to associate life-time for each security association";
          }
        }
      }
    }
    container controllers {
      description
        "Enable RSVP on controller";
      list controller {
        key "controller-name";
        description
          "Enable RSVP on controller";
        leaf controller-name {
          type xr:Interface-name;
          description
            "Name of controller";
        }
        container signalling {
          description
            "Configure RSVP signalling parameters";
          container refresh {
            description
              "Configure refresh options";
            container out-of-band {
              description
                "Configure refresh options for out-of-band tunnels";
              leaf interval {
                type uint32 {
                  range "180..86400" {
                    description
                      "Refresh interval (seconds)";
                  }
                }
                description
                  "Set interval between successive refreshes";
              }
              leaf missed {
                type uint32 {
                  range "1..110000" {
                    description
                      "Number of Messages";
                  }
                }
                description
                  "Set max number of consecutive missed messages for state expiry";
              }
            }
          }
        }
      }
    }
    container signalling {
      description
        "Configure global RSVP signalling parameters";
      container graceful-restart {
        presence "Indicates a graceful-restart node is configured.";
        description
          "Configure RSVP Graceful-Restart parameters";
      }
      container graceful-restart-lsp-type {
        presence "Indicates a graceful-restart-lsp-type node is configured.";
        description
          "Configure to send LSP's ctype for Recovery and Suggested label";
      }
      leaf graceful-restart-recovery-time {
        type uint32 {
          range "0..3600" {
            description
              "Recovery time (seconds)";
          }
        }
        description
          "Configure the recovery-time";
      }
      leaf graceful-restart-restart-time {
        type uint32 {
          range "60..3600" {
            description
              "Restart time (seconds)";
          }
        }
        description
          "Configure the restart-time";
      }
      container hello {
        description
          "Configure Hello parameters";
        container graceful-restart {
          description
            "Configure Graceful-Restart Hello parameters";
          container refresh {
            description
              "Configure Graceful-Restart Hello refresh parameters";
            leaf interval {
              type uint32 {
                range "3000..30000" {
                  description
                    "Hello interval (milliseconds)";
                }
              }
              description
                "Set interval between successive Hello messages";
            }
            leaf misses {
              type uint32 {
                range "1..10" {
                  description
                    "Number of messages";
                }
              }
              description
                "Set max number of consecutive missed Hello messages";
            }
          }
        }
      }
      leaf event-per-pulse {
        type uint32 {
          range "0..1600" {
            description
              "Max event per Pulse";
          }
        }
        description
          "Set Max event sent per pulse";
      }
      container prefix-filtering {
        description
          "Enable prefix-filtering for an access-list";
        leaf access-list {
          type string {
            length "1..32" {
              description
                "Access list name - maximum 32 characters";
            }
          }
          description
            "Specify access-list name";
        }
        container default-deny-action {
          description
            "Action to take when ACL match returns default deny";
          container drop {
            presence "Indicates a drop node is configured.";
            description
              "Drop the packet";
          }
        }
      }
      container message-bundle {
        description
          "Sending bundled messages";
        container disable {
          presence "Indicates a disable node is configured.";
          description
            "Disable bundling of outgoing RSVP messages";
        }
      }
      container nodeid-subobject {
        description
          "Sending nodeid-subobject in RRO of Reservation";
        container disable {
          presence "Indicates a disable node is configured.";
          description
            "Disable inserting nodeid-subobject in RRO of Reservation";
        }
      }
      container patherr {
        description
          "Path Error message";
        container state-removal {
          description
            "State-Removal flag in Path Error message";
          container disable {
            presence "Indicates a disable node is configured.";
            description
              "Disable State-Removal flag for Path Error";
          }
        }
      }
      container checksum {
        description
          "RSVP message checksum computation";
        container disable {
          presence "Indicates a disable node is configured.";
          description
            "Disable RSVP message checksum computation/validation";
        }
      }
      container out-of-band {
        description
          "Configure out-of-band signalling parameters";
        leaf vrf {
          type xr:Cisco-ios-xr-string {
            length "1..32" {
              description
                "VRF name";
            }
          }
          description
            "VRF used for out-of-band control signalling";
        }
      }
    }
    container authentication {
      description
        "Configure RSVP authentication parameters";
      container key-source {
        description
          "Specify key-source for authenticating RSVP signalling messages";
        leaf key-chain {
          type xr:Cisco-ios-xr-string {
            length "1..32" {
              description
                "Name of key-chain";
            }
          }
          description
            "Use key-chain to authenticate RSVP signalling messages";
        }
      }
      leaf window-size {
        type uint32 {
          range "1..64" {
            description
              "Window-size to restrict out of order messages";
          }
        }
        description
          "Use window-size to limit number of out-of-order messages";
      }
      leaf life-time {
        type uint32 {
          range "30..86400" {
            description
              "Life-time (in seconds) for each security association";
          }
        }
        description
          "Use to associate life-time for each security association";
      }
      leaf retransmit {
        type uint32 {
          range "0..10000" {
            description
              "Number of states to retransmit when messages are dropped to prevent OOS.";
          }
        }
        description
          "Configure retransmit options";
      }
    }
    container neighbors {
      description
        "Configure RSVP neighbors for RSVP authentication";
      list neighbor {
        key "neighbor-address";
        description
          "Configure RSVP neighbors for RSVP authentication";
        leaf neighbor-address {
          type inet:ipv4-address-no-zone;
          description
            "Configure RSVP neighbors for RSVP authentication";
        }
        container authentication {
          description
            "Configure RSVP authentication parameters";
          container key-source {
            description
              "Specify key-source for authenticating RSVP signalling messages";
            leaf key-chain {
              type string {
                length "1..32" {
                  description
                    "Name of key-chain";
                }
              }
              description
                "Use key-chain to authenticate RSVP signalling messages";
            }
          }
          leaf window-size {
            type uint32 {
              range "1..64" {
                description
                  "Window-size to restrict out of order messages";
              }
            }
            description
              "Use window-size to limit number of out-of-order messages";
          }
          leaf life-time {
            type uint32 {
              range "30..86400" {
                description
                  "Life-time (in seconds) for each security association";
              }
            }
            description
              "Use to associate life-time for each security association";
          }
        }
      }
    }
    container bandwidth {
      description
        "Configure RSVP default I/F bandwidth parameters";
      container mam {
        description
          "Maximum Allocation Model";
        container percentage {
          description
            "Supply bandwidths as percentages of physical link bandwidth";
          container max-reservable {
            presence "Indicates a max-reservable node is configured.";
            description
              "Maximum reservable bandwidth";
            leaf max-reservable-bandwidth {
              type uint32 {
                range "0..10000" {
                  description
                    "B/W I/F percentage";
                }
              }
              mandatory true;
              description
                "Maximum reservable bandwidth";
            }
            leaf bc0 {
              type uint32 {
                range "0..10000" {
                  description
                    "B/W I/F percentage";
                }
              }
              description
                "BC0 pool";
            }
            leaf bc1 {
              type uint32 {
                range "0..10000" {
                  description
                    "B/W I/F percentage";
                }
              }
              description
                "BC1 pool";
            }
          }
        }
      }
      container rdm {
        description
          "Russian Doll Model";
        container percentage {
          description
            "Supply bandwidths as percentages of physical link bandwidth";
          container max-reservable-bc0 {
            presence "Indicates a max-reservable-bc0 node is configured.";
            description
              "Maximum reservable/BC0";
            leaf bc0 {
              type uint32 {
                range "0..10000" {
                  description
                    "B/W I/F percentage";
                }
              }
              mandatory true;
              description
                "Maximum reservable/BC0";
            }
            leaf bc1 {
              type uint32 {
                range "0..10000" {
                  description
                    "B/W I/F percentage";
                }
              }
              description
                "BC1 pool";
            }
          }
        }
      }
    }
    container latency {
      description
        "Set the latency attributes";
      leaf threshold {
        type uint32 {
          range "0..180" {
            description
              "Set the latency threshold to a time in seconds";
          }
        }
        description
          "Set the latency threshold to a value in seconds (default 60)";
      }
    }
    container logging {
      description
        "RSVP logging configuration";
      container events {
        description
          "Global logging events";
        container nsr {
          presence "Indicates a nsr node is configured.";
          description
            "Enable NSR Status Logging";
        }
        container issu {
          presence "Indicates a issu node is configured.";
          description
            "Enable ISSU Status Logging";
        }
      }
    }
    container ltrace-buffer {
      description
        "RSVP trace buffer files";
      container multiplier {
        presence "Indicates a multiplier node is configured.";
        description
          "trace buffer file size multiplier";
        leaf multiplier-factor {
          type uint32 {
            range "2..6" {
              description
                "Multiplier factor";
            }
          }
          mandatory true;
          description
            "trace buffer file size multiplier";
        }
        container rare {
          presence "Indicates a rare node is configured.";
          description
            "Rare trace buffer";
        }
        container common {
          presence "Indicates a common node is configured.";
          description
            "Common trace buffer";
        }
        container sig {
          presence "Indicates a sig node is configured.";
          description
            "Signalling trace buffer";
        }
        container sig-err {
          presence "Indicates a sig-err node is configured.";
          description
            "Signalling errors trace buffer";
        }
        container intf {
          presence "Indicates a intf node is configured.";
          description
            "Interface trace buffer";
        }
        container dbg-err {
          presence "Indicates a dbg-err node is configured.";
          description
            "Debug errors trace buffer";
        }
        container sync {
          presence "Indicates a sync node is configured.";
          description
            "Sync trace buffer";
        }
      }
    }
  }
}
