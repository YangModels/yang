module Cisco-IOS-XR-um-8000-controller-fabric-cfg {
  namespace "http://cisco.com/ns/yang/Cisco-IOS-XR-um-8000-controller-fabric-cfg";
  prefix um-8000-controller-fabric-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR 8000-controller-fabric package configuration.
     
     This YANG module augments the
     modules with configuration data.
     
     Copyright (c) 2021-2022 by Cisco Systems, Inc.
     All rights reserved.";

  revision 2021-08-19 {
    description
      "Initial release";
    semver:module-version "1.0.0";
  }

  container controller-fabric {
    description
      "Configure Fabric";
    container planes {
      description
        "Configure Fabric Plane";
      list plane {
        must "shutdown";
        key "plane-id";
        description
          "Configure Fabric Plane";
        leaf plane-id {
          type uint32 {
            range "0..7" {
              description
                "Fabric Plane number";
            }
          }
          description
            "Configure Fabric Plane";
        }
        container shutdown {
          presence "Indicates a shutdown node is configured.";
          description
            "Shutdown the fabric data plane";
        }
      }
    }
    container mode {
      description
        "Configure Fabric Mode as either 8FC or 5FC";
      container five-fc {
        presence "Indicates a five-fc node is configured.";
        description
          "5 Fabric Card mode, default is 8 FC";
        container fc-0-2-4-5-6 {
          presence "Indicates a fc-0-2-4-5-6 node is configured.";
          description
            "FC Slots 0,2,4,5 and 6";
        }
      }
    }
  }
}
