module Cisco-IOS-XR-um-mibs-eventmib-cfg {
  namespace "http://cisco.com/ns/yang/Cisco-IOS-XR-um-mibs-eventmib-cfg";
  prefix um-mibs-eventmib-cfg;

  import Cisco-IOS-XR-types {
    prefix xr;
  }
  import Cisco-IOS-XR-um-snmp-server-cfg {
    prefix a1;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR mibs-eventmib package configuration.
     
     This YANG module augments the
     modules with configuration data.
     
     Copyright (c) 2021-2022 by Cisco Systems, Inc.
     All rights reserved.";

  revision 2022-07-11 {
    description
      "Added missing description statement to nodes";
    semver:module-version "1.0.0";
  }
  revision 2021-06-29 {
    description
      "Initial release";
    semver:module-version "1.0.0";
  }

  augment "/a1:snmp-server-mibs" {
    description
      "This augment extends snmp-server-mibs nodes
       configuration";
    container eventmib {
      description
        "Event MIB configuration";
      container packet-losses {
        description
          "Packet Loss threshold monitoring";
        list packet-loss {
          key "packet-loss-name";
          description
            "Packet Loss threshold monitoring";
          leaf packet-loss-name {
            type xr:Interface-name;
            description
              "Packet Loss threshold monitoring";
          }
          leaf rising {
            type uint32 {
              range "0..2147483647" {
                description
                  "Trigger Trap when Delta above this value";
              }
            }
            description
              "Upper threshold value";
          }
          leaf falling {
            type uint32 {
              range "0..2147483647" {
                description
                  "Trigger Trap when Delta below this value";
              }
            }
            description
              "Lower threshold value";
          }
          leaf interval {
            type uint32 {
              range "5..1440" {
                description
                  "Interval in multiples of 5 mins";
              }
            }
            description
              "Packet loss sampling interval in multiples of 5 mins";
          }
        }
      }
      container congestion-controls {
        description
          "Congestion Control threshold monitoring";
        list congestion-control {
          key "congestion-control-name";
          description
            "Congestion Control threshold monitoring";
          leaf congestion-control-name {
            type xr:Interface-name;
            description
              "Congestion Control threshold monitoring";
          }
          leaf rising {
            type uint32 {
              range "0..100" {
                description
                  "Threshold as configured percentage bandwidth of interface ";
              }
            }
            description
              "Upper threshold value";
          }
          leaf falling {
            type uint32 {
              range "0..100" {
                description
                  "Threshold as configured percentage bandwidth of interface ";
              }
            }
            description
              "Lower threshold value";
          }
          leaf interval {
            type uint32 {
              range "5..1440" {
                description
                  "Interval in multiples of 5 mins";
              }
            }
            description
              "Congestion control sampling interval in multiples of 5 mins";
          }
        }
      }
    }
  }
}
