module Cisco-IOS-XR-controller-fc-oper {
  namespace "http://cisco.com/ns/yang/Cisco-IOS-XR-controller-fc-oper";
  prefix controller-fc-oper;

  import Cisco-IOS-XR-types {
    prefix xr;
  }
  import cisco-semver {
    prefix semver;
  }
  include Cisco-IOS-XR-controller-fc-oper-sub1 {
    revision-date 2021-11-10;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR controller-fc package operational data.
     
     This module contains definitions
     for the following management objects:
       fibre-channel: Fiber Channel Controller operational data
     
     Copyright (c) 2013-2021 by Cisco Systems, Inc.
     All rights reserved.";

  revision 2021-11-10 {
    description
      "Added LED state field and made BER threshold as optional.
       2021-10-10
         Added new container FC-CTLR-AINS-INFO under FC-CTLR-AINS-INFO.
       2021-08-22
         fc_ctrlr_prbs_framing,fc_ctrlr_prbs_dir andfc_ctrlr_prbs_err_inject";
    semver:module-version "1.0.1M";
  }
  revision 2021-06-30 {
    description
      "sf-ber-threshold and sd-ber-threshold added in fc_ctrlr_port_info bag";
    semver:module-version "1.0.0";
  }
  revision 2021-04-20 {
    description
      "Fibre Channel controller oper model added";
  }
  revision 2019-04-05 {
    description
      "Establish semantic version baseline.";
  }
  revision 2015-11-09 {
    description
      "IOS XR 6.0 revision.";
  }

  container fibre-channel {
    config false;
    description
      "Fiber Channel Controller operational data";
    container fc-controllers {
      description
        "List of FC controllers";
      list fc-controller {
        key "controller-name";
        description
          "Fibre Channel controller";
        container fc-controller-info {
          description
            "Port info of Fibre Channel controller";
          uses FC-CTRLR-PORT-INFO;
        }
        container prbs-info {
          description
            "PRBS info of Fibre Channel controller";
          uses FC-CTRLR-PRBS-INFO;
        }
        leaf controller-name {
          type xr:Interface-name;
          description
            "Controller name";
        }
      }
    }
  }
}
