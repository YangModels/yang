module cisco-xr-openconfig-system-deviations {


  namespace "http://cisco.com/ns/yang/cisco-xr-openconfig-system-deviations";
  prefix  "oc-sysdevs";

  import openconfig-system { prefix oc-sys; }

  organization "Cisco Systems, Inc.";

  contact
    "Cisco Systems, Inc.
     Customer Service

     Postal: 170 West Tasman Drive
     San Jose, CA 95134

     Tel: +1 800 553-NETS

     E-mail: cs-yang@cisco.com";

  description
    "This module contains a set of deviations for 
 
     openconfig-system.yang 

     on Cisco IOS-XR devices.

     Copyright (c) 2016-2019, 2022 by Cisco Systems, Inc.
     All rights reserved.";

  revision "2018-12-12" {
    description
      "Initial revision applicable to IOS-XR 7.0.1";
  }

  deviation /oc-sys:system/oc-sys:logging/oc-sys:console/oc-sys:selectors/oc-sys:selector/oc-sys:facility {
    deviate replace {
      type string;
    }
  }

  deviation /oc-sys:system/oc-sys:logging/oc-sys:console/oc-sys:selectors/oc-sys:selector/oc-sys:config/oc-sys:facility {
    deviate not-supported;
  }

  deviation
      /oc-sys:system/oc-sys:logging/oc-sys:console/oc-sys:selectors/oc-sys:selector/oc-sys:state/oc-sys:facility {
    deviate not-supported;
  }

  deviation /oc-sys:system/oc-sys:logging/oc-sys:remote-servers/oc-sys:remote-server/oc-sys:config/oc-sys:source-address {
    deviate not-supported;
  }

  deviation /oc-sys:system/oc-sys:logging/oc-sys:remote-servers/oc-sys:remote-server/oc-sys:state/oc-sys:source-address {
    deviate not-supported;
  }

  deviation /oc-sys:system/oc-sys:logging/oc-sys:remote-servers/oc-sys:remote-server/oc-sys:selectors/oc-sys:selector/oc-sys:facility {
    deviate replace {
      type string;
    }
  }

  deviation /oc-sys:system/oc-sys:logging/oc-sys:remote-servers/oc-sys:remote-server/oc-sys:selectors/oc-sys:selector/oc-sys:config/oc-sys:facility {
    deviate not-supported;
  }

  deviation /oc-sys:system/oc-sys:logging/oc-sys:remote-servers/oc-sys:remote-server/oc-sys:selectors/oc-sys:selector/oc-sys:state/oc-sys:facility {
    deviate not-supported;
  }

  deviation /oc-sys:system/oc-sys:ntp/oc-sys:config/oc-sys:ntp-source-address {
    deviate not-supported;
  }

  deviation /oc-sys:system/oc-sys:ntp/oc-sys:state/oc-sys:ntp-source-address {
    deviate not-supported;
  }

  deviation /oc-sys:system/oc-sys:ntp/oc-sys:state/oc-sys:auth-mismatch {
    deviate not-supported;
  }
  
  deviation /oc-sys:system/oc-sys:grpc-server/oc-sys:config/oc-sys:listen-addresses {
    deviate not-supported;
  }

  deviation /oc-sys:system/oc-sys:grpc-server/oc-sys:state/oc-sys:enable {
    deviate not-supported;
  }

  deviation /oc-sys:system/oc-sys:grpc-server/oc-sys:state/oc-sys:port {
    deviate not-supported;
  }

  deviation /oc-sys:system/oc-sys:grpc-server/oc-sys:state/oc-sys:transport-security {
    deviate not-supported;
  }

  deviation /oc-sys:system/oc-sys:grpc-server/oc-sys:state/oc-sys:certificate-id {
    deviate not-supported;
  }

  deviation /oc-sys:system/oc-sys:grpc-server/oc-sys:state/oc-sys:listen-addresses {
    deviate not-supported;
  }

  deviation /oc-sys:system/oc-sys:aaa/oc-sys:authentication/oc-sys:admin-user/oc-sys:config/oc-sys:admin-password {
    deviate not-supported;
  }

  deviation /oc-sys:system/oc-sys:aaa/oc-sys:authentication/oc-sys:admin-user/oc-sys:config/oc-sys:admin-password-hashed {
    deviate not-supported;
  }

  deviation /oc-sys:system/oc-sys:aaa/oc-sys:authentication/oc-sys:admin-user/oc-sys:state/oc-sys:admin-password {
    deviate not-supported;
  }

  deviation /oc-sys:system/oc-sys:aaa/oc-sys:authentication/oc-sys:admin-user/oc-sys:state/oc-sys:admin-password-hashed {
    deviate not-supported;
  }

  deviation /oc-sys:system/oc-sys:aaa/oc-sys:authentication/oc-sys:admin-user/oc-sys:state/oc-sys:admin-username {
    deviate not-supported;
  }

  deviation /oc-sys:system/oc-sys:aaa/oc-sys:authentication/oc-sys:users/oc-sys:user/oc-sys:config/oc-sys:ssh-key {
    deviate not-supported;
  }

  deviation /oc-sys:system/oc-sys:aaa/oc-sys:authentication/oc-sys:users/oc-sys:user/oc-sys:state/oc-sys:ssh-key {
    deviate not-supported;
  }

  deviation /oc-sys:system/oc-sys:aaa/oc-sys:server-groups/oc-sys:server-group/oc-sys:servers/oc-sys:server/oc-sys:config/oc-sys:name {
    deviate not-supported;
  }

  deviation /oc-sys:system/oc-sys:aaa/oc-sys:server-groups/oc-sys:server-group/oc-sys:servers/oc-sys:server/oc-sys:state/oc-sys:name {
    deviate not-supported;
  }

  deviation /oc-sys:system/oc-sys:aaa/oc-sys:server-groups/oc-sys:server-group/oc-sys:servers/oc-sys:server/oc-sys:state/oc-sys:connection-timeouts {
    deviate not-supported;
  }

  deviation /oc-sys:system/oc-sys:aaa/oc-sys:server-groups/oc-sys:server-group/oc-sys:servers/oc-sys:server/oc-sys:state/oc-sys:errors-received {
    deviate not-supported;
  }

  deviation /oc-sys:system/oc-sys:aaa/oc-sys:server-groups/oc-sys:server-group/oc-sys:servers/oc-sys:server/oc-sys:tacacs/oc-sys:config/oc-sys:source-address {
    deviate not-supported;
  }

  deviation /oc-sys:system/oc-sys:aaa/oc-sys:server-groups/oc-sys:server-group/oc-sys:servers/oc-sys:server/oc-sys:tacacs/oc-sys:state/oc-sys:source-address {
    deviate not-supported;
  }
  
  deviation /oc-sys:system/oc-sys:aaa/oc-sys:server-groups/oc-sys:server-group/oc-sys:servers/oc-sys:server/oc-sys:radius/oc-sys:config/oc-sys:auth-port {
    deviate not-supported;
  }

  deviation /oc-sys:system/oc-sys:aaa/oc-sys:server-groups/oc-sys:server-group/oc-sys:servers/oc-sys:server/oc-sys:radius/oc-sys:config/oc-sys:acct-port {
    deviate not-supported;
  }

  deviation /oc-sys:system/oc-sys:aaa/oc-sys:server-groups/oc-sys:server-group/oc-sys:servers/oc-sys:server/oc-sys:radius/oc-sys:config/oc-sys:secret-key {
    deviate not-supported;
  }

  deviation /oc-sys:system/oc-sys:aaa/oc-sys:server-groups/oc-sys:server-group/oc-sys:servers/oc-sys:server/oc-sys:radius/oc-sys:config/oc-sys:source-address {
    deviate not-supported;
  }

  deviation /oc-sys:system/oc-sys:aaa/oc-sys:server-groups/oc-sys:server-group/oc-sys:servers/oc-sys:server/oc-sys:radius/oc-sys:config/oc-sys:retransmit-attempts {
    deviate not-supported;
  }

  deviation /oc-sys:system/oc-sys:aaa/oc-sys:server-groups/oc-sys:server-group/oc-sys:servers/oc-sys:server/oc-sys:radius/oc-sys:state/oc-sys:auth-port {
    deviate not-supported;
  }

  deviation /oc-sys:system/oc-sys:aaa/oc-sys:server-groups/oc-sys:server-group/oc-sys:servers/oc-sys:server/oc-sys:radius/oc-sys:state/oc-sys:acct-port {
    deviate not-supported;
  }

  deviation /oc-sys:system/oc-sys:aaa/oc-sys:server-groups/oc-sys:server-group/oc-sys:servers/oc-sys:server/oc-sys:radius/oc-sys:state/oc-sys:secret-key {
    deviate not-supported;
  }

  deviation /oc-sys:system/oc-sys:aaa/oc-sys:server-groups/oc-sys:server-group/oc-sys:servers/oc-sys:server/oc-sys:radius/oc-sys:state/oc-sys:source-address {
    deviate not-supported;
  }

  deviation /oc-sys:system/oc-sys:aaa/oc-sys:server-groups/oc-sys:server-group/oc-sys:servers/oc-sys:server/oc-sys:radius/oc-sys:state/oc-sys:retransmit-attempts {
    deviate not-supported;
  }

  deviation /oc-sys:system/oc-sys:aaa/oc-sys:server-groups/oc-sys:server-group/oc-sys:servers/oc-sys:server/oc-sys:radius/oc-sys:state/oc-sys:counters/oc-sys:retried-access-requests {
    deviate not-supported;
  }

  deviation /oc-sys:system/oc-sys:aaa/oc-sys:server-groups/oc-sys:server-group/oc-sys:servers/oc-sys:server/oc-sys:radius/oc-sys:state/oc-sys:counters/oc-sys:access-accepts {
    deviate not-supported;
  }

  deviation /oc-sys:system/oc-sys:aaa/oc-sys:server-groups/oc-sys:server-group/oc-sys:servers/oc-sys:server/oc-sys:radius/oc-sys:state/oc-sys:counters/oc-sys:access-rejects {
    deviate not-supported;
  }

  deviation /oc-sys:system/oc-sys:aaa/oc-sys:server-groups/oc-sys:server-group/oc-sys:servers/oc-sys:server/oc-sys:radius/oc-sys:state/oc-sys:counters/oc-sys:timeout-access-requests {
    deviate not-supported;
  }

  deviation /oc-sys:system/oc-sys:telnet-server/oc-sys:config/oc-sys:enable {
    deviate not-supported;
  }

  deviation /oc-sys:system/oc-sys:telnet-server/oc-sys:config/oc-sys:timeout {
    deviate not-supported;
  }

  deviation /oc-sys:system/oc-sys:telnet-server/oc-sys:config/oc-sys:rate-limit {
    deviate not-supported;
  }

  deviation /oc-sys:system/oc-sys:telnet-server/oc-sys:config/oc-sys:session-limit {
    deviate not-supported;
  }

  deviation /oc-sys:system/oc-sys:telnet-server/oc-sys:state/oc-sys:enable {
    deviate not-supported;
  }

  deviation /oc-sys:system/oc-sys:telnet-server/oc-sys:state/oc-sys:timeout {
    deviate not-supported;
  }

  deviation /oc-sys:system/oc-sys:telnet-server/oc-sys:state/oc-sys:rate-limit {
    deviate not-supported;
  }

  deviation /oc-sys:system/oc-sys:telnet-server/oc-sys:state/oc-sys:session-limit {
    deviate not-supported;
  }

  deviation /oc-sys:system/oc-sys:processes/oc-sys:process {
    deviate not-supported;
  }

  deviation /oc-sys:system/oc-sys:config/oc-sys:domain-name {
    deviate not-supported;
  }

  deviation /oc-sys:system/oc-sys:state/oc-sys:domain-name {
    deviate not-supported;
  }

  deviation /oc-sys:system/oc-sys:messages/oc-sys:debug-entries/oc-sys:debug-service {
    deviate not-supported;
  }
}
//total deviations:62
