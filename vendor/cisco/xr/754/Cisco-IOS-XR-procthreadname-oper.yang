module Cisco-IOS-XR-procthreadname-oper {
  namespace "http://cisco.com/ns/yang/Cisco-IOS-XR-procthreadname-oper";
  prefix procthreadname-oper;

  import Cisco-IOS-XR-types {
    prefix xr;
  }
  import cisco-semver {
    prefix semver;
  }
  include Cisco-IOS-XR-procthreadname-oper-sub1 {
    revision-date 2022-07-07;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR procthreadname package operational data.
     
     This module contains definitions
     for the following management objects:
       processes-thread: Process statistics
     
     Copyright (c) 2013-2022 by Cisco Systems, Inc.
     All rights reserved.";

  revision 2022-07-07 {
    description
      "Removed container thread-name.";
    semver:module-version "1.0.1M";
  }
  revision 2019-05-28 {
    description
      "Initial version.";
    semver:module-version "1.0.0";
  }
  revision 2019-04-05 {
    description
      "Establish semantic version baseline.";
  }
  revision 2015-11-09 {
    description
      "IOS XR 6.0 revision.";
  }

  container processes-thread {
    config false;
    description
      "Process statistics";
    container nodes {
      description
        "List of nodes";
      list node {
        key "node-name";
        description
          "Node ID";
        leaf node-name {
          type xr:Node-id;
          description
            "Node name";
        }
        uses THREADLIST;
      }
    }
  }
}
