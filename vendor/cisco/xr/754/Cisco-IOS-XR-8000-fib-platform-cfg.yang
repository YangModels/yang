module Cisco-IOS-XR-8000-fib-platform-cfg {
  namespace "http://cisco.com/ns/yang/Cisco-IOS-XR-8000-fib-platform-cfg";
  prefix xr-8000-fib-platform-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR 8000-fib-platform package configuration.
     
     This module contains definitions
     for the following management objects:
       cef: Establish CEF configuration
     
     Copyright (c) 2013-2022 by Cisco Systems, Inc.
     All rights reserved.";

  revision 2022-03-01 {
    description
      "Updated max rotate value of hash rotate to 35";
    semver:module-version "1.0.1m";
  }
  revision 2019-04-05 {
    description
      "Establish semantic version baseline.";
    semver:module-version "1.0.0";
  }
  revision 2015-11-09 {
    description
      "IOS XR 6.0 revision.";
  }

  container cef {
    description
      "Establish CEF configuration";
    container load-balance {
      description
        "Specify Load balancing algorithm";
      container hash {
        description
          "Specify Hash adjust";
        leaf rotate {
          type uint32 {
            range "1..35";
          }
          description
            "Router-ID is bypassed when hash rotate count
             is used";
        }
      }
    }
  }
}
