module Cisco-IOS-XR-platforms-ofa-table-stats-oper {
  namespace "http://cisco.com/ns/yang/Cisco-IOS-XR-platforms-ofa-table-stats-oper";
  prefix platforms-ofa-table-stats-oper;

  import Cisco-IOS-XR-types {
    prefix xr;
  }
  import cisco-semver {
    prefix semver;
  }
  include Cisco-IOS-XR-platforms-ofa-table-stats-oper-sub1 {
    revision-date 2022-10-20;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR platforms-ofa-table-stats package operational data.
     
     This module contains definitions
     for the following management objects:
       ofa: OFA Data
     
     Copyright (c) 2013-2022 by Cisco Systems, Inc.
     All rights reserved.";

  revision 2022-10-20 {
    description
      "Added iptnldecapsaf
       2021-09-22
         Removal of mplspweport OFA object
       2021-09-22
         Adding dot1x support
       2021-07-07
         Added Quaratine DB counters to ofa table stats";
    semver:module-version "3.0.1M";
  }
  revision 2020-06-19 {
    description
      "Bwalk Error Counters IosSetYangSchemaRev Cisco-IOS-XR-platforms-ofa-table-stats-oper";
    semver:module-version "3.0.0";
  }
  revision 2019-12-14 {
    description
      "Added the Yang Model for ofa sw resources";
    semver:module-version "1.1.0";
  }
  revision 2019-06-06 {
    description
      "Added the Yang Model for ofa sw resources";
    semver:module-version "1.0.0";
  }
  revision 2019-04-05 {
    description
      "Establish semantic version baseline.";
  }
  revision 2015-11-09 {
    description
      "IOS XR 6.0 revision.";
  }

  typedef Ofa-table {
    type enumeration {
      enum "test-if" {
        value 0;
        description
          "test if";
      }
      enum "test-if-with-create-reject" {
        value 1;
        description
          "testifwithcreatereject";
      }
      enum "test-nh" {
        value 2;
        description
          "test nh";
      }
      enum "test-global-discard" {
        value 3;
        description
          "testglobaldiscard";
      }
      enum "test-nhg" {
        value 4;
        description
          "test nhg";
      }
      enum "test-rt" {
        value 5;
        description
          "test rt";
      }
      enum "test-dynhg" {
        value 6;
        description
          "testdynhg";
      }
      enum "test-async-nhg" {
        value 7;
        description
          "testasyncnhg";
      }
      enum "test-async-nhgstats" {
        value 8;
        description
          "testasyncnhgstats";
      }
      enum "test-ip-punt-policy" {
        value 9;
        description
          "test ippuntpolicy";
      }
      enum "test-punt" {
        value 10;
        description
          "test punt";
      }
      enum "test-punt-policy-stats" {
        value 11;
        description
          "testpuntpolicystats";
      }
      enum "test-async-update" {
        value 12;
        description
          "testasyncupdate";
      }
      enum "test-async-barrier-with-knob" {
        value 13;
        description
          "testasyncbarrierwithknob";
      }
      enum "test-async-barrier-with-outknob" {
        value 14;
        description
          "testasyncbarrierwithoutknob";
      }
      enum "test-o-fast-ats" {
        value 15;
        description
          "testofastats";
      }
      enum "test-o-fast-ats1" {
        value 16;
        description
          "testofastats1";
      }
      enum "test-o-fast-ats2" {
        value 17;
        description
          "testofastats2";
      }
      enum "test-dpastats1" {
        value 18;
        description
          "testdpastats1";
      }
      enum "test-dpastats2" {
        value 19;
        description
          "testdpastats2";
      }
      enum "test-srvgrid" {
        value 20;
        description
          "testsrvgrid";
      }
      enum "test-ddel-q" {
        value 21;
        description
          "test ddel q";
      }
      enum "test-mco-list" {
        value 22;
        description
          "testmcolist";
      }
      enum "test-syncmco-list" {
        value 23;
        description
          "testsyncmcolist";
      }
      enum "test-syncmctblstats" {
        value 24;
        description
          "testsyncmctblstats";
      }
      enum "test-dddp" {
        value 25;
        description
          "testdddp";
      }
      enum "test-grid1" {
        value 26;
        description
          "testgrid1";
      }
      enum "test-ssm" {
        value 27;
        description
          "testssm";
      }
      enum "test-encap-mgr" {
        value 28;
        description
          "testencapmgr";
      }
      enum "test-mplsrte" {
        value 29;
        description
          "testmplsrte";
      }
      enum "sys" {
        value 30;
        description
          "sys";
      }
      enum "npu" {
        value 31;
        description
          "npu";
      }
      enum "npu-host-port" {
        value 32;
        description
          "npuhostport";
      }
      enum "npuhwid" {
        value 33;
        description
          "npuhwid";
      }
      enum "optics-port" {
        value 34;
        description
          "opticsport";
      }
      enum "gi-port" {
        value 35;
        description
          "giport";
      }
      enum "l1-port" {
        value 36;
        description
          "l1port";
      }
      enum "mac-port" {
        value 37;
        description
          "macport";
      }
      enum "l2-port" {
        value 38;
        description
          "l2port";
      }
      enum "eth-port" {
        value 39;
        description
          "ethport";
      }
      enum "eth-ports-tats" {
        value 40;
        description
          "ethportstats";
      }
      enum "l2intf" {
        value 41;
        description
          "l2intf";
      }
      enum "l2if" {
        value 42;
        description
          "l2if";
      }
      enum "mplspwe-port" {
        value 43;
        description
          "mplspweport";
      }
      enum "mhpwe-port" {
        value 44;
        description
          "mhpweport";
      }
      enum "l2xc" {
        value 45;
        description
          "l2xc";
      }
      enum "l2vpnstats" {
        value 46;
        description
          "l2vpnstats";
      }
      enum "l1-ports-tats" {
        value 47;
        description
          "l1portstats";
      }
      enum "mac-ports-tats" {
        value 48;
        description
          "macportstats";
      }
      enum "l3intf" {
        value 49;
        description
          "l3intf";
      }
      enum "l3if" {
        value 50;
        description
          "l3if";
      }
      enum "l3intfrxstats" {
        value 51;
        description
          "l3intfrxstats";
      }
      enum "ip-route" {
        value 52;
        description
          "iproute";
      }
      enum "ip6-route" {
        value 53;
        description
          "ip6route";
      }
      enum "punt-policy-stats" {
        value 54;
        description
          "puntpolicystats";
      }
      enum "lpts-policy-stats" {
        value 55;
        description
          "lptspolicystats";
      }
      enum "tep" {
        value 56;
        description
          "tep";
      }
      enum "ip-punt-policy" {
        value 57;
        description
          "ippuntpolicy";
      }
      enum "ip6-punt-policy" {
        value 58;
        description
          "ip6puntpolicy";
      }
      enum "iplpts-policy" {
        value 59;
        description
          "iplptspolicy";
      }
      enum "ip6lpts-policy" {
        value 60;
        description
          "ip6lptspolicy";
      }
      enum "isis-punt-policy" {
        value 61;
        description
          "isispuntpolicy";
      }
      enum "isislpts-policy" {
        value 62;
        description
          "isislptspolicy";
      }
      enum "nh-group" {
        value 63;
        description
          "nhgroup";
      }
      enum "ipnh-group" {
        value 64;
        description
          "ipnhgroup";
      }
      enum "ip6nh-group" {
        value 65;
        description
          "ip6nhgroup";
      }
      enum "ipnh" {
        value 66;
        description
          "ipnh";
      }
      enum "ip6nh" {
        value 67;
        description
          "ip6nh";
      }
      enum "macllnh" {
        value 68;
        description
          "macllnh";
      }
      enum "ipvrf" {
        value 69;
        description
          "ipvrf";
      }
      enum "vrfid" {
        value 70;
        description
          "vrfid";
      }
      enum "mplsnh" {
        value 71;
        description
          "mplsnh";
      }
      enum "lspnh" {
        value 72;
        description
          "lspnh";
      }
      enum "encap-mgr" {
        value 73;
        description
          "encapmgr";
      }
      enum "mpls-label" {
        value 74;
        description
          "mplslabel";
      }
      enum "punt" {
        value 75;
        description
          "punt";
      }
      enum "punt-police-r" {
        value 76;
        description
          "puntpolicer";
      }
      enum "lpts-police-r" {
        value 77;
        description
          "lptspolicer";
      }
      enum "punt-lpts-police-r" {
        value 78;
        description
          "puntlptspolicer";
      }
      enum "punt-stats" {
        value 79;
        description
          "puntstats";
      }
      enum "tm-port" {
        value 80;
        description
          "tmport";
      }
      enum "span-session" {
        value 81;
        description
          "spansession";
      }
      enum "police-rstats" {
        value 82;
        description
          "policerstats";
      }
      enum "tm-ports-tats" {
        value 83;
        description
          "tmportstats";
      }
      enum "voq-grp" {
        value 84;
        description
          "voqgrp";
      }
      enum "l3intftxstats" {
        value 85;
        description
          "l3intftxstats";
      }
      enum "mplstetxstats" {
        value 86;
        description
          "mplstetxstats";
      }
      enum "mplslblstats" {
        value 87;
        description
          "mplslblstats";
      }
      enum "police-r" {
        value 88;
        description
          "policer";
      }
      enum "l2intfrxstats" {
        value 89;
        description
          "l2intfrxstats";
      }
      enum "l2intftxstats" {
        value 90;
        description
          "l2intftxstats";
      }
      enum "pbr-tt-ipv4" {
        value 91;
        description
          "pbr tt ipv4";
      }
      enum "pbr-tt-ipv6" {
        value 92;
        description
          "pbr tt ipv6";
      }
      enum "bfdhwoff" {
        value 93;
        description
          "bfdhwoff";
      }
      enum "bfdoff" {
        value 94;
        description
          "bfdoff";
      }
      enum "bfdoffstats" {
        value 95;
        description
          "bfdoffstats";
      }
      enum "global" {
        value 96;
        description
          "global";
      }
      enum "lag-port" {
        value 97;
        description
          "lagport";
      }
      enum "agg-port" {
        value 98;
        description
          "aggport";
      }
      enum "agg-member" {
        value 99;
        description
          "aggmember";
      }
      enum "qos-profile" {
        value 100;
        description
          "qosprofile";
      }
      enum "acl-profile" {
        value 101;
        description
          "acl profile";
      }
      enum "tmrate-profile" {
        value 102;
        description
          "tmrateprofile";
      }
      enum "ipacl" {
        value 103;
        description
          "ipacl";
      }
      enum "ip6acl" {
        value 104;
        description
          "ip6acl";
      }
      enum "sched-tree" {
        value 105;
        description
          "schedtree";
      }
      enum "tmcos" {
        value 106;
        description
          "tmcos";
      }
      enum "statsagg" {
        value 107;
        description
          "statsagg";
      }
      enum "nhprotect" {
        value 108;
        description
          "nhprotect";
      }
      enum "sampler" {
        value 109;
        description
          "sampler";
      }
      enum "l2qos" {
        value 110;
        description
          "l2qos";
      }
      enum "peer-qos" {
        value 111;
        description
          "peerqos";
      }
      enum "ipqos" {
        value 112;
        description
          "ipqos";
      }
      enum "ip6qos" {
        value 113;
        description
          "ip6qos";
      }
      enum "mplsqos" {
        value 114;
        description
          "mplsqos";
      }
      enum "qos-group" {
        value 115;
        description
          "qosgroup";
      }
      enum "qosid" {
        value 116;
        description
          "qosid";
      }
      enum "extlif" {
        value 117;
        description
          "extlif";
      }
      enum "elif" {
        value 118;
        description
          "elif";
      }
      enum "ingaclstats" {
        value 119;
        description
          "ingaclstats";
      }
      enum "egraclstats" {
        value 120;
        description
          "egraclstats";
      }
      enum "edpl" {
        value 121;
        description
          "edpl";
      }
      enum "l2protect" {
        value 122;
        description
          "l2protect";
      }
      enum "sat" {
        value 123;
        description
          "sat";
      }
      enum "satstats" {
        value 124;
        description
          "satstats";
      }
      enum "cfmoam-profile-def" {
        value 125;
        description
          "cfmoamprofiledef";
      }
      enum "cfmmaid" {
        value 126;
        description
          "cfmmaid";
      }
      enum "cfmdefmps" {
        value 127;
        description
          "cfmdefmps";
      }
      enum "cfmofflmep" {
        value 128;
        description
          "cfmofflmep";
      }
      enum "cfmoffrmep" {
        value 129;
        description
          "cfmoffrmep";
      }
      enum "cfmnonoff" {
        value 130;
        description
          "cfmnonoff";
      }
      enum "cfmhwoffrxstats" {
        value 131;
        description
          "cfmhwoffrxstats";
      }
      enum "cfmnonoff-load" {
        value 132;
        description
          "cfmnonoffload";
      }
      enum "cfm-default-s" {
        value 133;
        description
          "cfmdefaults";
      }
      enum "cfmmntassocid" {
        value 134;
        description
          "cfmmntassocid";
      }
      enum "ipmc-route" {
        value 135;
        description
          "ipmcroute";
      }
      enum "l2ipmc-route" {
        value 136;
        description
          "l2ipmcroute";
      }
      enum "ipmco-list" {
        value 137;
        description
          "ipmcolist";
      }
      enum "l2mco-list" {
        value 138;
        description
          "l2mcolist";
      }
      enum "meshmc" {
        value 139;
        description
          "meshmc";
      }
      enum "l2-bridge" {
        value 140;
        description
          "l2bridge";
      }
      enum "l2-bridge-port" {
        value 141;
        description
          "l2bridgeport";
      }
      enum "l2-bridge-mac" {
        value 142;
        description
          "l2bridgemac";
      }
      enum "l2brmac" {
        value 143;
        description
          "l2brmac";
      }
      enum "ip-tunnel-decap" {
        value 144;
        description
          "iptunneldecap";
      }
      enum "l2vlan-range" {
        value 145;
        description
          "l2vlanrange";
      }
      enum "ip-tunnel-encap" {
        value 146;
        description
          "iptunnelencap";
      }
      enum "iptnl-encap" {
        value 147;
        description
          "iptnlencap";
      }
      enum "iptnldecap" {
        value 148;
        description
          "iptnldecap";
      }
      enum "iptnldecapvni" {
        value 149;
        description
          "iptnldecapvni";
      }
      enum "iptnlnh" {
        value 150;
        description
          "iptnlnh";
      }
      enum "rawget" {
        value 151;
        description
          "rawget";
      }
      enum "ip6mc-route" {
        value 152;
        description
          "ip6mcroute";
      }
      enum "ip6mc-comp-grp" {
        value 153;
        description
          "ip6mc comp grp";
      }
      enum "l2evpnact-remote-peer-id" {
        value 154;
        description
          "l2evpnactremotepeerid";
      }
      enum "l2evpnact-local-shl" {
        value 155;
        description
          "l2evpnactlocalshl";
      }
      enum "l2evpnact-remote-shl" {
        value 156;
        description
          "l2evpnactremoteshl";
      }
      enum "evpn-iml-range" {
        value 157;
        description
          "evpn imlrange";
      }
      enum "l2-bridge-o-list" {
        value 158;
        description
          "l2bridgeolist";
      }
      enum "l2acl" {
        value 159;
        description
          "l2acl";
      }
      enum "l2evpn-nh" {
        value 160;
        description
          "l2evpn nh";
      }
      enum "l2-bridge-port-sc" {
        value 161;
        description
          "l2bridgeport sc";
      }
      enum "l3intfmctxstats" {
        value 162;
        description
          "l3intfmctxstats";
      }
      enum "tidl-sample" {
        value 163;
        description
          "tidl sample";
      }
      enum "tidl-ref-sample" {
        value 164;
        description
          "tidl ref sample";
      }
      enum "ipacl-prefix" {
        value 165;
        description
          "ipaclprefix";
      }
      enum "ip6acl-prefix" {
        value 166;
        description
          "ip6aclprefix";
      }
      enum "ipacl-port" {
        value 167;
        description
          "ipaclport";
      }
      enum "scaleacl" {
        value 168;
        description
          "scaleacl";
      }
      enum "ipmcf-hop" {
        value 169;
        description
          "ipmcfhop";
      }
      enum "bundle-swoff" {
        value 170;
        description
          "bundle swoff";
      }
      enum "mcidswoff" {
        value 171;
        description
          "mcidswoff";
      }
      enum "dest-map" {
        value 172;
        description
          "destmap";
      }
      enum "l2-bridge-port-pw" {
        value 173;
        description
          "l2bridgeport pw";
      }
      enum "l2evpnact-local-shlstats" {
        value 174;
        description
          "l2evpnactlocalshlstats";
      }
      enum "test-hidden" {
        value 175;
        description
          "testhidden";
      }
      enum "test-local" {
        value 176;
        description
          "testlocal";
      }
      enum "test-repeated" {
        value 177;
        description
          "testrepeated";
      }
      enum "limd" {
        value 178;
        description
          "limd";
      }
      enum "litap" {
        value 179;
        description
          "litap";
      }
      enum "l3ifstats" {
        value 180;
        description
          "l3ifstats";
      }
      enum "mplsstats" {
        value 181;
        description
          "mplsstats";
      }
      enum "sr-test-ats" {
        value 182;
        description
          "srtestats";
      }
      enum "srteifstats" {
        value 183;
        description
          "srteifstats";
      }
      enum "exception-nh" {
        value 184;
        description
          "exceptionnh";
      }
      enum "srv6-global" {
        value 185;
        description
          "srv6 global";
      }
      enum "srv6sid" {
        value 186;
        description
          "srv6sid";
      }
      enum "srv6nh" {
        value 187;
        description
          "srv6nh";
      }
      enum "sr6sid" {
        value 188;
        description
          "sr6sid";
      }
      enum "sr6nh" {
        value 189;
        description
          "sr6nh";
      }
      enum "sr6-global" {
        value 190;
        description
          "sr6 global";
      }
      enum "redirect-vrf" {
        value 191;
        description
          "redirectvrf";
      }
      enum "test-xtf" {
        value 192;
        description
          "test xtf";
      }
      enum "ippbr" {
        value 193;
        description
          "ippbr";
      }
      enum "ippbrstats" {
        value 194;
        description
          "ippbrstats";
      }
      enum "mpls-mdt-bud" {
        value 195;
        description
          "mplsmdtbud";
      }
      enum "mpls-label-rxstats" {
        value 196;
        description
          "mplslabelrxstats";
      }
      enum "l2mac-static" {
        value 197;
        description
          "l2macstatic";
      }
      enum "dot1x" {
        value 198;
        description
          "dot1x";
      }
      enum "iprte" {
        value 199;
        description
          "iprte";
      }
      enum "ip6rte" {
        value 200;
        description
          "ip6rte";
      }
      enum "llnh" {
        value 201;
        description
          "llnh";
      }
      enum "urpfintf" {
        value 202;
        description
          "urpfintf";
      }
      enum "ipmcrxstats" {
        value 203;
        description
          "ipmcrxstats";
      }
      enum "mplsrte" {
        value 204;
        description
          "mplsrte";
      }
      enum "protectnh" {
        value 205;
        description
          "protectnh";
      }
      enum "ipllnh" {
        value 206;
        description
          "ipllnh";
      }
      enum "ip6llnh" {
        value 207;
        description
          "ip6llnh";
      }
      enum "macnh" {
        value 208;
        description
          "macnh";
      }
      enum "qos-match-stats" {
        value 209;
        description
          "qosmatchstats";
      }
      enum "ofal2xc" {
        value 210;
        description
          "ofal2xc";
      }
      enum "ofamplspwe-port" {
        value 211;
        description
          "ofamplspweport";
      }
      enum "pwenh" {
        value 212;
        description
          "pwenh";
      }
      enum "pwenh-group" {
        value 213;
        description
          "pwenhgroup";
      }
      enum "ipmcrte" {
        value 214;
        description
          "ipmcrte";
      }
      enum "ip6mcrte" {
        value 215;
        description
          "ip6mcrte";
      }
      enum "ipmcr-test-ats" {
        value 216;
        description
          "ipmcrtestats";
      }
      enum "ip6mcr-test-ats" {
        value 217;
        description
          "ip6mcrtestats";
      }
      enum "transport-nh" {
        value 218;
        description
          "transportnh";
      }
      enum "port-range" {
        value 219;
        description
          "portrange";
      }
      enum "mcid" {
        value 220;
        description
          "mcid";
      }
      enum "mc-gid" {
        value 221;
        description
          "mc gid";
      }
      enum "mcgidole" {
        value 222;
        description
          "mcgidole";
      }
      enum "mco-list" {
        value 223;
        description
          "mcolist";
      }
      enum "test-da" {
        value 224;
        description
          "testda";
      }
      enum "test-ca" {
        value 225;
        description
          "testca";
      }
      enum "test-ba" {
        value 226;
        description
          "testba";
      }
      enum "test-aa" {
        value 227;
        description
          "testaa";
      }
      enum "test-async-aa" {
        value 228;
        description
          "testasyncaa";
      }
      enum "test-reliable-notif" {
        value 229;
        description
          "testreliablenotif";
      }
      enum "test-de" {
        value 230;
        description
          "testde";
      }
      enum "test-ce" {
        value 231;
        description
          "testce";
      }
      enum "test-be" {
        value 232;
        description
          "testbe";
      }
      enum "test-db" {
        value 233;
        description
          "testdb";
      }
      enum "test-cb" {
        value 234;
        description
          "testcb";
      }
      enum "test-bb" {
        value 235;
        description
          "testbb";
      }
      enum "test-df" {
        value 236;
        description
          "testdf";
      }
      enum "test-cf" {
        value 237;
        description
          "testcf";
      }
      enum "test-bf" {
        value 238;
        description
          "testbf";
      }
      enum "test-af" {
        value 239;
        description
          "testaf";
      }
      enum "test-cz" {
        value 240;
        description
          "testcz";
      }
      enum "test-ax" {
        value 241;
        description
          "testax";
      }
      enum "test-ay" {
        value 242;
        description
          "testay";
      }
      enum "test-ef" {
        value 243;
        description
          "testef";
      }
      enum "test-ff" {
        value 244;
        description
          "testff";
      }
      enum "test-npurc" {
        value 245;
        description
          "testnpurc";
      }
      enum "test-gf" {
        value 246;
        description
          "testgf";
      }
      enum "test-eastwestscheduling" {
        value 247;
        description
          "testeastwestscheduling";
      }
      enum "test-transnh" {
        value 248;
        description
          "testtransnh";
      }
      enum "test-eth-port" {
        value 249;
        description
          "testethport";
      }
      enum "test-eastwest" {
        value 250;
        description
          "testeastwest";
      }
      enum "test-ifstats" {
        value 251;
        description
          "testifstats";
      }
      enum "test-async-oor" {
        value 252;
        description
          "testasyncoor";
      }
      enum "test-async-db" {
        value 253;
        description
          "testasyncdb";
      }
      enum "test-syncmcas-too-r" {
        value 254;
        description
          "testsyncmcastoor";
      }
      enum "test-syncdeviceoor" {
        value 255;
        description
          "testsyncdeviceoor";
      }
      enum "test-az" {
        value 256;
        description
          "testaz";
      }
      enum "test-by" {
        value 257;
        description
          "testby";
      }
      enum "police-r-group" {
        value 258;
        description
          "policergroup";
      }
      enum "meter-profile" {
        value 259;
        description
          "meterprofile";
      }
      enum "acl-mirror" {
        value 260;
        description
          "acl mirror";
      }
      enum "meter-action-profile" {
        value 261;
        description
          "meteractionprofile";
      }
      enum "voqrm" {
        value 262;
        description
          "voqrm";
      }
      enum "port-wfq-profile" {
        value 263;
        description
          "portwfqprofile";
      }
      enum "rpfif" {
        value 264;
        description
          "rpfif";
      }
      enum "brmac" {
        value 265;
        description
          "brmac";
      }
      enum "br-static-mac" {
        value 266;
        description
          "brstaticmac";
      }
      enum "xconnect" {
        value 267;
        description
          "xconnect";
      }
      enum "bridge" {
        value 268;
        description
          "bridge";
      }
      enum "pwe-port" {
        value 269;
        description
          "pweport";
      }
      enum "olist" {
        value 270;
        description
          "olist";
      }
      enum "lsmprotect" {
        value 271;
        description
          "lsmprotect";
      }
      enum "monitor-session" {
        value 272;
        description
          "monitorsession";
      }
      enum "monitor-session-stats" {
        value 273;
        description
          "monitorsessionstats";
      }
      enum "mplsmcast" {
        value 274;
        description
          "mplsmcast";
      }
      enum "l2ifstats" {
        value 275;
        description
          "l2ifstats";
      }
      enum "imlnh" {
        value 276;
        description
          "imlnh";
      }
      enum "evinh" {
        value 277;
        description
          "evinh";
      }
      enum "member-list" {
        value 278;
        description
          "memberlist";
      }
      enum "test-oor" {
        value 279;
        description
          "testoor";
      }
      enum "hwre-source-s-oor" {
        value 280;
        description
          "hwresources oor";
      }
      enum "qospfcstats" {
        value 281;
        description
          "qospfcstats";
      }
      enum "pfctc" {
        value 282;
        description
          "pfctc";
      }
      enum "pfc-watchdog" {
        value 283;
        description
          "pfc watchdog";
      }
      enum "qos-shared" {
        value 284;
        description
          "qosshared";
      }
      enum "ecntxstats" {
        value 285;
        description
          "ecntxstats";
      }
      enum "tm-remote-credit" {
        value 286;
        description
          "tmremotecredit";
      }
      enum "ipmcole" {
        value 287;
        description
          "ipmcole";
      }
      enum "ip6mcole" {
        value 288;
        description
          "ip6mcole";
      }
      enum "pbr" {
        value 289;
        description
          "pbr";
      }
      enum "pbrstats" {
        value 290;
        description
          "pbrstats";
      }
      enum "punt-stormcontrol" {
        value 291;
        description
          "puntstormcontrol";
      }
      enum "ip6mcrxstats" {
        value 292;
        description
          "ip6mcrxstats";
      }
      enum "ipmctxintf" {
        value 293;
        description
          "ipmctxintf";
      }
      enum "ipmc-mdt-encap" {
        value 294;
        description
          "ipmcmdtencap";
      }
      enum "ipmc-mdt-decap" {
        value 295;
        description
          "ipmcmdtdecap";
      }
      enum "op2tap" {
        value 296;
        description
          "op2tap";
      }
      enum "mplsole" {
        value 297;
        description
          "mplsole";
      }
      enum "syncrpc" {
        value 298;
        description
          "syncrpc";
      }
      enum "tnlstats" {
        value 299;
        description
          "tnlstats";
      }
      enum "l2dhcp" {
        value 300;
        description
          "l2dhcp";
      }
      enum "pbrsbf" {
        value 301;
        description
          "pbrsbf";
      }
      enum "statsrpc" {
        value 302;
        description
          "statsrpc";
      }
      enum "oglpts" {
        value 303;
        description
          "oglpts";
      }
      enum "oglpts-prefix" {
        value 304;
        description
          "oglptsprefix";
      }
      enum "og6lpts-prefix" {
        value 305;
        description
          "og6lptsprefix";
      }
      enum "stormcontrol" {
        value 306;
        description
          "stormcontrol";
      }
      enum "acl-police-r" {
        value 307;
        description
          "aclpolicer";
      }
      enum "acl-police-rstats" {
        value 308;
        description
          "aclpolicerstats";
      }
      enum "aclkey-profile" {
        value 309;
        description
          "aclkeyprofile";
      }
      enum "acl-action-profile" {
        value 310;
        description
          "aclactionprofile";
      }
      enum "dummytable" {
        value 311;
        description
          "dummytable";
      }
      enum "ip-sub" {
        value 312;
        description
          "ipsub";
      }
      enum "dot1x-mac" {
        value 313;
        description
          "dot1x mac";
      }
      enum "eoam" {
        value 314;
        description
          "eoam";
      }
      enum "featacl-group" {
        value 315;
        description
          "feataclgroup";
      }
      enum "pfcwdstats" {
        value 316;
        description
          "pfcwdstats";
      }
      enum "pktmemresmon" {
        value 317;
        description
          "pktmemresmon";
      }
      enum "iptnldecapsaf" {
        value 318;
        description
          "iptnldecapsaf";
      }
    }
    description
      "Ofa table";
  }

  container ofa {
    config false;
    description
      "OFA Data";
    container stats {
      description
        "OFA Stats Data";
      container nodes {
        description
          "OFA data for available nodes";
        list node {
          key "node-name";
          description
            "OFA operational data for a particular node";
          container table-datas {
            description
              "OFA Resources table";
            list table-data {
              key "resource";
              description
                "OFA Resources table";
              leaf resource {
                type Ofa-table;
                description
                  "Resource type";
              }
              uses OFA-NPD-SYSDB-TABLE-RESOURCE;
            }
          }
          leaf node-name {
            type xr:Node-id;
            description
              "Node ID";
          }
        }
      }
    }
  }
}
