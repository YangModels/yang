module Cisco-IOS-XR-crypto-macsec-secy-oper {
  namespace "http://cisco.com/ns/yang/Cisco-IOS-XR-crypto-macsec-secy-oper";
  prefix crypto-macsec-secy-oper;

  import Cisco-IOS-XR-types {
    prefix xr;
  }
  import cisco-semver {
    prefix semver;
  }
  include Cisco-IOS-XR-crypto-macsec-secy-oper-sub1 {
    revision-date 2022-02-08;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR crypto-macsec-secy package operational data.
     
     This module contains definitions
     for the following management objects:
       macsec: Macsec operational data
     
     Copyright (c) 2013-2022 by Cisco Systems, Inc.
     All rights reserved.";

  revision 2022-02-08 {
    description
      "Added Standby Container for MKA operational info";
    semver:module-version "1.0.1";
  }
  revision 2019-04-05 {
    description
      "Establish semantic version baseline.";
    semver:module-version "1.0.1";
  }
  revision 2015-11-09 {
    description
      "IOS XR 6.0 revision.";
  }

  container macsec {
    config false;
    description
      "Macsec operational data";
    container secy {
      description
        "MAC Security Entity";
      container interfaces {
        description
          "MAC Security Data";
        list interface {
          key "name";
          description
            "MAC Security Data for the Interface";
          container stats {
            description
              "MACsec Stats";
            uses MACSEC-SECY-STATS;
          }
          leaf name {
            type xr:Interface-name;
            description
              "Interface Name";
          }
        }
      }
    }
  }
}
