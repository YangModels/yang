module Cisco-IOS-XR-um-cef-load-balancing-cfg {
  namespace "http://cisco.com/ns/yang/Cisco-IOS-XR-um-cef-load-balancing-cfg";
  prefix um-cef-load-balancing-cfg;

  import Cisco-IOS-XR-um-cef-accounting-cfg {
    prefix a1;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR cef-load-balancing package configuration.
     
     This YANG module augments the
     modules with configuration data.
     
     Copyright (c) 2020 by Cisco Systems, Inc.
     All rights reserved.";

  revision 2020-09-21 {
    description
      "Initial release";
    semver:module-version "1.0.0";
  }

  augment "/a1:cef" {
    container load-balancing {
      description
        "Load balance ";
      container algorithm {
        description
          "hash algorithm ";
        leaf adjust {
          type uint32 {
            range "0..31" {
              description
                "Adjust count - configure up to 31 for Typhoon & Tomahawk; up to 3 for Trident cards; Value will be masked on Trident (to make it <= 3) if this configured value is beyond 3";
            }
          }
          description
            "Specify adjust count to rotate the resultant hash of hash algo";
        }
      }
      container fields {
        description
          "hash fields";
        container l3 {
          description
            "Exclude L4 port info from hash calculation";
          container global {
            presence "Indicates a global node is configured.";
            description
              "configure globally system wide";
          }
        }
        container l4 {
          description
            "Load balancing at layer 4";
          container gtp {
            presence "Indicates a gtp node is configured.";
            description
              "Includes GTP TEID for hash calculation";
          }
        }
        container ipv6 {
          description
            "Use ipv6 fields for load-balancing";
          container disable-flow-label {
            presence "Indicates a disable-flow-label node is configured.";
            description
              "Exclude ipv6 flow-label from hash calculation";
          }
        }
        container mpls {
          description
            "Use mpls fields for load-balancing";
          container entropy-label {
            presence "Indicates a entropy-label node is configured.";
            description
              "Include mpls entropy-label in addition for hashing";
          }
        }
      }
    }
  }
}
