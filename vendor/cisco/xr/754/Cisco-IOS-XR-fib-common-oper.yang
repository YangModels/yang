module Cisco-IOS-XR-fib-common-oper {
  namespace "http://cisco.com/ns/yang/Cisco-IOS-XR-fib-common-oper";
  prefix fib-common-oper;

  import ietf-inet-types {
    prefix inet;
  }
  import Cisco-IOS-XR-types {
    prefix xr;
  }
  import cisco-semver {
    prefix semver;
  }
  include Cisco-IOS-XR-fib-common-oper-sub7 {
    revision-date 2023-02-06;
  }
  include Cisco-IOS-XR-fib-common-oper-sub6 {
    revision-date 2023-02-06;
  }
  include Cisco-IOS-XR-fib-common-oper-sub5 {
    revision-date 2023-02-06;
  }
  include Cisco-IOS-XR-fib-common-oper-sub4 {
    revision-date 2023-02-06;
  }
  include Cisco-IOS-XR-fib-common-oper-sub3 {
    revision-date 2023-02-06;
  }
  include Cisco-IOS-XR-fib-common-oper-sub2 {
    revision-date 2023-02-06;
  }
  include Cisco-IOS-XR-fib-common-oper-sub1 {
    revision-date 2023-02-06;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR fib-common package operational data.
     
     This module contains definitions
     for the following management objects:
       fib-statistics: cef interface drops operational data
       fib: FIB operational data
       oc-aft-l3: Openconfig L3 abstract forwarding table data
       mpls-forwarding: MPLS forwarding operational data
     
     Copyright (c) 2013-2023 by Cisco Systems, Inc.
     All rights reserved.";

  revision 2023-02-06 {
    description
      "Added disable-rfc5549-ipv4-over-ipv6-nexthop platform capability.
       2022-10-17
         CNHG changes
       2022-04-27
         Added vxlan-vni-id to ltep-tunnel
       2022-03-15
         Added vxlan-tunnels
       2022-02-01
         Added policy and hardware ingress and egress paths
       2021-11-26
         Added ltep-tunnels and hardware ingress and egress paths
       2021-11-05
         Added rtep-tunnels and hardware ingress and egress paths
       2021-11-03
         Added ltep-nve-tunnels hardware ingress and egress paths
       2021-10-23
         Added ltep-nve-tunnels and added object-id to object-base";
    semver:module-version "4.0.1M";
  }
  revision 2021-10-17 {
    description
      "Modify the type of list fsum-attr-cnt
       2021-09-17
          Rename lists unicast-prefix, broadcast-prefix and leafs num-retry-objects, old-unresolved-entries, new-unresolved-entries, unresolved-entries
       2021-07-30
          Added evpn bridge ID and SHG ID to srv6-information-for-path bag
       2021-07-06
          Added global-main subtree and support show CLIs for FIB IPC infra
       2021-05-25
          Migrate NHINFO to TI infra";
    semver:module-version "4.0.0";
  }
  revision 2020-12-02 {
    description
      "Adding per-object accounting.
       2020-10-20
           NBC documentation of CSCvu06764, CSCvv14573,CSCvv76648
       2020-05-26
           Update SRv6 Block Space naming convention
       2020-05-05
           changes related to treat SRv6 and SID as well-known when parsing XML for yang";
    semver:module-version "3.0.0";
  }
  revision 2020-01-16 {
    description
      "NBC documentation of CSCvs27272,CSCvs22018,CSCvs45512
       2019-10-29
         Updated srv6 global bag";
    semver:module-version "2.0.0";
  }
  revision 2019-09-27 {
    description
      "IOS XR 7.0.x revision.";
    semver:module-version "1.1.0";
  }
  revision 2019-04-05 {
    description
      "Establish semantic version baseline.";
    semver:module-version "1.0.0";
  }
  revision 2019-04-02 {
    description
      "Fixed schema descriptions.";
  }
  revision 2017-09-07 {
    description
      "Fixed type translation error.";
  }
  revision 2017-05-01 {
    description
      "Fixing backward compatibility error in module.";
  }
  revision 2017-01-20 {
    description
      "IOS XR 6.2.1 revision";
  }
  revision 2015-11-09 {
    description
      "IOS XR 6.0 revision.";
  }

  typedef Fib-route-source {
    type enumeration {
      enum "lsd" {
        value 5;
        description
          "LSD";
      }
      enum "rib" {
        value 7;
        description
          "RIB";
      }
      enum "mrib" {
        value 14;
        description
          "MRIB";
      }
    }
    description
      "Fib route source";
  }

  typedef Fib-protocol {
    type enumeration {
      enum "ipv4" {
        value 0;
        description
          "ipv4 protocol";
      }
      enum "ipv6" {
        value 1;
        description
          "ipv6 protocol";
      }
      enum "mpls" {
        value 2;
        description
          "MPLS protocol";
      }
    }
    description
      "Fib protocol";
  }

  typedef Fib-object {
    type enumeration {
      enum "none" {
        value 0;
        description
          "None";
      }
      enum "adjacency" {
        value 8;
        description
          "NHINFO";
      }
      enum "all" {
        value 23;
        description
          "ALL";
      }
    }
    description
      "Fib object";
  }

  typedef Fibipv6-flow-label {
    type uint32 {
      range "0..1048575";
    }
    description
      "Fibipv6 flow label";
  }

  typedef Ipvpn-tunnel {
    type enumeration {
      enum "ipvpn-tunnel-type-invalid" {
        value 0;
        description
          "Invalid";
      }
      enum "ipvpn-tunnel-type-l2tp" {
        value 1;
        description
          "l2tpv3";
      }
      enum "ipvpn-tunnel-type-mgre" {
        value 2;
        description
          "merge";
      }
      enum "ipvpn-tunnel-type-vxlan-l2" {
        value 3;
        description
          "vxlan l2";
      }
      enum "ipvpn-tunnel-type-gre" {
        value 4;
        description
          "gre";
      }
      enum "ipvpn-tunnel-type-ip" {
        value 5;
        description
          "ip";
      }
      enum "ipvpn-tunnel-type-te" {
        value 6;
        description
          "te";
      }
      enum "ipvpn-tunnel-type-vxlan-l3" {
        value 7;
        description
          "vxlan l3";
      }
      enum "ipvpn-tunnel-type-vxlan-l3-sfi" {
        value 8;
        description
          "vxlan l3 sfi";
      }
      enum "ipvpn-tunnel-type-mpl-so-udp" {
        value 9;
        description
          "mpls udp";
      }
      enum "ipvpn-tunnel-type-max" {
        value 10;
        description
          "max";
      }
    }
    description
      "Ipvpn tunnel";
  }

  typedef Fib-object-attribute {
    type enumeration {
      enum "none" {
        value 0;
        description
          "Invalid type of attribute";
      }
      enum "error" {
        value 1;
        description
          "Error type of attribute";
      }
      enum "out-of-resource" {
        value 2;
        description
          "Out-of-Resource type of attribute";
      }
      enum "oadjacency" {
        value 3;
        description
          "Adjacency type of attribute";
      }
    }
    description
      "Fib object attribute";
  }

  typedef Fibafi-proto {
    type enumeration {
      enum "ipv4" {
        value 0;
        description
          "ipv4 protocol";
      }
      enum "ipv4-mpls" {
        value 1;
        description
          "ipv4 mpls protocol";
      }
      enum "ipv6" {
        value 2;
        description
          "ipv6 protocol";
      }
      enum "ipv6-mpls" {
        value 3;
        description
          "ipv6 mpls protocol";
      }
    }
    description
      "Fibafi proto";
  }

  typedef Fib-label {
    type uint32 {
      range "16..1048575";
    }
    description
      "Fib label";
  }

  typedef Fibllc-entry {
    type enumeration {
      enum "xc" {
        value 1;
        description
          "LabelXconnect";
      }
      enum "pfx" {
        value 2;
        description
          "IPPrefix";
      }
    }
    description
      "Fibllc entry";
  }

  typedef Fibnh-info-repl {
    type enumeration {
      enum "fib-nh-repl-none" {
        value 0;
        description
          "None Replicated NHINFO";
      }
      enum "fib-nh-repl-rsvpte" {
        value 1;
        description
          "Replicated NHINFO for TE Accounting";
      }
      enum "fib-nh-repl-sr-mpls" {
        value 2;
        description
          "Replicated NHINFO for SR MPLS Accounting";
      }
      enum "fib-nh-repl-bm" {
        value 3;
        description
          "Replicated NHINFO for Bundle member";
      }
    }
    description
      "Fibnh info repl";
  }

  typedef Fibfrr {
    type enumeration {
      enum "fib-te-frr-node" {
        value 0;
        description
          "TE FRR";
      }
      enum "fib-te-frr-intf" {
        value 1;
        description
          "TE Interface FRR";
      }
      enum "fib-te-frr-protected-nh" {
        value 2;
        description
          "TE Protected FRR";
      }
      enum "fib-te-frr-backup-nh" {
        value 3;
        description
          "TE Backup FRR";
      }
      enum "fib-per-link-frr-protected-nh" {
        value 4;
        description
          "Per Link Protected FRR";
      }
      enum "fib-per-link-frr-backup-nh" {
        value 5;
        description
          "Per Link Backup FRR";
      }
      enum "fib-prefix-frr-protected-nh" {
        value 6;
        description
          "Per Prefix Protected FRR";
      }
      enum "fib-prefix-frr-backup-nh" {
        value 7;
        description
          "Per Prefix Backup FRR";
      }
      enum "fib-pic-frr-protected-nh" {
        value 8;
        description
          "BGP PIC Protected FRR";
      }
      enum "fib-pic-frr-backup-nh" {
        value 9;
        description
          "BGP PIC Backup FRR";
      }
    }
    description
      "Fibfrr";
  }

  typedef Fib-link {
    type enumeration {
      enum "link-ipv4" {
        value 0;
        description
          "IPv4 link protocol";
      }
      enum "link-ipv6" {
        value 1;
        description
          "IPv6 link protocol";
      }
      enum "link-mpls" {
        value 2;
        description
          "MPLS link protocol";
      }
    }
    description
      "Fib link";
  }

  typedef Fibnh-remote {
    type enumeration {
      enum "fib-nh-rx" {
        value 1;
        description
          "NHINFO Remote Type";
      }
    }
    description
      "Fibnh remote";
  }

  typedef Mpls-label {
    type uint32 {
      range "16..1048575";
    }
    description
      "Mpls label";
  }

  typedef Mplseos {
    type enumeration {
      enum "eos0" {
        value 0;
        description
          "EOS Disable";
      }
      enum "eos1" {
        value 1;
        description
          "EOS Enable";
      }
    }
    description
      "Mplseos";
  }

  typedef Prefix-len-range {
    type uint32 {
      range "0..128";
    }
    description
      "Prefix len range";
  }

  typedef Fibnh-local {
    type enumeration {
      enum "fib-nh-tx" {
        value 0;
        description
          "NHINFO Local Type";
      }
      enum "fib-nh-special" {
        value 2;
        description
          "NHINFO Special Type";
      }
    }
    description
      "Fibnh local";
  }

  typedef Generic-index {
    type uint32 {
      range "0..4294967295";
    }
    description
      "Generic index";
  }

  grouping STATE {
    description
      "Common node of prefix, label";
    container state {
      description
        "Operational data";
      uses FIB-OC-AFT-PRFX-STATE-V2;
    }
  }

  grouping NH-INFO-SPECIAL-PUNT-DETAIL-HARDWARE-INGRESS {
    description
      "Common node of
       nh-info-special-detail-hardware-ingress,
       nh-info-special-mpls-detail-hardware-ingress";
    container nh-info-special-punt-detail-hardware-ingress {
      description
        "Detail hardware ingress info for special-punt
         NHInfo entry";
      uses FIB-SH-NHINFO;
    }
  }

  grouping NH-INFO-SPECIAL-PUNT-DETAIL {
    description
      "Common node of nh-info-special-detail,
       nh-info-special-mpls-detail";
    container nh-info-special-punt-detail {
      description
        "Detail special NHInfo punt entry";
      uses FIB-SH-NHINFO;
    }
  }

  grouping NH-INFO-SPECIAL-DISCARD-DETAIL {
    description
      "Common node of nh-info-special-detail,
       nh-info-special-mpls-detail";
    container nh-info-special-discard-detail {
      description
        "Detail special NHInfo discard entry";
      uses FIB-SH-NHINFO;
    }
  }

  grouping NH-INFO-SPECIAL-DROP-DETAIL {
    description
      "Common node of nh-info-special-detail,
       nh-info-special-mpls-detail";
    container nh-info-special-drop-detail {
      description
        "Detail special NHInfo punt entry";
      uses FIB-SH-NHINFO;
    }
  }

  grouping OBJECT-TABLE {
    description
      "Common node of summary-protocol, total";
    container objects {
      description
        "Object Table";
      list object {
        key "object-id";
        description
          "Object Table entry";
        leaf object-id {
          type uint32;
          description
            "Object ID";
        }
        uses FIB-BAG-SUM-OBJ;
      }
    }
  }

  grouping NH-INFO-SPECIAL-DROP-BRIEF {
    description
      "Common node of nh-info-special-brief,
       nh-info-special-mpls-brief";
    container nh-info-special-drop-brief {
      description
        "Brief special NHInfo drop entry";
      uses FIB-SH-NHINFO;
    }
  }

  grouping NH-INFO-SPECIAL-DISCARD-BRIEF {
    description
      "Common node of nh-info-special-brief,
       nh-info-special-mpls-brief";
    container nh-info-special-discard-brief {
      description
        "Brief special NHInfo discard entry";
      uses FIB-SH-NHINFO;
    }
  }

  grouping NH-INFO-SPECIAL-PUNT-BRIEF {
    description
      "Common node of nh-info-special-brief,
       nh-info-special-mpls-brief";
    container nh-info-special-punt-brief {
      description
        "Brief special NHInfo punt entry";
      uses FIB-SH-NHINFO;
    }
  }

  grouping NH-INFO-SPECIAL-DROP-DETAIL-HARDWARE-EGRESS {
    description
      "Common node of
       nh-info-special-detail-hardware-egress,
       nh-info-special-mpls-detail-hardware-egress";
    container nh-info-special-drop-detail-hardware-egress {
      description
        "Detail hardware egress info for special-drop
         NHInfo entry";
      uses FIB-SH-NHINFO;
    }
  }

  grouping ERROR {
    description
      "Common node of ipv4, ipv6";
    container error {
      description
        "Error data";
      container state {
        description
          "Error data";
        uses FIB-OC-AFT-ERROR-STATE;
      }
    }
  }

  grouping PREFIX-TABLE {
    description
      "Common node of ipv6-unicast, ipv4-unicast";
    container prefixes {
      description
        "Table of IP prefixes";
      list prefix {
        key "prefix";
        description
          "Prefix data";
        leaf prefix {
          type string;
          description
            "Prefix";
        }
        uses STATE;
      }
    }
  }

  grouping NH-INFO-SPECIAL-NULL-DETAIL-HARDWARE-INGRESS {
    description
      "Common node of
       nh-info-special-detail-hardware-ingress,
       nh-info-special-mpls-detail-hardware-ingress";
    container nh-info-special-null-detail-hardware-ingress {
      description
        "Detail hardware ingress info for special-null
         NHInfo entry";
      uses FIB-SH-NHINFO;
    }
  }

  grouping NH-INFO-SPECIAL-DISCARD-DETAIL-HARDWARE-EGRESS {
    description
      "Common node of
       nh-info-special-detail-hardware-egress,
       nh-info-special-mpls-detail-hardware-egress";
    container nh-info-special-discard-detail-hardware-egress {
      description
        "Detail hardware egress info for special-discard
         NHInfo entry";
      uses FIB-SH-NHINFO;
    }
  }

  grouping NH-INFO-SPECIAL-NULL-BRIEF {
    description
      "Common node of nh-info-special-brief,
       nh-info-special-mpls-brief";
    container nh-info-special-null-brief {
      description
        "Brief special NHInfo null entry";
      uses FIB-SH-NHINFO;
    }
  }

  grouping OOR {
    description
      "Common node of ipv4, ipv6";
    container oor {
      description
        "OOR data";
      container state {
        description
          "OOR data";
        uses FIB-OC-AFT-OOR-STATE;
      }
    }
  }

  grouping NH-INFO-SPECIAL-DISCARD-DETAIL-HARDWARE-INGRESS {
    description
      "Common node of
       nh-info-special-detail-hardware-ingress,
       nh-info-special-mpls-detail-hardware-ingress";
    container nh-info-special-discard-detail-hardware-ingress {
      description
        "Detail hardware ingress info for special-discard
         NHInfo entry";
      uses FIB-SH-NHINFO;
    }
  }

  grouping NH-INFO-SPECIAL-NULL-DETAIL {
    description
      "Common node of nh-info-special-detail,
       nh-info-special-mpls-detail";
    container nh-info-special-null-detail {
      description
        "Detail special NHInfo null entry";
      uses FIB-SH-NHINFO;
    }
  }

  grouping NH-INFO-SPECIAL-NULL-DETAIL-HARDWARE-EGRESS {
    description
      "Common node of
       nh-info-special-detail-hardware-egress,
       nh-info-special-mpls-detail-hardware-egress";
    container nh-info-special-null-detail-hardware-egress {
      description
        "Detail hardware egress info for special-null
         NHInfo entry";
      uses FIB-SH-NHINFO;
    }
  }

  grouping NH-INFO-SPECIAL-PUNT-DETAIL-HARDWARE-EGRESS {
    description
      "Common node of
       nh-info-special-detail-hardware-egress,
       nh-info-special-mpls-detail-hardware-egress";
    container nh-info-special-punt-detail-hardware-egress {
      description
        "Detail hardware egress info for special-punt
         NHInfo entry";
      uses FIB-SH-NHINFO;
    }
  }

  grouping NH-INFO-SPECIAL-DROP-DETAIL-HARDWARE-INGRESS {
    description
      "Common node of
       nh-info-special-detail-hardware-ingress,
       nh-info-special-mpls-detail-hardware-ingress";
    container nh-info-special-drop-detail-hardware-ingress {
      description
        "Detail hardware ingress info for special-drop
         NHInfo entry";
      uses FIB-SH-NHINFO;
    }
  }

  container fib-statistics {
    config false;
    description
      "cef interface drops operational data";
    container nodes {
      description
        "List of nodes";
      list node {
        key "node-name";
        description
          "Specific node operational data";
        container drops {
          description
            "Specific node drops";
          uses FIB-STATISTICS-BAG-DROPS;
        }
        leaf node-name {
          type xr:Node-id;
          description
            "Node name";
        }
      }
    }
  }
  container fib {
    config false;
    description
      "FIB operational data";
    container nodes {
      description
        "Table of nodes";
      list node {
        key "node-name";
        description
          "Operational data for a specific Node";
        container global {
          description
            "FIB Global info";
          container fib-cofo {
            description
              "Collapsed Forwarding";
            container fib-cofo-idb {
              description
                "Collapsed Forwarding IDB Table";
              container fib-cofo-idb-table-entries {
                description
                  "Collapsed Forwarding Idb Table Entries";
                list fib-cofo-idb-table-entry {
                  description
                    "Collapsed Forwarding Idb Table Entries";
                  leaf sdr-id {
                    type uint32;
                    description
                      "SDR ID value";
                  }
                  leaf if-index {
                    type uint32;
                    description
                      "Interface Index";
                  }
                  uses FIB-SH-COFO-IDB-TBL-ENTRY-INFO;
                }
              }
            }
            container fib-cofo-table-id {
              description
                "Collapsed Forwarding Table Id Table";
              container fib-cofo-table-id-entries {
                description
                  "Collapsed Forwarding Table Id Entries";
                list fib-cofo-table-id-entry {
                  description
                    "Collapsed Forwarding Idb Table Entries";
                  leaf sdr-id {
                    type uint32;
                    description
                      "SDR ID value";
                  }
                  leaf protocol {
                    type Fib-protocol;
                    description
                      "Protocol";
                  }
                  leaf rd {
                    type xr:Cisco-ios-xr-string;
                    description
                      "Route Distinguisher";
                  }
                  leaf table-id {
                    type uint32;
                    description
                      "Table Id";
                  }
                  uses FIB-SH-COFO-TBL-ID-ENTRY-INFO;
                }
              }
              container fib-cofo-table-id-summary {
                description
                  "Collapsed Forwarding Table Id Entries";
                uses FIB-SH-COFO-TBL-ID-DB-SUM;
              }
            }
          }
          container summary {
            description
              "Global Summary";
            container total {
              description
                "Display total";
              container counters {
                description
                  "Display total counters and common info";
                uses FIB-GLOBAL-SUMMARY-TOTAL;
              }
              uses OBJECT-TABLE;
            }
            container summary-protocols {
              description
                "Summary Protocol Table";
              list summary-protocol {
                key "protocol-name";
                description
                  "Summary Protocol Table entry";
                container proto-counters {
                  description
                    "Display protocol counters";
                  uses FIB-GLOBAL-SUMMARY-PROTO;
                }
                leaf protocol-name {
                  type Fibafi-proto;
                  description
                    "Protocol Name";
                }
                uses OBJECT-TABLE;
              }
            }
          }
          container encap-id-database {
            description
              "Encap ID database";
            container summary {
              description
                "Encap ID DB summary";
              uses FIB-ENCAP-ID-SUMMARY;
            }
            container encap-id-incompletes {
              description
                "Incomplete Encap ID entry table";
              list encap-id-incomplete {
                key "object-id";
                description
                  "Incomplete Encap ID entry";
                leaf object-id {
                  type xr:Cisco-ios-xr-string;
                  description
                    "Object ID";
                }
                uses FIB-OBJECT-ENCAP-ID-INFO;
              }
            }
            container encap-ids {
              description
                "Encap ID table";
              list encap-id {
                key "encap-id";
                description
                  "Encap ID entry";
                leaf encap-id {
                  type xr:Cisco-ios-xr-string;
                  description
                    "Encap ID";
                }
                uses FIB-OBJECT-ENCAP-ID-INFO;
              }
            }
          }
          container object-history {
            description
              "FIB Global Object History";
            container obj-history-protos {
              description
                "Proto Table";
              list obj-history-proto {
                key "protocol-name";
                description
                  "Protocol Table entry";
                leaf protocol-name {
                  type Fibafi-proto;
                  description
                    "Protocol Name";
                }
                uses FIB-GLOBAL-SUMMARY-OBJ-HISTORY-PROTO;
              }
            }
          }
          container tunnel-database {
            description
              "TunnelTable database";
            container ltep-nve-tunnel-hardware-egresses {
              description
                "Ltep NVE Tunnel database";
              list ltep-nve-tunnel-hardware-egress {
                description
                  "LTEP NVE table entry";
                leaf table-id {
                  type xr:Hex-integer;
                  description
                    "Table ID";
                }
                leaf nve-interface-id {
                  type uint32;
                  description
                    "NVE interface ID";
                }
                leaf vni-id {
                  type uint32;
                  description
                    "VNI ID";
                }
                uses FIB-GLOBAL-LTEP-NVE-ENTRY;
              }
            }
            container ltep-nve-tunnels {
              description
                "Ltep NVE Tunnel database";
              list ltep-nve-tunnel {
                description
                  "LTEP NVE table entry";
                leaf table-id {
                  type xr:Hex-integer;
                  description
                    "Table ID";
                }
                leaf nve-interface-id {
                  type uint32;
                  description
                    "NVE interface ID";
                }
                leaf vni-id {
                  type uint32;
                  description
                    "VNI ID";
                }
                uses FIB-GLOBAL-LTEP-NVE-ENTRY;
              }
            }
            container ltep-nve-tunnel-hardware-ingresses {
              description
                "Ltep NVE Tunnel database";
              list ltep-nve-tunnel-hardware-ingress {
                description
                  "LTEP NVE table entry";
                leaf table-id {
                  type xr:Hex-integer;
                  description
                    "Table ID";
                }
                leaf nve-interface-id {
                  type uint32;
                  description
                    "NVE interface ID";
                }
                leaf vni-id {
                  type uint32;
                  description
                    "VNI ID";
                }
                uses FIB-GLOBAL-LTEP-NVE-ENTRY;
              }
            }
          }
          container aggregation-db {
            description
              "Aggregation database";
            container aggregation-entries {
              description
                "Aggregation table";
              list aggregation-entry {
                description
                  "Aggregation table entry";
                leaf protocol {
                  type Fib-protocol;
                  description
                    "Protocol type";
                }
                leaf object-type {
                  type Fib-object;
                  description
                    "Object Type";
                }
                leaf attribute-type {
                  type Fib-object-attribute;
                  description
                    "Attribute Type";
                }
                leaf is-mpls {
                  type boolean;
                  description
                    "Is MPLS flag?";
                }
                leaf adjacency-interface {
                  type xr:Interface-name;
                  description
                    "Adjacency interface name";
                }
                uses FIB-GLOBAL-AGGREGATION-ENTRY;
              }
            }
            container aggregation-summary {
              description
                "Aggregation table summary";
              uses FIB-GLOBAL-AGGREGATION-SUMMARY;
            }
          }
        }
        container global-main {
          description
            "FIB Global info from the Main thread";
          container global-retry-db-entries {
            description
              "Details for retry db";
            list global-retry-db-entry {
              description
                "Details for retry_db corresponding to index";
              leaf index {
                type Generic-index;
                description
                  "Index";
              }
              leaf frsc {
                type Generic-index;
                description
                  "Frsc";
              }
              leaf queue-id {
                type Generic-index;
                description
                  "Queue Id";
              }
              uses FIB-RETRY-DB-INFO;
            }
          }
          container clients {
            description
              "Client table";
            list client {
              key "client-id";
              description
                "FIB Client";
              leaf client-id {
                type uint32;
                description
                  "Client ID";
              }
              uses FIB-GLOBAL-CLIENT;
            }
          }
        }
        container protocols {
          description
            "Protocol table";
          list protocol {
            key "protocol-name";
            description
              "Protocol table entry";
            container resource-oor {
              description
                "Resource out of resource information";
              uses FIB-SH-RSRC-AVAIL-OOR-STATE;
            }
            container issu-state {
              description
                "CEF ISSU State";
              uses FIB-ISSU-STATE;
            }
            container cef-tables {
              description
                "Details for cef tables db";
              list cef-table {
                description
                  "Details for cef_db corresponding to
                   table_id";
                leaf table-id {
                  type xr:Hex-integer;
                  description
                    "Table Id";
                }
                leaf vrf-name {
                  type string;
                  description
                    "VRF Name";
                }
                uses FIB-SH-SUM;
              }
            }
            container interfaces {
              description
                "Interface list data details";
              list interface {
                description
                  "Details for interface list data";
                leaf protocol-id {
                  type Fib-protocol;
                  description
                    "Protocol ID";
                }
                leaf interface-list-id {
                  type uint32 {
                    range "0..4294967295";
                  }
                  description
                    "Interface List ID";
                }
                leaf interface-list-name {
                  type xr:Cisco-ios-xr-string;
                  description
                    "Interface List Name";
                }
                uses FIB-GENERIC-INTF-LIST-DATA;
              }
            }
            container resource {
              description
                "Resource information";
              container resource-detail-info {
                description
                  "Detailed info";
                uses FIB-SH-RSRC-AVAIL-STATE;
              }
              container resource-hardware-ingress-info {
                description
                  "Detailed info with ingress hardware info";
                uses FIB-SH-RSRC-AVAIL-STATE;
              }
              container resource-hardware-egress-info {
                description
                  "Detailed info with egress hardware info";
                uses FIB-SH-RSRC-AVAIL-STATE;
              }
              container resource-summary-info {
                description
                  "Summary info";
                uses FIB-SH-RSRC-AVAIL-STATE;
              }
            }
            container fib-summaries {
              description
                "Summary for FIB tables";
              list fib-summary {
                description
                  "Summary for the requested fib table";
                leaf vrf-name {
                  type string;
                  description
                    "VRF Name";
                }
                leaf table-id {
                  type xr:Hex-integer;
                  description
                    "FIB table id";
                }
                uses FIB-SH-SUM;
              }
            }
            container object-queues {
              description
                "Object queue details";
              list object-queue {
                key "object-queue-id";
                description
                  "Details for corresponding object queue id";
                leaf object-queue-id {
                  type uint32 {
                    range "0..255";
                  }
                  description
                    "Object Queue ID";
                }
                uses FIB-OBJECT-QUEUE-INFO;
              }
            }
            container external-summary-all {
              description
                "Summary for all external clients";
              uses FIB-SH-TBL-EXT-SUM-ALL;
            }
            container frr-log {
              description
                "Table of Fast Reroute activation logs";
              container frr-interfaces {
                description
                  "FRR Interface Table";
                list frr-interface {
                  key "frr-interface-name";
                  description
                    "Specify FRR Interface Name";
                  container logs {
                    description
                      "FRR log table";
                    list log {
                      key "log-index";
                      description
                        "Specify index into frr log table";
                      leaf log-index {
                        type uint32;
                        description
                          "FRR Log Index";
                      }
                      uses FIB-SH-FRR-LOG;
                    }
                  }
                  leaf frr-interface-name {
                    type xr:Interface-name;
                    description
                      "Interface Name";
                  }
                }
              }
            }
            container retry-db-entries {
              description
                "Details for retry db";
              list retry-db-entry {
                description
                  "Details for retry_db corresponding to index";
                leaf index {
                  type Generic-index;
                  description
                    "Index";
                }
                leaf frsc {
                  type Generic-index;
                  description
                    "Frsc";
                }
                leaf queue-id {
                  type Generic-index;
                  description
                    "Queue Id";
                }
                uses FIB-RETRY-DB-INFO;
              }
            }
            container protocol-tunnel-database {
              description
                "Protocol tunnel database";
              container ltep-tunnel-hardware-egresses {
                description
                  "Ltep Tunnel database, HW Egress";
                list ltep-tunnel-hardware-egress {
                  description
                    "LTEP table entry, HW Egress";
                  leaf tunnel-type {
                    type Ipvpn-tunnel;
                    description
                      "Tunnel type";
                  }
                  leaf source-address {
                    type xr:Cisco-ios-xr-string;
                    description
                      "Source address";
                  }
                  leaf underlay-table-id {
                    type xr:Hex-integer;
                    description
                      "Underlay Table Id";
                  }
                  leaf vxlan-vni-id {
                    type uint32;
                    description
                      "VxLAN VNI ID";
                  }
                  uses FIB-COMMON-LTEP-ENTRY;
                }
              }
              container rtep-tunnel-hardware-egresses {
                description
                  "Rtep Tunnel database, HW Egress";
                list rtep-tunnel-hardware-egress {
                  description
                    "RTEP table entry, HW Egress";
                  leaf tunnel-type {
                    type Ipvpn-tunnel;
                    description
                      "Tunnel type";
                  }
                  leaf destination-address {
                    type xr:Cisco-ios-xr-string;
                    description
                      "Destination address";
                  }
                  leaf underlay-table-id {
                    type xr:Hex-integer;
                    description
                      "Underlay Table Id";
                  }
                  leaf vxlan-overlay-table-id {
                    type xr:Hex-integer;
                    description
                      "VxLAN Overlay Table Id";
                  }
                  leaf vxlan-e-vni-id {
                    type uint32;
                    description
                      "VxLAN E-VNI ID";
                  }
                  leaf is-default {
                    type boolean;
                    description
                      "Is Default LTEP NVE";
                  }
                  leaf table-id {
                    type xr:Hex-integer;
                    description
                      "LTEP_NVE Table ID";
                  }
                  leaf nve-interface-id {
                    type uint32;
                    description
                      "LTEP_NVE NVE ID";
                  }
                  leaf vni-id {
                    type uint32;
                    description
                      "LTEP_NVE VNI ID";
                  }
                  uses FIB-RTEP-ENTRY;
                }
              }
              container rtep-tunnel-internals {
                description
                  "Rtep tunnel database";
                list rtep-tunnel-internal {
                  description
                    "RTEP table entry";
                  leaf tunnel-type {
                    type Ipvpn-tunnel;
                    description
                      "Tunnel type";
                  }
                  leaf destination-address {
                    type xr:Cisco-ios-xr-string;
                    description
                      "Destination address";
                  }
                  leaf underlay-table-id {
                    type xr:Hex-integer;
                    description
                      "Underlay Table Id";
                  }
                  leaf vxlan-overlay-table-id {
                    type xr:Hex-integer;
                    description
                      "VxLAN Overlay Table Id";
                  }
                  leaf vxlan-e-vni-id {
                    type uint32;
                    description
                      "VxLAN E-VNI ID";
                  }
                  leaf is-default {
                    type boolean;
                    description
                      "Is Default LTEP NVE";
                  }
                  leaf table-id {
                    type xr:Hex-integer;
                    description
                      "LTEP_NVE Table ID";
                  }
                  leaf nve-interface-id {
                    type uint32;
                    description
                      "LTEP_NVE NVE ID";
                  }
                  leaf vni-id {
                    type uint32;
                    description
                      "LTEP_NVE VNI ID";
                  }
                  uses FIB-RTEP-ENTRY;
                }
              }
              container rtep-tunnels {
                description
                  "Rtep tunnel database";
                list rtep-tunnel {
                  description
                    "RTEP table entry";
                  leaf tunnel-type {
                    type Ipvpn-tunnel;
                    description
                      "Tunnel type";
                  }
                  leaf destination-address {
                    type xr:Cisco-ios-xr-string;
                    description
                      "Destination address";
                  }
                  leaf underlay-table-id {
                    type xr:Hex-integer;
                    description
                      "Underlay Table Id";
                  }
                  leaf vxlan-overlay-table-id {
                    type xr:Hex-integer;
                    description
                      "VxLAN Overlay Table Id";
                  }
                  leaf vxlan-e-vni-id {
                    type uint32;
                    description
                      "VxLAN E-VNI ID";
                  }
                  leaf is-default {
                    type boolean;
                    description
                      "Is Default LTEP NVE";
                  }
                  leaf table-id {
                    type xr:Hex-integer;
                    description
                      "LTEP_NVE Table ID";
                  }
                  leaf nve-interface-id {
                    type uint32;
                    description
                      "LTEP_NVE NVE ID";
                  }
                  leaf vni-id {
                    type uint32;
                    description
                      "LTEP_NVE VNI ID";
                  }
                  uses FIB-RTEP-ENTRY;
                }
              }
              container ltep-tunnel-hardware-ingresses {
                description
                  "Ltep Tunnel database, HW Ingress";
                list ltep-tunnel-hardware-ingress {
                  description
                    "LTEP table entry, HW Ingress";
                  leaf tunnel-type {
                    type Ipvpn-tunnel;
                    description
                      "Tunnel type";
                  }
                  leaf source-address {
                    type xr:Cisco-ios-xr-string;
                    description
                      "Source address";
                  }
                  leaf underlay-table-id {
                    type xr:Hex-integer;
                    description
                      "Underlay Table Id";
                  }
                  leaf vxlan-vni-id {
                    type uint32;
                    description
                      "VxLAN VNI ID";
                  }
                  uses FIB-COMMON-LTEP-ENTRY;
                }
              }
              container ltep-tunnel-internals {
                description
                  "Ltep tunnel database";
                list ltep-tunnel-internal {
                  description
                    "LTEP table entry";
                  leaf tunnel-type {
                    type Ipvpn-tunnel;
                    description
                      "Tunnel type";
                  }
                  leaf source-address {
                    type xr:Cisco-ios-xr-string;
                    description
                      "Source address";
                  }
                  leaf underlay-table-id {
                    type xr:Hex-integer;
                    description
                      "Underlay Table Id";
                  }
                  leaf vxlan-vni-id {
                    type uint32;
                    description
                      "VxLAN VNI ID";
                  }
                  uses FIB-COMMON-LTEP-ENTRY;
                }
              }
              container rtep-tunnel-hardware-ingresses {
                description
                  "Rtep Tunnel database, HW Ingress";
                list rtep-tunnel-hardware-ingress {
                  description
                    "RTEP table entry, HW Ingress";
                  leaf tunnel-type {
                    type Ipvpn-tunnel;
                    description
                      "Tunnel type";
                  }
                  leaf destination-address {
                    type xr:Cisco-ios-xr-string;
                    description
                      "Destination address";
                  }
                  leaf underlay-table-id {
                    type xr:Hex-integer;
                    description
                      "Underlay Table Id";
                  }
                  leaf vxlan-overlay-table-id {
                    type xr:Hex-integer;
                    description
                      "VxLAN Overlay Table Id";
                  }
                  leaf vxlan-e-vni-id {
                    type uint32;
                    description
                      "VxLAN E-VNI ID";
                  }
                  leaf is-default {
                    type boolean;
                    description
                      "Is Default LTEP NVE";
                  }
                  leaf table-id {
                    type xr:Hex-integer;
                    description
                      "LTEP_NVE Table ID";
                  }
                  leaf nve-interface-id {
                    type uint32;
                    description
                      "LTEP_NVE NVE ID";
                  }
                  leaf vni-id {
                    type uint32;
                    description
                      "LTEP_NVE VNI ID";
                  }
                  uses FIB-RTEP-ENTRY;
                }
              }
              container vxlan-tunnels {
                description
                  "Vxlan tunnel database";
                list vxlan-tunnel {
                  description
                    "VXLAN evni table entry";
                  leaf vrf-name {
                    type string;
                    description
                      "VXLAN EVNI Table vrf name";
                  }
                  leaf vni-id {
                    type uint32;
                    description
                      "VNI ID";
                  }
                  uses FIB-VNI-INFO-ENTRY;
                }
              }
              container ltep-tunnels {
                description
                  "Ltep tunnel database";
                list ltep-tunnel {
                  description
                    "LTEP table entry";
                  leaf tunnel-type {
                    type Ipvpn-tunnel;
                    description
                      "Tunnel type";
                  }
                  leaf source-address {
                    type xr:Cisco-ios-xr-string;
                    description
                      "Source address";
                  }
                  leaf underlay-table-id {
                    type xr:Hex-integer;
                    description
                      "Underlay Table Id";
                  }
                  leaf vxlan-vni-id {
                    type uint32;
                    description
                      "VxLAN VNI ID";
                  }
                  uses FIB-COMMON-LTEP-ENTRY;
                }
              }
            }
            container vrfs {
              description
                "VRF table";
              list vrf {
                key "vrf-name";
                description
                  "VRF table entry";
                container ip-prefix-details {
                  description
                    "IP FIB prefix detail table";
                  list ip-prefix-detail {
                    description
                      "IP FIB prefix detail table entry";
                    leaf prefix {
                      type inet:ip-address-no-zone;
                      description
                        "Destination IP address";
                    }
                    leaf prefix-length {
                      type xr:Ipv6-prefix-length;
                      description
                        "IP FIB prefix length";
                    }
                    uses FIB-SH-TBL-FIB;
                  }
                }
                container summary {
                  description
                    "Operational data for FIB Tablee";
                  uses FIB-SH-SUM;
                }
                container attributes {
                  description
                    "Information on attribute data";
                  list attribute {
                    description
                      "Attribute Data";
                    leaf attribute-index {
                      type uint32 {
                        range "0..4294967295";
                      }
                      description
                        "Attribute Index";
                    }
                    leaf attribute-local-index {
                      type uint32 {
                        range "0..4294967295";
                      }
                      description
                        "Attribute Local Index";
                    }
                    uses FIB-ATTRIBUTE-DET;
                  }
                }
                container ipv6-d-var-details {
                  description
                    "IPv6 FIB prefix DVAR table";
                  list ipv6-d-var-detail {
                    description
                      "IPv6 FIB prefix dvar entry";
                    leaf table-id {
                      type xr:Hex-integer;
                      description
                        "Table Id";
                    }
                    leaf prefix {
                      type inet:ip-address-no-zone;
                      description
                        "IPv6 address";
                    }
                    leaf prefix-length {
                      type xr:Ipv6-prefix-length;
                      description
                        "IPv6 prefix length";
                    }
                    uses FIB-SH-TBL-FIB-DVARS;
                  }
                }
                container interface-infos {
                  description
                    "Table of InterfaceInfo";
                  list interface-info {
                    key "link-type";
                    description
                      "Specify link type";
                    container interfaces {
                      description
                        "Table of interfaces";
                      list interface {
                        key "interface-name";
                        description
                          "Specify Interface name";
                        leaf interface-name {
                          type xr:Interface-name;
                          description
                            "Interface Name";
                        }
                        uses FIB-SH-INT;
                      }
                    }
                    leaf link-type {
                      type Fib-link;
                      description
                        "Link type";
                    }
                  }
                }
                container recursive-nexthops {
                  description
                    "Information on Recursive Nexthop";
                  list recursive-nexthop {
                    description
                      "Route address, Prefix length";
                    leaf address {
                      type inet:ipv4-address-no-zone;
                      description
                        "Route Address ";
                    }
                    leaf prefix-length {
                      type xr:Ipv4-prefix-length;
                      description
                        "Prefix Length";
                    }
                    uses FIB-SH-REC-NH;
                  }
                }
                container ip-prefix-briefs {
                  description
                    "IP FIB prefix brief table";
                  list ip-prefix-brief {
                    description
                      "IP FIB prefix brief table entry";
                    leaf prefix {
                      type inet:ip-address-no-zone;
                      description
                        "Destination IP address";
                    }
                    leaf prefix-length {
                      type xr:Ipv6-prefix-length;
                      description
                        "IP FIB prefix length";
                    }
                    uses FIB-SH-TBL-FIB;
                  }
                }
                container ipv4-d-var-details {
                  description
                    "IPv4 FIB prefix DVAR table";
                  list ipv4-d-var-detail {
                    description
                      "IPv4 FIB prefix dvar entry";
                    leaf table-id {
                      type xr:Hex-integer;
                      description
                        "Table Id";
                    }
                    leaf prefix {
                      type inet:ipv4-address-no-zone;
                      description
                        "IPv4 address";
                    }
                    leaf prefix-length {
                      type xr:Ipv4-prefix-length;
                      description
                        "IPv4 prefix length";
                    }
                    uses FIB-SH-TBL-FIB-DVARS;
                  }
                }
                container attribute-summary {
                  description
                    "Information on attribute summary";
                  uses FIB-ATTRIBUTE-SUMMARY;
                }
                container ipv6-recursive-nexthops {
                  description
                    "Information on IPv6 Recursive Nexthop";
                  list ipv6-recursive-nexthop {
                    description
                      "IPv6 Route address, IPv6 Prefix length";
                    leaf address {
                      type inet:ip-address-no-zone;
                      description
                        "IPv6 Route Address ";
                    }
                    leaf prefix-length {
                      type xr:Ipv6-prefix-length;
                      description
                        "IPv6 Prefix Length";
                    }
                    uses FIB-SH-REC-NH;
                  }
                }
                container policy-database {
                  description
                    "Database of Policies";
                  container policy-hardware-egresses {
                    description
                      "Policy Table";
                    list policy-hardware-egress {
                      key "policy-name";
                      description
                        "Policy Entry";
                      leaf policy-name {
                        type xr:Cisco-ios-xr-string {
                          length "1..64";
                        }
                        description
                          "Policy Name";
                      }
                      uses FIB-SH-POLICY-ENTRY;
                    }
                  }
                  container policies {
                    description
                      "Policy Table";
                    list policy {
                      key "policy-name";
                      description
                        "Policy Entry";
                      leaf policy-name {
                        type xr:Cisco-ios-xr-string {
                          length "1..64";
                        }
                        description
                          "Policy Name";
                      }
                      uses FIB-SH-POLICY-ENTRY;
                    }
                  }
                  container policy-hardware-ingresses {
                    description
                      "Policy Table";
                    list policy-hardware-ingress {
                      key "policy-name";
                      description
                        "Policy Entry";
                      leaf policy-name {
                        type xr:Cisco-ios-xr-string {
                          length "1..64";
                        }
                        description
                          "Policy Name";
                      }
                      uses FIB-SH-POLICY-ENTRY;
                    }
                  }
                }
                container nh-info {
                  description
                    "FIB NHInfo table";
                  container nh-info-detail-hardware-egress {
                    description
                      "NHInfoTable is accessed by two keys;
                       {NHInterface,NHAddress}";
                    container nh-info-local-mpls-detail-hardware-egresses {
                      description
                        "Local (non-remote) nhinfo";
                      list nh-info-local-mpls-detail-hardware-egress {
                        description
                          "MPLS Detail-Hardware-Egress NHinfo
                           entry";
                        leaf nh-local-type {
                          type Fibnh-local;
                          description
                            "Next-hop Type";
                        }
                        leaf parent-nh-interface-name {
                          type xr:Interface-name;
                          description
                            "Parent Interface Name";
                        }
                        leaf nh-interface-name {
                          type xr:Interface-name;
                          description
                            "Interface Name";
                        }
                        leaf nh-proto {
                          type Fib-protocol;
                          description
                            "Next-hop proto";
                        }
                        leaf nh-pfx-length {
                          type uint32;
                          description
                            "Next-hop prefix length";
                        }
                        leaf nh-address {
                          type xr:Cisco-ios-xr-string;
                          description
                            "Next-hop address in string format";
                        }
                        uses FIB-SH-NHINFO;
                      }
                    }
                    container nh-info-special-detail-hardware-egress {
                      description
                        "Detail hardware egress info for Special
                         nhinfo";
                      uses NH-INFO-SPECIAL-NULL-DETAIL-HARDWARE-EGRESS;
                      uses NH-INFO-SPECIAL-PUNT-DETAIL-HARDWARE-EGRESS;
                      uses NH-INFO-SPECIAL-DISCARD-DETAIL-HARDWARE-EGRESS;
                      uses NH-INFO-SPECIAL-DROP-DETAIL-HARDWARE-EGRESS;
                    }
                    container nh-info-local-detail-hardware-egresses {
                      description
                        "Local (non-remote) nhinfo";
                      list nh-info-local-detail-hardware-egress {
                        description
                          "Detail-Hardware-Egress NHinfo entry";
                        leaf nh-local-type {
                          type Fibnh-local;
                          description
                            "Next-hop Type";
                        }
                        leaf parent-nh-interface-name {
                          type xr:Interface-name;
                          description
                            "Parent Interface Name";
                        }
                        leaf nh-interface-name {
                          type xr:Interface-name;
                          description
                            "Interface Name";
                        }
                        leaf nh-proto {
                          type Fib-protocol;
                          description
                            "Next-hop proto";
                        }
                        leaf nh-pfx-length {
                          type uint32;
                          description
                            "Next-hop prefix length";
                        }
                        leaf nh-address {
                          type xr:Cisco-ios-xr-string;
                          description
                            "Next-hop address in string format";
                        }
                        uses FIB-SH-NHINFO;
                      }
                    }
                    container nh-info-remote-mpls-detail-hardware-egresses {
                      description
                        "Detail hardware egress info for remote
                         NHInfo table";
                      list nh-info-remote-mpls-detail-hardware-egress {
                        description
                          "MPLS Detail-Hardware-Egress NHinfo
                           entry";
                        leaf nh-remote-type {
                          type Fibnh-remote;
                          description
                            "Next-hop Type";
                        }
                        leaf parent-nh-interface-name {
                          type xr:Interface-name;
                          description
                            "Parent Interface Name";
                        }
                        leaf nh-interface-name {
                          type xr:Interface-name;
                          description
                            "Interface Name";
                        }
                        leaf nh-proto {
                          type Fib-protocol;
                          description
                            "Next-hop proto";
                        }
                        leaf nh-pfx-length {
                          type uint32;
                          description
                            "Next-hop prefix length";
                        }
                        leaf nh-address {
                          type xr:Cisco-ios-xr-string;
                          description
                            "Next-hop address in string format";
                        }
                        uses FIB-SH-NHINFO;
                      }
                    }
                    container nh-info-special-mpls-detail-hardware-egress {
                      description
                        "Detail hardware egress info for Special
                         nhinfo";
                      uses NH-INFO-SPECIAL-NULL-DETAIL-HARDWARE-EGRESS;
                      uses NH-INFO-SPECIAL-PUNT-DETAIL-HARDWARE-EGRESS;
                      uses NH-INFO-SPECIAL-DISCARD-DETAIL-HARDWARE-EGRESS;
                      uses NH-INFO-SPECIAL-DROP-DETAIL-HARDWARE-EGRESS;
                    }
                    container nh-info-remote-detail-hardware-egresses {
                      description
                        "Detail hardware egress info for remote
                         NHInfo table";
                      list nh-info-remote-detail-hardware-egress {
                        description
                          "Detail-Hardware-Egress NHinfo entry";
                        leaf nh-remote-type {
                          type Fibnh-remote;
                          description
                            "Next-hop Type";
                        }
                        leaf parent-nh-interface-name {
                          type xr:Interface-name;
                          description
                            "Parent Interface Name";
                        }
                        leaf nh-interface-name {
                          type xr:Interface-name;
                          description
                            "Interface Name";
                        }
                        leaf nh-proto {
                          type Fib-protocol;
                          description
                            "Next-hop proto";
                        }
                        leaf nh-pfx-length {
                          type uint32;
                          description
                            "Next-hop prefix length";
                        }
                        leaf nh-address {
                          type xr:Cisco-ios-xr-string;
                          description
                            "Next-hop address in string format";
                        }
                        uses FIB-SH-NHINFO;
                      }
                    }
                  }
                  container nh-info-detail {
                    description
                      "NHInfoTable is accessed by two keys;
                       {NHInterface,NHAddress}";
                    container nh-info-local-details {
                      description
                        "Local (non-remote) nhinfo";
                      list nh-info-local-detail {
                        description
                          "Detail NHinfo entry";
                        leaf nh-local-type {
                          type Fibnh-local;
                          description
                            "Next-hop Type";
                        }
                        leaf parent-nh-interface-name {
                          type xr:Interface-name;
                          description
                            "Parent Interface Name";
                        }
                        leaf nh-interface-name {
                          type xr:Interface-name;
                          description
                            "Interface Name";
                        }
                        leaf nh-proto {
                          type Fib-protocol;
                          description
                            "Next-hop proto";
                        }
                        leaf nh-pfx-length {
                          type uint32;
                          description
                            "Next-hop prefix length";
                        }
                        leaf nh-address {
                          type xr:Cisco-ios-xr-string;
                          description
                            "Next-hop address in string format";
                        }
                        uses FIB-SH-NHINFO;
                      }
                    }
                    container nh-info-remote-mpls-details {
                      description
                        "Detailed Remote NHInfo table";
                      list nh-info-remote-mpls-detail {
                        description
                          "MPLS Detail NHinfo entry";
                        leaf nh-remote-type {
                          type Fibnh-remote;
                          description
                            "Next-hop Type";
                        }
                        leaf parent-nh-interface-name {
                          type xr:Interface-name;
                          description
                            "Parent Interface Name";
                        }
                        leaf nh-interface-name {
                          type xr:Interface-name;
                          description
                            "Interface Name";
                        }
                        leaf nh-proto {
                          type Fib-protocol;
                          description
                            "Next-hop proto";
                        }
                        leaf nh-pfx-length {
                          type uint32;
                          description
                            "Next-hop prefix length";
                        }
                        leaf nh-address {
                          type xr:Cisco-ios-xr-string;
                          description
                            "Next-hop address in string format";
                        }
                        uses FIB-SH-NHINFO;
                      }
                    }
                    container nh-info-local-mpls-details {
                      description
                        "Local (non-remote) nhinfo";
                      list nh-info-local-mpls-detail {
                        description
                          "MPLS Detail NHinfo entry";
                        leaf nh-local-type {
                          type Fibnh-local;
                          description
                            "Next-hop Type";
                        }
                        leaf parent-nh-interface-name {
                          type xr:Interface-name;
                          description
                            "Parent Interface Name";
                        }
                        leaf nh-interface-name {
                          type xr:Interface-name;
                          description
                            "Interface Name";
                        }
                        leaf nh-proto {
                          type Fib-protocol;
                          description
                            "Next-hop proto";
                        }
                        leaf nh-pfx-length {
                          type uint32;
                          description
                            "Next-hop prefix length";
                        }
                        leaf nh-address {
                          type xr:Cisco-ios-xr-string;
                          description
                            "Next-hop address in string format";
                        }
                        uses FIB-SH-NHINFO;
                      }
                    }
                    container nh-info-special-detail {
                      description
                        "Special nhinfo";
                      uses NH-INFO-SPECIAL-PUNT-DETAIL;
                      uses NH-INFO-SPECIAL-DROP-DETAIL;
                      uses NH-INFO-SPECIAL-NULL-DETAIL;
                      uses NH-INFO-SPECIAL-DISCARD-DETAIL;
                    }
                    container nh-info-special-mpls-detail {
                      description
                        "Special nhinfo";
                      uses NH-INFO-SPECIAL-PUNT-DETAIL;
                      uses NH-INFO-SPECIAL-DROP-DETAIL;
                      uses NH-INFO-SPECIAL-NULL-DETAIL;
                      uses NH-INFO-SPECIAL-DISCARD-DETAIL;
                    }
                    container nh-info-remote-details {
                      description
                        "Detailed Remote NHInfo table";
                      list nh-info-remote-detail {
                        description
                          "Detail NHinfo entry";
                        leaf nh-remote-type {
                          type Fibnh-remote;
                          description
                            "Next-hop Type";
                        }
                        leaf parent-nh-interface-name {
                          type xr:Interface-name;
                          description
                            "Parent Interface Name";
                        }
                        leaf nh-interface-name {
                          type xr:Interface-name;
                          description
                            "Interface Name";
                        }
                        leaf nh-proto {
                          type Fib-protocol;
                          description
                            "Next-hop proto";
                        }
                        leaf nh-pfx-length {
                          type uint32;
                          description
                            "Next-hop prefix length";
                        }
                        leaf nh-address {
                          type xr:Cisco-ios-xr-string;
                          description
                            "Next-hop address in string format";
                        }
                        uses FIB-SH-NHINFO;
                      }
                    }
                  }
                  container nh-info-detail-hardware-ingress {
                    description
                      "NHInfoTable is accessed by two keys;
                       {NHInterface,NHAddress}";
                    container nh-info-special-mpls-detail-hardware-ingress {
                      description
                        "Special nhinfo";
                      uses NH-INFO-SPECIAL-PUNT-DETAIL-HARDWARE-INGRESS;
                      uses NH-INFO-SPECIAL-NULL-DETAIL-HARDWARE-INGRESS;
                      uses NH-INFO-SPECIAL-DROP-DETAIL-HARDWARE-INGRESS;
                      uses NH-INFO-SPECIAL-DISCARD-DETAIL-HARDWARE-INGRESS;
                    }
                    container nh-info-remote-detail-hardware-ingresses {
                      description
                        "Detailed hardware ingress info for
                         remote NHInfo table";
                      list nh-info-remote-detail-hardware-ingress {
                        description
                          "Detail-Hardware-Ingress NHinfo entry";
                        leaf nh-remote-type {
                          type Fibnh-remote;
                          description
                            "Next-hop Type";
                        }
                        leaf parent-nh-interface-name {
                          type xr:Interface-name;
                          description
                            "Parent Interface Name";
                        }
                        leaf nh-interface-name {
                          type xr:Interface-name;
                          description
                            "Interface Name";
                        }
                        leaf nh-proto {
                          type Fib-protocol;
                          description
                            "Next-hop proto";
                        }
                        leaf nh-pfx-length {
                          type uint32;
                          description
                            "Next-hop prefix length";
                        }
                        leaf nh-address {
                          type xr:Cisco-ios-xr-string;
                          description
                            "Next-hop address in string format";
                        }
                        uses FIB-SH-NHINFO;
                      }
                    }
                    container nh-info-remote-mpls-detail-hardware-ingresses {
                      description
                        "Detailed hardware ingress info for
                         remote NHInfo table";
                      list nh-info-remote-mpls-detail-hardware-ingress {
                        description
                          "MPLS Detail-Hardware-Ingress NHinfo
                           entry";
                        leaf nh-remote-type {
                          type Fibnh-remote;
                          description
                            "Next-hop Type";
                        }
                        leaf parent-nh-interface-name {
                          type xr:Interface-name;
                          description
                            "Parent Interface Name";
                        }
                        leaf nh-interface-name {
                          type xr:Interface-name;
                          description
                            "Interface Name";
                        }
                        leaf nh-proto {
                          type Fib-protocol;
                          description
                            "Next-hop proto";
                        }
                        leaf nh-pfx-length {
                          type uint32;
                          description
                            "Next-hop prefix length";
                        }
                        leaf nh-address {
                          type xr:Cisco-ios-xr-string;
                          description
                            "Next-hop address in string format";
                        }
                        uses FIB-SH-NHINFO;
                      }
                    }
                    container nh-info-local-detail-hardware-ingresses {
                      description
                        "Local (non-remote) nhinfo";
                      list nh-info-local-detail-hardware-ingress {
                        description
                          "Detail-Hardware-Ingress NHinfo entry";
                        leaf nh-local-type {
                          type Fibnh-local;
                          description
                            "Next-hop Type";
                        }
                        leaf parent-nh-interface-name {
                          type xr:Interface-name;
                          description
                            "Parent Interface Name";
                        }
                        leaf nh-interface-name {
                          type xr:Interface-name;
                          description
                            "Interface Name";
                        }
                        leaf nh-proto {
                          type Fib-protocol;
                          description
                            "Next-hop proto";
                        }
                        leaf nh-pfx-length {
                          type uint32;
                          description
                            "Next-hop prefix length";
                        }
                        leaf nh-address {
                          type xr:Cisco-ios-xr-string;
                          description
                            "Next-hop address in string format";
                        }
                        uses FIB-SH-NHINFO;
                      }
                    }
                    container nh-info-special-detail-hardware-ingress {
                      description
                        "Special nhinfo";
                      uses NH-INFO-SPECIAL-PUNT-DETAIL-HARDWARE-INGRESS;
                      uses NH-INFO-SPECIAL-NULL-DETAIL-HARDWARE-INGRESS;
                      uses NH-INFO-SPECIAL-DROP-DETAIL-HARDWARE-INGRESS;
                      uses NH-INFO-SPECIAL-DISCARD-DETAIL-HARDWARE-INGRESS;
                    }
                    container nh-info-local-mpls-detail-hardware-ingresses {
                      description
                        "Local (non-remote) nhinfo";
                      list nh-info-local-mpls-detail-hardware-ingress {
                        description
                          "MPLS Detail-Hardware-Ingress NHinfo
                           entry";
                        leaf nh-local-type {
                          type Fibnh-local;
                          description
                            "Next-hop Type";
                        }
                        leaf parent-nh-interface-name {
                          type xr:Interface-name;
                          description
                            "Parent Interface Name";
                        }
                        leaf nh-interface-name {
                          type xr:Interface-name;
                          description
                            "Interface Name";
                        }
                        leaf nh-proto {
                          type Fib-protocol;
                          description
                            "Next-hop proto";
                        }
                        leaf nh-pfx-length {
                          type uint32;
                          description
                            "Next-hop prefix length";
                        }
                        leaf nh-address {
                          type xr:Cisco-ios-xr-string;
                          description
                            "Next-hop address in string format";
                        }
                        uses FIB-SH-NHINFO;
                      }
                    }
                  }
                  container nh-info-brief {
                    description
                      "NHInfoTable is accessed by two keys;
                       {NHInterface,NHAddress}";
                    container nh-info-special-mpls-brief {
                      description
                        "Special nhinfo";
                      uses NH-INFO-SPECIAL-DISCARD-BRIEF;
                      uses NH-INFO-SPECIAL-NULL-BRIEF;
                      uses NH-INFO-SPECIAL-PUNT-BRIEF;
                      uses NH-INFO-SPECIAL-DROP-BRIEF;
                    }
                    container nh-info-special-brief {
                      description
                        "Special nhinfo";
                      uses NH-INFO-SPECIAL-DISCARD-BRIEF;
                      uses NH-INFO-SPECIAL-NULL-BRIEF;
                      uses NH-INFO-SPECIAL-PUNT-BRIEF;
                      uses NH-INFO-SPECIAL-DROP-BRIEF;
                    }
                    container nh-info-local-mpls-briefs {
                      description
                        "Local (non-remote) nhinfo";
                      list nh-info-local-mpls-brief {
                        description
                          "MPLS Brief NHinfo entry";
                        leaf nh-local-type {
                          type Fibnh-local;
                          description
                            "Next-hop Type";
                        }
                        leaf parent-nh-interface-name {
                          type xr:Interface-name;
                          description
                            "Parent Interface Name";
                        }
                        leaf nh-interface-name {
                          type xr:Interface-name;
                          description
                            "Interface Name";
                        }
                        leaf nh-proto {
                          type Fib-protocol;
                          description
                            "Next-hop proto";
                        }
                        leaf nh-pfx-length {
                          type uint32;
                          description
                            "Next-hop prefix length";
                        }
                        leaf nh-address {
                          type xr:Cisco-ios-xr-string;
                          description
                            "Next-hop address in string format";
                        }
                        uses FIB-SH-NHINFO;
                      }
                    }
                    container nh-info-remote-briefs {
                      description
                        "remote nhinfo";
                      list nh-info-remote-brief {
                        description
                          "Brief NHinfo entry";
                        leaf nh-remote-type {
                          type Fibnh-remote;
                          description
                            "Next-hop Type";
                        }
                        leaf parent-nh-interface-name {
                          type xr:Interface-name;
                          description
                            "Parent Interface Name";
                        }
                        leaf nh-interface-name {
                          type xr:Interface-name;
                          description
                            "Interface Name";
                        }
                        leaf nh-proto {
                          type Fib-protocol;
                          description
                            "Next-hop proto";
                        }
                        leaf nh-pfx-length {
                          type uint32;
                          description
                            "Next-hop prefix length";
                        }
                        leaf nh-address {
                          type xr:Cisco-ios-xr-string;
                          description
                            "Next-hop address in string format";
                        }
                        uses FIB-SH-NHINFO;
                      }
                    }
                    container nh-info-local-briefs {
                      description
                        "Local (non-remote) nhinfo";
                      list nh-info-local-brief {
                        description
                          "Brief NHinfo entry";
                        leaf nh-local-type {
                          type Fibnh-local;
                          description
                            "Next-hop Type";
                        }
                        leaf parent-nh-interface-name {
                          type xr:Interface-name;
                          description
                            "Parent Interface Name";
                        }
                        leaf nh-interface-name {
                          type xr:Interface-name;
                          description
                            "Interface Name";
                        }
                        leaf nh-proto {
                          type Fib-protocol;
                          description
                            "Next-hop proto";
                        }
                        leaf nh-pfx-length {
                          type uint32;
                          description
                            "Next-hop prefix length";
                        }
                        leaf nh-address {
                          type xr:Cisco-ios-xr-string;
                          description
                            "Next-hop address in string format";
                        }
                        uses FIB-SH-NHINFO;
                      }
                    }
                    container nh-info-remote-mpls-briefs {
                      description
                        "remote nhinfo";
                      list nh-info-remote-mpls-brief {
                        description
                          "MPLS Brief NHinfo entry";
                        leaf nh-remote-type {
                          type Fibnh-remote;
                          description
                            "Next-hop Type";
                        }
                        leaf parent-nh-interface-name {
                          type xr:Interface-name;
                          description
                            "Parent Interface Name";
                        }
                        leaf nh-interface-name {
                          type xr:Interface-name;
                          description
                            "Interface Name";
                        }
                        leaf nh-proto {
                          type Fib-protocol;
                          description
                            "Next-hop proto";
                        }
                        leaf nh-pfx-length {
                          type uint32;
                          description
                            "Next-hop prefix length";
                        }
                        leaf nh-address {
                          type xr:Cisco-ios-xr-string;
                          description
                            "Next-hop address in string format";
                        }
                        uses FIB-SH-NHINFO;
                      }
                    }
                  }
                }
                leaf vrf-name {
                  type string;
                  description
                    "VRF Name";
                }
              }
            }
            container exact-routes {
              description
                "Exact Route Table";
              list exact-route {
                description
                  "Exact route for the given source and
                   destination addresses";
                leaf protocol-name {
                  type Fib-protocol;
                  description
                    "Fib Protocol Name";
                }
                leaf vrf-name {
                  type string;
                  description
                    "VRF Name";
                }
                leaf source {
                  type xr:Cisco-ios-xr-string;
                  description
                    "Source address";
                }
                leaf destination {
                  type xr:Cisco-ios-xr-string;
                  description
                    "Destination address";
                }
                leaf ipv6-flow-label {
                  type Fibipv6-flow-label;
                  description
                    "IPv6 flow label (applies only to and used
                     only for IPv6)";
                }
                uses FIB-SH-TBL-FIB;
              }
            }
            container protocol-global {
              description
                "FIB SRV6 global information";
              container segment-routing {
                description
                  "FIB SRV6 global segment routing information";
                container srv6 {
                  description
                    "FIB ipv6 global segment routing srv6
                     information";
                  uses FIB-SRV6-GBL-UPD;
                }
              }
            }
            container nh-ids {
              description
                "NHIdTable is accessed by two keys; {NHId}
                 and/or {NHInterface,NHAddress";
              list nh-id {
                description
                  "NextHopId table entry";
                leaf nh-id {
                  type uint32;
                  description
                    "NexthopId Value";
                }
                leaf nh-interface-name {
                  type xr:Interface-name;
                  description
                    "Interface Name";
                }
                leaf nh-address {
                  type xr:Cisco-ios-xr-string;
                  description
                    "Next-hop address in string format (e.g., 1
                     .2.3.4)";
                }
                uses FIB-SH-NHID-ENTRY;
              }
            }
            container frr-nhinfo-pendings {
              description
                "FIB FRR NHINFO pending information";
              list frr-nhinfo-pending {
                description
                  "FIB FRR Nhinfo pending information";
                leaf queue-index {
                  type Generic-index;
                  description
                    "FIB FRR Queue Index";
                }
                leaf frr-type {
                  type Fibfrr;
                  description
                    "FRR Type";
                }
                leaf link-type {
                  type Fib-link;
                  description
                    "Link Type";
                }
                leaf prefix-length {
                  type Prefix-len-range;
                  description
                    "Prefix Length";
                }
                leaf interface-name {
                  type xr:Interface-name;
                  description
                    "Interface Name";
                }
                leaf main-interface-name {
                  type xr:Interface-name;
                  description
                    "Main Interface Name";
                }
                leaf next-hop-prefix {
                  type inet:ip-address-no-zone;
                  description
                    "NextHop Address";
                }
                leaf replicated-nh-type {
                  type Fibnh-info-repl;
                  description
                    "Replicated NextHop Type";
                }
                uses FIB-SH-FRR-NHINFO;
              }
            }
            container external-client-summaries {
              description
                "External Client Summary Table";
              list external-client-summary {
                description
                  "Summary of the external clients";
                leaf ecd-ver {
                  type uint32;
                  description
                    "Ecd Version";
                }
                leaf id {
                  type uint32;
                  description
                    "ID of the client: ECDv1 is component id,
                     ECDv2 is client id";
                }
                uses FIB-SH-TBL-EXT-CLIENT-SUM;
              }
            }
            container misc {
              description
                "CEF misc hidden data";
              uses FIB-SH-MISC;
            }
            container object-queue-entries {
              description
                "Object queue entry details";
              list object-queue-entry {
                key "object-queue-id";
                description
                  "Object queue id";
                container object-queue-entry-infos {
                  description
                    "Details for corresponding object queue
                     entry";
                  list object-queue-entry-info {
                    key "item-index";
                    description
                      "Details for corresponding object queue
                       entry";
                    leaf item-index {
                      type uint32 {
                        range "0..4294967295";
                      }
                      description
                        "Item Index";
                    }
                    uses FIB-OBJECT-QUEUE-ITEM-INFO;
                  }
                }
                leaf object-queue-id {
                  type uint32 {
                    range "0..255";
                  }
                  description
                    "Object Queue ID";
                }
              }
            }
            container local-label {
              description
                "Fib Local label";
              container conflicts {
                description
                  "FIB Local-label conflicts database";
                list conflict {
                  description
                    "CEF Local-label conflicts entry";
                  leaf label {
                    type Fib-label;
                    description
                      "Local label";
                  }
                  leaf source {
                    type Fib-route-source;
                    description
                      "Route source";
                  }
                  leaf ll-ctype {
                    type Fibllc-entry;
                    description
                      "Type of entry";
                  }
                  leaf pfx-tbl-id {
                    type uint32;
                    description
                      "Table ID of IP prefix";
                  }
                  leaf prefix {
                    type xr:Cisco-ios-xr-string;
                    description
                      "IP Prefix";
                  }
                  leaf prefix-len {
                    type uint32;
                    description
                      "Length of IP Prefix";
                  }
                  uses FIB-MPLS-LLC;
                }
              }
            }
            leaf protocol-name {
              type Fib-protocol;
              description
                "Protocol Name ";
            }
          }
        }
        leaf node-name {
          type xr:Node-id;
          description
            "Node name";
        }
      }
    }
  }
  container oc-aft-l3 {
    config false;
    description
      "Openconfig L3 abstract forwarding table data";
    container vrfs {
      description
        "Table VRFs - openconfig network-instances";
      list vrf {
        key "vrf-name";
        description
          "VRF/network-instace table";
        container abstract-forwarding-tables {
          description
            "Abstract forwarding table per FIB protocol";
          container mpls {
            description
              "MPLS abstract forwarding table";
            container labels {
              description
                "Table of MPLS labels";
              list label {
                key "label";
                description
                  "Label data";
                leaf label {
                  type string;
                  description
                    "Label";
                }
                uses STATE;
              }
            }
          }
          container next-hop-groups {
            description
              "Next-hop groups associated with the
               forwarding instance";
            list next-hop-group {
              key "nh-grp-id";
              description
                "A next-hop group associated with the
                 forwarding instance";
              container condition-groups {
                description
                  "A condition group associated with the
                   forwarding instance";
                list condition-group {
                  key "cond-id";
                  description
                    "A condition group associated with the
                     forwarding instance";
                  container state {
                    description
                      "A condition group associated with the
                       forwarding instance";
                    uses FIB-OC-AFT-COND-GRP-STATE-V2;
                  }
                  leaf cond-id {
                    type uint32;
                    description
                      "A unique ID identifying the condition
                       group entry for the AFT entry";
                  }
                }
              }
              container state {
                description
                  "A next-hop group associated with the
                   forwarding instance";
                uses FIB-OC-AFT-NH-GROUP-STATE-V2;
              }
              leaf nh-grp-id {
                type uint32;
                description
                  "A unique ID identifying the next-hop group
                   entry for the AFT entry";
              }
            }
          }
          container next-hops {
            description
              "A next-hop associated with the forwarding
               instance";
            list next-hop {
              key "nh-id";
              description
                "Prefix data";
              container state {
                description
                  "A unique index identifying the next-hop
                   entry for the AFT nexthop entry";
                uses FIB-OC-AFT-NEXTHOP-V2;
              }
              leaf nh-id {
                type uint32;
                description
                  "A unique ID identifying the next-hop entry
                   for the AFT nexthop entry";
              }
            }
          }
          container ipv6-unicast {
            description
              "IPv6 abstract forwarding table";
            uses PREFIX-TABLE;
          }
          container ipv4-unicast {
            description
              "IPv4 abstract forwarding table";
            uses PREFIX-TABLE;
          }
        }
        leaf vrf-name {
          type xr:Cisco-ios-xr-string;
          description
            "Network Instance Name";
        }
      }
    }
    container protocol {
      description
        "Abstract forwarding table per FIB protocol";
      container ipv6 {
        description
          "IPv6 abstract forwarding table";
        uses OOR;
        uses ERROR;
      }
      container ipv4 {
        description
          "IPv4 abstract forwarding table";
        uses OOR;
        uses ERROR;
      }
    }
  }
  container mpls-forwarding {
    config false;
    description
      "MPLS forwarding operational data";
    container nodes {
      description
        "Table of Nodes";
      list node {
        key "node-name";
        description
          "Operational data for a specific Node";
        container forwarding-summary {
          description
            "MPLS forwarding summary";
          uses MPLS-FWDING-SUMMARY;
        }
        container frr-logs {
          description
            "FRR Log Table";
          list frr-log {
            key "event-id";
            description
              "FRR Log information";
            leaf event-id {
              type uint32;
              description
                "Event ID";
            }
            uses FIB-MPLS-FRR-EVENT;
          }
        }
        container label-fib {
          description
            "Labels For FIB";
          container forwarding-details {
            description
              "MPLS Forwarding Detail table";
            list forwarding-detail {
              description
                "MPLS forwarding details";
              leaf label-value {
                type Mpls-label;
                description
                  "Local label value";
              }
              leaf eos {
                type Mplseos;
                description
                  "End of stack flag";
              }
              uses MPLS-SH-LEAF;
            }
          }
          container informations {
            description
              "Forwarding filtering details";
            list information {
              description
                "MPLS forwarding information";
              leaf label-value {
                type Mpls-label;
                description
                  "Local label value";
              }
              leaf eos {
                type Mplseos;
                description
                  "End of stack flag";
              }
              uses MPLS-SH-LEAF;
            }
          }
          container label-security {
            description
              "MPLS label security";
            container interfaces {
              description
                "MPLS label security interface table";
              list interface {
                key "interface-name";
                description
                  "Specify interface Name";
                leaf interface-name {
                  type xr:Interface-name;
                  description
                    "Interface Name";
                }
                uses MPLS-LABEL-SECURITY-INTF;
              }
            }
            container summary {
              description
                "MPLS label security summary";
              uses MPLS-LABEL-SECURITY-SUMMARY;
            }
          }
        }
        container tunnel {
          description
            "TE Tunnel information";
          container forwarding-tunnels {
            description
              "Forwarding details for TE tunnels";
            list forwarding-tunnel {
              key "interface-name";
              description
                "Forwarding information for the TE tunnel";
              leaf interface-name {
                type xr:Interface-name;
                description
                  "Interface Name";
              }
              uses MPLS-SH-TEHEAD;
            }
          }
        }
        container frr-database {
          description
            "MPLS forwarding FRR Database";
          container frrdb-summary {
            description
              "MPLS forwarding FRR Database Summary";
            uses FIB-MPLS-FRR-DB-SUM;
          }
          container frrdb-protected-interface-table-summaries {
            description
              "MPLS forwarding FRR Database Protected
               Interface Summary Table";
            list frrdb-protected-interface-table-summary {
              key "interface-name";
              description
                "MPLS forwarding FRR Database Protected
                 Interface Summary";
              leaf interface-name {
                type xr:Interface-name;
                description
                  "Interface Name";
              }
              uses FIB-MPLS-FRR-DB-SUM;
            }
          }
          container frrdb-tunnel-midpoint-summary {
            description
              "MPLS forwarding FRR Database Tunnel Midpoint
               Summary";
            uses FIB-MPLS-FRR-DB-SUM;
          }
          container frrdb-tunnel-midpoints {
            description
              "MPLS forwarding FRR Database Tunnel Midpoint
               Table";
            list frrdb-tunnel-midpoint {
              key "local-label";
              description
                "MPLS forwarding FRR Database Tunnel Midpoint
                 Entry";
              leaf local-label {
                type Mpls-label;
                description
                  "Local label value";
              }
              uses MPLS-FRR-DB-ENTRY;
            }
          }
          container frrdb-tunnel-heads {
            description
              "MPLS forwarding FRR Database Tunnel Head
               Table";
            list frrdb-tunnel-head {
              key "interface-name";
              description
                "MPLS forwarding FRR Database Tunnel Head
                 Entry";
              leaf interface-name {
                type xr:Interface-name;
                description
                  "Interface Name";
              }
              uses MPLS-FRR-DB-ENTRY;
            }
          }
          container frrdb-tunnel-head-summary {
            description
              "MPLS forwarding FRR Database Tunnel Head
               Summary";
            uses FIB-MPLS-FRR-DB-SUM;
          }
          container frrdb-backup-interface-summaries {
            description
              "MPLS forwarding FRR Database Backup Interface
               Summary Table";
            list frrdb-backup-interface-summary {
              key "interface-name";
              description
                "MPLS forwarding FRR Database Backup
                 Interface Summary";
              leaf interface-name {
                type xr:Interface-name;
                description
                  "Interface Name";
              }
              uses FIB-MPLS-FRR-DB-SUM;
            }
          }
        }
        leaf node-name {
          type xr:Node-id;
          description
            "Node ID";
        }
      }
    }
  }
}
