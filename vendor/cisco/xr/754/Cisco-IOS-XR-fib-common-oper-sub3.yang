submodule Cisco-IOS-XR-fib-common-oper-sub3 {
  belongs-to Cisco-IOS-XR-fib-common-oper {
    prefix Cisco-IOS-XR-fib-common-oper;
  }

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR fib-common package operational data.
     
     Copyright (c) 2013-2023 by Cisco Systems, Inc.
     All rights reserved.";

  revision 2023-02-06 {
    description
      "Added disable-rfc5549-ipv4-over-ipv6-nexthop platform capability.
       2022-10-17
         CNHG changes
       2022-04-27
         Added vxlan-vni-id to ltep-tunnel
       2022-03-15
         Added vxlan-tunnels
       2022-02-01
         Added policy and hardware ingress and egress paths
       2021-11-26
         Added ltep-tunnels and hardware ingress and egress paths
       2021-11-05
         Added rtep-tunnels and hardware ingress and egress paths
       2021-11-03
         Added ltep-nve-tunnels hardware ingress and egress paths
       2021-10-23
         Added ltep-nve-tunnels and added object-id to object-base";
    semver:module-version "4.0.1M";
  }
  revision 2021-10-17 {
    description
      "Modify the type of list fsum-attr-cnt
       2021-09-17
          Rename lists unicast-prefix, broadcast-prefix and leafs num-retry-objects, old-unresolved-entries, new-unresolved-entries, unresolved-entries
       2021-07-30
          Added evpn bridge ID and SHG ID to srv6-information-for-path bag
       2021-07-06
          Added global-main subtree and support show CLIs for FIB IPC infra
       2021-05-25
          Migrate NHINFO to TI infra";
    semver:module-version "4.0.0";
  }
  revision 2020-12-02 {
    description
      "Adding per-object accounting.
       2020-10-20
           NBC documentation of CSCvu06764, CSCvv14573,CSCvv76648
       2020-05-26
           Update SRv6 Block Space naming convention
       2020-05-05
           changes related to treat SRv6 and SID as well-known when parsing XML for yang";
    semver:module-version "3.0.0";
  }
  revision 2020-01-16 {
    description
      "NBC documentation of CSCvs27272,CSCvs22018,CSCvs45512
       2019-10-29
         Updated srv6 global bag";
    semver:module-version "2.0.0";
  }
  revision 2019-09-27 {
    description
      "IOS XR 7.0.x revision.";
    semver:module-version "1.1.0";
  }
  revision 2019-04-05 {
    description
      "Establish semantic version baseline.";
    semver:module-version "1.0.0";
  }
  revision 2019-04-02 {
    description
      "Fixed schema descriptions.";
  }
  revision 2017-09-07 {
    description
      "Fixed type translation error.";
  }
  revision 2017-05-01 {
    description
      "Fixing backward compatibility error in module.";
  }
  revision 2017-01-20 {
    description
      "IOS XR 6.2.1 revision";
  }
  revision 2015-11-09 {
    description
      "IOS XR 6.0 revision.";
  }

  typedef Oc-encapsulation-header {
    type enumeration {
      enum "oc-encap-type-gre" {
        value 0;
        description
          "oc encap type gre";
      }
      enum "oc-encap-type-ipv4" {
        value 1;
        description
          "oc encap type ipv4";
      }
      enum "oc-encap-type-ipv6" {
        value 2;
        description
          "oc encap type ipv6";
      }
      enum "oc-encap-type-mpls" {
        value 3;
        description
          "oc encap type mpls";
      }
      enum "oc-encap-type-vxlan" {
        value 4;
        description
          "oc encap type vxlan";
      }
    }
    description
      "Oc encapsulation header";
  }

  grouping FIB-OC-AFT-ERROR-STATE {
    description
      "FIB OC AFT ERROR STATE";
    leaf is-in-error-state {
      type boolean;
      description
        "Error State";
    }
  }

  grouping FIB-OC-AFT-OOR-STATE {
    description
      "FIB OC AFT OOR STATE";
    leaf is-in-oor-state {
      type boolean;
      description
        "OOR State";
    }
  }

  grouping FIB-OC-AFT-NEXTHOP-V2 {
    description
      "FIB OC AFT NEXTHOP V2";
    leaf pfx {
      type string;
      description
        "IP prefix or MPLS label";
    }
    leaf encap-type {
      type Oc-encapsulation-header;
      description
        "Encapsulation type";
    }
    leaf if-hdl {
      type xr:Interface-name;
      description
        "Interface handle";
    }
    leaf-list pushed-label-stack {
      type uint32;
      description
        "Pushed MPLS label stack";
    }
  }

  grouping FIB-OC-AFT-NH-GROUP-STATE-V2 {
    description
      "FIB OC AFT NH GROUP STATE V2";
    leaf bckup-grp-id {
      type uint64;
      description
        "Backup group ID";
    }
    leaf-list nhid {
      type uint64;
      description
        "List of next-hop IDs";
    }
    leaf-list wt-of-nh {
      type uint64;
      description
        "List of next-hop Weights";
    }
    leaf-list fwd-class {
      type uint8;
      description
        "List of active forward classes";
    }
  }

  grouping FIB-OC-AFT-COND-GRP-STATE-V2 {
    description
      "FIB OC AFT COND GRP STATE V2";
    leaf nhg-id {
      type uint64;
      description
        "Nexthop Group ID of subset of nh's for this fwd
         class";
    }
    leaf-list interface-name {
      type xr:Interface-name;
      description
        "Interface name";
    }
  }

  grouping FIB-OC-AFT-PRFX-STATE-V2 {
    description
      "FIB OC AFT PRFX STATE V2";
    leaf grp-id {
      type uint64;
      description
        "Next-hop Group ID";
    }
  }
}
