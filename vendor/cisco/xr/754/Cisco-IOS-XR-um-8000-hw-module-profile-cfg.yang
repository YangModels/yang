module Cisco-IOS-XR-um-8000-hw-module-profile-cfg {
  namespace "http://cisco.com/ns/yang/Cisco-IOS-XR-um-8000-hw-module-profile-cfg";
  prefix um-8000-hw-module-profile-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR 8000-hw-module-profile package configuration.
     
     This YANG module augments the
     modules with configuration data.
     
     Copyright (c) 2021-2023 by Cisco Systems, Inc.
     All rights reserved.";

  revision 2023-02-07 {
    description
      "Feature xoff mode added
       2022-12-06
         Added SROPT mode feature
       2022-09-28
         Modified lpm high node as lpm tcam-banks in  hw-module profile route scale lpm
       2022-09-08
         Added  high lpm scale
       2022-09-02
         Added leafs in hw-module profile cef
       2022-08-04
         Added buffer-extend support
       2022-06-06
         Removed location-name list key node
       2022-04-24
         Added npu-compatibility support
       2022-04-06
         Updated buffer-extended and buffer-internal nodes
       2022-03-22
         Added new leaf pause-threshold-bytes.Added must constraints to list traffic-class and leaf pause-threshold.
       2022-03-10
         Added missing nodes
       2021-12-20
         Added new router scale ipv6-unicast connected-prefix scale feature";
    semver:module-version "1.0.1M";
  }
  revision 2021-03-19 {
    description
      "Initial release";
    semver:module-version "1.0.0";
  }

  container hw-module {
    description
      "Configure h/w module";
    container profile {
      description
        "Configure profile.";
      container tcam {
        description
          "Configure profile for TCAM LC cards";
        container fib {
          description
            "Forwarding table to configure";
          container ipv4 {
            description
              "Configure ipv4 addresses in TCAM";
            container unicast {
              description
                "Unicast address";
              leaf percent {
                type uint32 {
                  range "1..100" {
                    description
                      "value in percent";
                  }
                }
                description
                  "percent to configure";
              }
            }
          }
          container ipv6 {
            description
              "Configure ipv6 addresses in TCAM";
            container unicast {
              description
                "Unicast address";
              leaf percent {
                type uint32 {
                  range "0..100" {
                    description
                      "value in percent";
                  }
                }
                description
                  "percent to configure";
              }
            }
          }
        }
        container format {
          description
            "format of the tcam entry";
          container access-list {
            description
              "Access List format";
            container ipv4 {
              presence "Indicates a ipv4 node is configured.";
              description
                "IPv4";
              container src-addr {
                presence "Indicates a src-addr node is configured.";
                description
                  "ipv4 source address";
              }
              container dst-addr {
                presence "Indicates a dst-addr node is configured.";
                description
                  "ipv4 destination address";
              }
              container src-port {
                presence "Indicates a src-port node is configured.";
                description
                  "source port for TCP/UDP";
              }
              container dst-port {
                presence "Indicates a dst-port node is configured.";
                description
                  "destination port for TCP/UDP";
              }
              container proto {
                presence "Indicates a proto node is configured.";
                description
                  "protocol field in IPV4 header";
              }
              container precedence {
                presence "Indicates a precedence node is configured.";
                description
                  "precedence/dscp field in IPV4 header";
              }
              container ttl-match {
                presence "Indicates a ttl-match node is configured.";
                description
                  "TTL in IPv4 header";
              }
              container tcp-flags {
                presence "Indicates a tcp-flags node is configured.";
                description
                  "tcp flags";
              }
              container frag-bit {
                presence "Indicates a frag-bit node is configured.";
                description
                  "fragment-bit";
              }
              container src-object-group {
                presence "Indicates a src-object-group node is configured.";
                description
                  "source object group";
              }
              container dst-object-group {
                presence "Indicates a dst-object-group node is configured.";
                description
                  "destination object group";
              }
              container packet-len {
                presence "Indicates a packet-len node is configured.";
                description
                  "packet length";
              }
              container fragment-offset {
                presence "Indicates a fragment-offset node is configured.";
                description
                  "fragment-offset";
              }
              leaf udf1 {
                type xr:Cisco-ios-xr-string {
                  length "1..800" {
                    description
                      "UDF name";
                  }
                }
                description
                  "user defined filter";
              }
              leaf udf2 {
                type xr:Cisco-ios-xr-string {
                  length "1..800" {
                    description
                      "UDF name";
                  }
                }
                description
                  "user defined filter";
              }
              leaf udf3 {
                type xr:Cisco-ios-xr-string {
                  length "1..800" {
                    description
                      "UDF name";
                  }
                }
                description
                  "user defined filter";
              }
              leaf udf4 {
                type xr:Cisco-ios-xr-string {
                  length "1..800" {
                    description
                      "UDF name";
                  }
                }
                description
                  "user defined filter";
              }
              leaf udf5 {
                type xr:Cisco-ios-xr-string {
                  length "1..800" {
                    description
                      "UDF name";
                  }
                }
                description
                  "user defined filter";
              }
              leaf udf6 {
                type xr:Cisco-ios-xr-string {
                  length "1..800" {
                    description
                      "UDF name";
                  }
                }
                description
                  "user defined filter";
              }
              leaf udf7 {
                type xr:Cisco-ios-xr-string {
                  length "1..800" {
                    description
                      "UDF name";
                  }
                }
                description
                  "user defined filter";
              }
              leaf udf8 {
                type xr:Cisco-ios-xr-string {
                  length "1..800" {
                    description
                      "UDF name";
                  }
                }
                description
                  "user defined filter";
              }
            }
            container ipv6 {
              presence "Indicates a ipv6 node is configured.";
              description
                "IPv6";
              container src-addr {
                presence "Indicates a src-addr node is configured.";
                description
                  "ipv6 source address";
              }
              container dst-addr {
                presence "Indicates a dst-addr node is configured.";
                description
                  "ipv6 destination address";
              }
              container src-port {
                presence "Indicates a src-port node is configured.";
                description
                  "source port for TCP/UDP (mandatory field)";
              }
              container dst-port {
                presence "Indicates a dst-port node is configured.";
                description
                  "destination port for TCP/UDP";
              }
              container next-hdr {
                presence "Indicates a next-hdr node is configured.";
                description
                  "next header field in IPV6 header (mandatory field)";
              }
              container traffic-class {
                presence "Indicates a traffic-class node is configured.";
                description
                  "traffic class in IPV6 header";
              }
              container frag-bit {
                presence "Indicates a frag-bit node is configured.";
                description
                  "fragment-bit";
              }
              container tcp-flags {
                presence "Indicates a tcp-flags node is configured.";
                description
                  "tcp flags";
              }
              container src-object-group {
                presence "Indicates a src-object-group node is configured.";
                description
                  "source object group";
              }
              container dst-object-group {
                presence "Indicates a dst-object-group node is configured.";
                description
                  "destination object group";
              }
              container packet-len {
                presence "Indicates a packet-len node is configured.";
                description
                  "packet length";
              }
              leaf udf1 {
                type xr:Cisco-ios-xr-string {
                  length "1..800" {
                    description
                      "UDF name";
                  }
                }
                description
                  "user defined filter";
              }
              leaf udf2 {
                type xr:Cisco-ios-xr-string {
                  length "1..800" {
                    description
                      "UDF name";
                  }
                }
                description
                  "user defined filter";
              }
              leaf udf3 {
                type xr:Cisco-ios-xr-string {
                  length "1..800" {
                    description
                      "UDF name";
                  }
                }
                description
                  "user defined filter";
              }
              leaf udf4 {
                type xr:Cisco-ios-xr-string {
                  length "1..800" {
                    description
                      "UDF name";
                  }
                }
                description
                  "user defined filter";
              }
              leaf udf5 {
                type xr:Cisco-ios-xr-string {
                  length "1..800" {
                    description
                      "UDF name";
                  }
                }
                description
                  "user defined filter";
              }
              leaf udf6 {
                type xr:Cisco-ios-xr-string {
                  length "1..800" {
                    description
                      "UDF name";
                  }
                }
                description
                  "user defined filter";
              }
              leaf udf7 {
                type xr:Cisco-ios-xr-string {
                  length "1..800" {
                    description
                      "UDF name";
                  }
                }
                description
                  "user defined filter";
              }
              leaf udf8 {
                type xr:Cisco-ios-xr-string {
                  length "1..800" {
                    description
                      "UDF name";
                  }
                }
                description
                  "user defined filter";
              }
            }
          }
        }
      }
      container qos {
        description
          "Configure qos profile";
        container voq-mode {
          description
            "voq mode to configure";
          container four {
            must
              "not(../eight or ../fair-four
               or ../fair-eight)";
            presence "Indicates a four node is configured.";
            description
              "4 VoQ Mode";
          }
          container eight {
            must
              "not(../four or ../fair-four
               or ../fair-eight)";
            presence "Indicates a eight node is configured.";
            description
              "8 VoQ Mode";
          }
          container fair-four {
            must
              "not(../four or ../eight
               or ../fair-eight)";
            presence "Indicates a fair-4 node is configured.";
            description
              "fair-4 VoQ Mode";
          }
          container fair-eight {
            must
              "not(../four or ../eight
               or ../fair-four)";
            presence "Indicates a fair-8 node is configured.";
            description
              "fair-8 VoQ Mode";
          }
        }
        leaf l2-mode {
          type enumeration {
            enum "L2" {
              value 2;
              description
                "Use L2 headers for QoS on L2 interfaces";
            }
            enum "L3" {
              value 3;
              description
                "Use L3 headers for QoS on L2 interfaces";
            }
          }
          description
            "Configure QOS mode for L2 interfaces";
        }
        container qos-stats-push-collection {
          must "../l2-mode";
          presence "Indicates a qos-stats-push-collection node is configured.";
          description
            "Enable QoS stats push collection";
        }
      }
      container cef {
        description
          "Configure cef profiles";
        leaf dark-bw {
          type enumeration {
            enum "enable" {
              value 1;
              description
                "Enable Dark bandwidth feature";
            }
          }
          description
            "Configure dark-bandwidth";
        }
        leaf sropt {
          type enumeration {
            enum "enable" {
              value 1;
              description
                "Enable SROPT feature";
            }
          }
          description
            "Configure SROPT functionality";
        }
        leaf bgplu {
          type enumeration {
            enum "enable" {
              value 1;
              description
                "Enable BGPLU feature";
            }
          }
          description
            "Configure bgplu attribute";
        }
        leaf cbf {
          type enumeration {
            enum "enable" {
              value 1;
              description
                "Enable CBF feature";
            }
          }
          description
            "Enable cbf";
        }
        container forward-class-lists {
          description
            "Configure hardware forward class list";
          leaf-list forward-class-list {
            type uint32 {
              range "0..7" {
                description
                  "forward class id";
              }
            }
            must "../../cbf";
            max-elements "8";
            description
              "Configure hardware forward class list";
          }
        }
        container ipv6 {
          description
            "IPv6";
          leaf hop-limit {
            type enumeration {
              enum "punt" {
                value 1;
                description
                  "Punt hop-limit 0 packets";
              }
            }
            description
              "Hop-limit 0 packets";
          }
        }
        container lpts {
          description
            "LPTS";
          container acl {
            presence "Indicates a acl node is configured.";
            description
              "Enable ACL";
          }
          leaf pifib-entry-counters {
            type uint32 {
              range "256..512" {
                description
                  "number of counters";
              }
            }
            description
              "Configure number of counters";
          }
        }
        container stats {
          description
            "Configure feature level stats";
          container label {
            description
              "Configure label stats";
            leaf app-default {
              type enumeration {
                enum "dynamic" {
                  value 1;
                  description
                    "Allocate counters till OOR";
                }
              }
              description
                "Applies to - LDP and SR";
            }
          }
        }
        container ttl {
          description
            "Configure ttl profile";
          container tunnel-ip {
            description
              "Configure tunnel-ip ttl mode";
            leaf decrement {
              type enumeration {
                enum "disable" {
                  value 1;
                  description
                    "Disable tunnl-ip inner ttl decrement";
                }
              }
              description
                "Configure tunnel-ip ttl decrement behaviour";
            }
          }
        }
        container te-tunnel {
          description
            "Configure te tunnel profile";
          container highscale-no-ldp-over-te {
            presence "Indicates a highscale-no-ldp-over-te node is configured.";
            description
              "Enable te tunnels high scale and disable ldp over te";
          }
          container highscale-ldp-over-te-no-sr-over-srte {
            presence "Indicates a highscale-ldp-over-te-no-sr-over-srte node is configured.";
            description
              "Enable high scale of TE tunnels with LDP over TE and disable SR over SRTE";
          }
          container label-over-te-counters {
            presence "Indicates a label-over-te-counters node is configured.";
            description
              "Enable label counters and disable TE counters";
          }
        }
        leaf ip-redirect {
          type enumeration {
            enum "enable" {
              value 1;
              description
                "Enable IP redirect";
            }
          }
          description
            "IP redirect";
        }
      }
      container stats {
        description
          "Configure qos stats profile";
        leaf voqs-sharing-counters {
          type enumeration {
            enum "1" {
              value 1;
              description
                "Counter for each queue";
            }
            enum "2" {
              value 2;
              description
                "2 Queues share counters";
            }
            enum "4" {
              value 4;
              description
                "4 Queues share counters";
            }
          }
          description
            "Configure number of voqs (1, 2, 4) sharing counters";
        }
        container acl-permit {
          presence "Indicates a acl-permit node is configured.";
          description
            "Configure ACL permit stats";
          container no-bvi-ingress {
            presence "Indicates a no-bvi-ingress node is configured.";
            description
              "Disable BVI ingress counter stats";
          }
        }
      }
      leaf bw-threshold {
        type xr:Cisco-ios-xr-string {
          length "1..800" {
            description
              "value in percent: 10-100 in increments of 10";
          }
          pattern "(100|[1-9]0)";
        }
        description
          "% of Total Fabric BW of Asic requires for INTF bring UP";
      }
      container priority-flow-control {
        description
          "Configure priority-flow-control parameters";
        container locations {
          description
            "Location to apply PFC configuration";
          list location {
            key "location-name";
            description
              "Location to apply PFC configuration";
            leaf location-name {
              type xr:Node-id;
              description
                "Location to apply PFC configuration";
            }
            container buffer-extended {
              description
                "Use Extended Packet Memory buffers";
              list traffic-class {
                must "pause-threshold or pause-threshold-bytes";
                key "traffic-class-id";
                description
                  "configure traffic-class";
                leaf traffic-class-id {
                  type uint32 {
                    range "0..7" {
                      description
                        "Traffic-class";
                    }
                  }
                  description
                    "configure traffic-class";
                }
                leaf pause-threshold {
                  type uint32 {
                    range "1..200000" {
                      description
                        "pause-threshold";
                    }
                  }
                  must "../ms or ../us";
                  must "not(../pause-threshold-bytes)";
                  description
                    "configure pause-threshold";
                }
                leaf pause-threshold-bytes {
                  type uint32 {
                    range "1..200000" {
                      description
                        "pause-threshold";
                    }
                  }
                  must "../kbytes or ../mbytes";
                  must "not(../pause-threshold)";
                  description
                    "configure pause-threshold";
                }
                container ms {
                  presence "Indicates a ms node is configured.";
                  description
                    "Milliseconds (2-25 ms)";
                  leaf headroom {
                    type uint32 {
                      range "0..200000" {
                        description
                          "headroom";
                      }
                    }
                    description
                      "configure headroom";
                  }
                }
                container us {
                  presence "Indicates a us node is configured.";
                  description
                    "Microseconds (2000-25000 us)";
                  leaf headroom {
                    type uint32 {
                      range "0..200000" {
                        description
                          "headroom";
                      }
                    }
                    description
                      "configure headroom";
                  }
                }
                container kbytes {
                  presence "Indicates a kbytes node is configured.";
                  description
                    "KBytes (1024-200000 kbytes)";
                  leaf headroom {
                    type uint32 {
                      range "1..200000" {
                        description
                          "headroom";
                      }
                    }
                    description
                      "configure headroom";
                  }
                }
                container mbytes {
                  presence "Indicates a mbytes node is configured.";
                  description
                    "MBytes (1-200 mbytes)";
                  leaf headroom {
                    type uint32 {
                      range "1..200000" {
                        description
                          "headroom";
                      }
                    }
                    description
                      "configure headroom";
                  }
                }
              }
              list traffic-class-default {
                key "traffic-class-id";
                description
                  "configure traffic-class";
                leaf traffic-class-id {
                  type uint32 {
                    range "0..7" {
                      description
                        "Traffic-class";
                    }
                  }
                  description
                    "configure traffic-class";
                }
              }
            }
            container buffer-internal {
              description
                "Use Internal Packet Memory buffers";
              list traffic-class {
                key "traffic-class-id";
                description
                  "configure traffic-class";
                leaf traffic-class-id {
                  type uint32 {
                    range "0..7" {
                      description
                        "Traffic-class";
                    }
                  }
                  description
                    "configure traffic-class";
                }
                leaf pause-threshold {
                  type uint32 {
                    range "307200..1574400" {
                      description
                        "pause-threshold (bytes)";
                    }
                  }
                  mandatory true;
                  description
                    "configure pause-threshold";
                }
                leaf headroom {
                  type uint32 {
                    range "345600..1651200" {
                      description
                        "headroom (bytes)";
                    }
                  }
                  mandatory true;
                  description
                    "configure headroom";
                }
                leaf ecn {
                  type uint32 {
                    range "153600..897408" {
                      description
                        "ecn (bytes)";
                    }
                  }
                  description
                    "configure ecn";
                }
                leaf max-threshold {
                  type uint32 {
                    range "153600..1495680" {
                      description
                        "ecn max threshold(bytes)";
                    }
                  }
                  description
                    "ecn max threshold";
                }
                leaf probability-percentage {
                  type uint32 {
                    range "1..100" {
                      description
                        "percentage";
                    }
                  }
                  description
                    "maximum probability percentage";
                }
              }
              list traffic-class-default {
                key "traffic-class-id";
                description
                  "configure traffic-class";
                leaf traffic-class-id {
                  type uint32 {
                    range "0..7" {
                      description
                        "Traffic-class";
                    }
                  }
                  description
                    "configure traffic-class";
                }
              }
            }
          }
        }
      }
      container gue {
        description
          "gue decap tunnel's udp destination port configuration";
        container udp-dest-port {
          description
            "configure separate udp port numbers for ipv4/ipv6/mpls";
          leaf ipv4 {
            type uint32 {
              range "1000..64000" {
                description
                  "value in decimal";
              }
            }
            must "../ipv6";
            description
              "Configure unreserved udp port number for ipv4 payload";
          }
          leaf ipv6 {
            type uint32 {
              range "1000..64000" {
                description
                  "value in decimal";
              }
            }
            must "../ipv4 and ../mpls";
            description
              "Configure unreserved udp port number for ipv6 payload";
          }
          leaf mpls {
            type uint32 {
              range "1000..64000" {
                description
                  "value in decimal";
              }
            }
            must "../ipv6";
            description
              "Configure unreserved udp port number for mpls payload";
          }
        }
      }
      container npu {
        description
          "Configure npu parameters";
        container buffer-extended {
          description
            "Configure buffer-extended parameters";
          container locations {
            description
              "Location to apply buffer-extended configuration";
            list location {
              key "location-name";
              description
                "Location to apply buffer-extended configuration";
              leaf location-name {
                type xr:Node-id;
                description
                  "Location to apply buffer-extended configuration";
              }
              container bandwidth-congestion-detection {
                description
                  "enable bandwidth congestion detection";
                container enable {
                  presence "Indicates a enable node is configured.";
                  description
                    "enable bandwidth congestion detection";
                }
              }
              container bandwidth-congestion-protect {
                description
                  "device global xoff enable";
                container enable {
                  presence "Indicates a enable node is configured.";
                  description
                    "device global xoff enable";
                }
              }
            }
          }
        }
      }
      container l2fib {
        description
          "Configure l2fib profiles";
        container pw-stats {
          presence "Indicates a pw-stats node is configured.";
          description
            "Configure PW stats";
        }
        container bridge-flush-convergence {
          presence "Indicates a bridge-flush-convergence node is configured.";
          description
            "Configure BD flush convergence mode";
        }
      }
      leaf npu-compatibility {
        type enumeration {
          enum "Q100" {
            value 1;
            description
              "Use Q100 for Chassis mode";
          }
          enum "Q200" {
            value 2;
            description
              "Use Q200 for Chassis mode";
          }
        }
        description
          "Configure npu-compatibility mode for chassis type";
      }
      container route {
        description
          "Configure route scale ipv6-unicast connected-prefix profile";
        container scale {
          description
            "Configure scale";
          container ipv6-unicast {
            description
              "ipv6-unicast";
            container connected-prefix {
              description
                "connected-prefix";
              container high {
                presence "Indicates profile ipv6-unicast connected-prefix high is configured";
                description
                  "Enable profile ipv6-unicast connected-prefix high";
              }
            }
          }
          container lpm {
            description
              "enable scale lpm profile";
            container tcam-banks {
              presence "Indicates profile lpm  tcam-banks is configured";
              description
                "Enable high scale for LPM using TCAM banks";
            }
          }
        }
      }
    }
  }
}
