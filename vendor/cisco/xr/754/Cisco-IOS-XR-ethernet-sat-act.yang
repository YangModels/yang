module Cisco-IOS-XR-ethernet-sat-act {
  namespace "http://cisco.com/ns/yang/Cisco-IOS-XR-ethernet-sat-act";
  prefix ethernet-sat-act;

  import Cisco-IOS-XR-types {
    prefix xr;
  }
  import Cisco-IOS-XR-ethernet-sat-datatypes {
    prefix dt1;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ethernet service activation test actions.
     
     Copyright (c) 2013-2018, 2021 by Cisco Systems, Inc.
     All rights reserved.";

  revision 2021-04-23 {
    description
      "Add the import semver module";
    semver:module-version "1.1.0";
  }
  revision 2018-07-10 {
    description
      "IOS XR 7.1.1 revision.";
  }

  typedef sat-mac-address-type {
    type string {
      pattern "[0-9a-fA-F]{4}(\\.[0-9a-fA-F]{4}){2}";
    }
    description
      "MAC address";
  }

  rpc service-activation-test-start {
    description
      "Start a SAT on the specified interface";
    input {
      leaf interface {
        type xr:Interface-name;
        mandatory true;
        description
          "Interface name";
      }
      leaf profile {
        type xr:Cisco-ios-xr-string {
          length "1..63";
        }
        mandatory true;
        description
          "Profile name";
      }
      leaf destination {
        type sat-mac-address-type;
        mandatory true;
        description
          "Destination MAC address";
      }
      leaf direction {
        type dt1:Sat-direction;
        mandatory true;
        description
          "Test direction";
      }
    }
    xr:xr-task "ethernet-services";
    xr:cli-command "ethernet service-activation-test start interface <interface> profile <profile> destination <destination> direction <direction>";
  }
  rpc service-activation-test-stop {
    description
      "Stop running SAT on the specified interface";
    input {
      leaf interface {
        type xr:Interface-name;
        mandatory true;
        description
          "Interface name";
      }
    }
    xr:xr-task "ethernet-services";
    xr:cli-command "ethernet service-activation-test stop interface <interface>";
  }
  rpc service-activation-test-stop-all {
    description
      "Stop running SAT on all interfaces";
    xr:xr-task "ethernet-services";
    xr:cli-command "ethernet service-activation-test stop all";
  }
  rpc service-activation-test-clear {
    description
      "Clear stored SAT results on the specified interface";
    input {
      leaf interface {
        type xr:Interface-name;
        mandatory true;
        description
          "Interface name";
      }
    }
    xr:xr-task "ethernet-services";
    xr:cli-command "clear ethernet service-activation-test results interface <interface>";
  }
  rpc service-activation-test-clear-all {
    description
      "Clear stored SAT results on all interfaces";
    xr:xr-task "ethernet-services";
    xr:cli-command "clear ethernet service-activation-test results all";
  }
}
