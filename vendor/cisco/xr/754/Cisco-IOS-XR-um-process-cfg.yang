module Cisco-IOS-XR-um-process-cfg {
  namespace "http://cisco.com/ns/yang/Cisco-IOS-XR-um-process-cfg";
  prefix um-process-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR process package configuration.
     
     This YANG module augments the
     modules with configuration data.
     
     Copyright (c) 2021 by Cisco Systems, Inc.
     All rights reserved.";

  revision 2021-03-31 {
    description
      "Initial release";
    semver:module-version "1.0.0";
  }

  feature classic-admin-config {
    description
      "Classic admin configuration supported";
  }

  feature isolation {
    description
      "Isolation configuration supported";
  }

  container admin {
    if-feature "classic-admin-config";
    description
      "Admin configuration";
    container process {
      description
        "Admin process config commands";
      container mandatory {
        description
          "Set the process mandatory";
        container locations {
          description
            "Location on which this config applies";
          container all {
            description
              "All locations";
            list executable {
              key "executable-name";
              description
                "Name of the executable";
              leaf executable-name {
                type xr:Cisco-ios-xr-string {
                  length "1..800" {
                    description
                      "Name of the executable";
                  }
                }
                description
                  "Name of the executable";
              }
            }
          }
          list location {
            must "executable";
            key "location-name";
            description
              "location specification";
            leaf location-name {
              type xr:Node-id;
              description
                "Fully qualified location specification";
            }
            list executable {
              key "executable-name";
              description
                "Name of the executable";
              leaf executable-name {
                type xr:Cisco-ios-xr-string {
                  length "1..800" {
                    description
                      "Name of the executable";
                  }
                }
                description
                  "Name of the executable";
              }
            }
          }
        }
      }
      container single-crash {
        description
          "Reboot condition for single mandatory process that crashes";
        leaf min-uptime {
          type uint32 {
            range "1..4294967295" {
              description
                "Up time in seconds";
            }
          }
          must "../process";
          description
            "Minimum process up time to reset crash count";
        }
        leaf process {
          type uint32 {
            range "1..500" {
              description
                "Number of crashes for a process to trigger reboot";
            }
          }
          must "../min-uptime";
          description
            "Number of crashes for a process to trigger reboot";
        }
      }
      container multiple-crash {
        presence "Indicates a multiple-crash node is configured.";
        description
          "Reboot condition for multiple mandatory processes that crash";
        leaf number-of-crashes {
          type uint32 {
            range "1..500" {
              description
                "Number of combined process crashes to trigger reboot";
            }
          }
          mandatory true;
          description
            "Reboot condition for multiple mandatory processes that crash";
        }
        leaf time-interval {
          type uint32 {
            range "1..4294967295" {
              description
                "Time interval in seconds";
            }
          }
          mandatory true;
          description
            "Time interval in seconds";
        }
      }
    }
  }
  container process {
    description
      "Process config commands";
    container mandatory {
      description
        "Set the process mandatory";
      container locations {
        description
          "Location on which this config applies";
        container all {
          description
            "All locations";
          list executable {
            key "executable-name";
            description
              "Name of the executable";
            leaf executable-name {
              type xr:Cisco-ios-xr-string {
                length "1..800" {
                  description
                    "Name of the executable";
                }
              }
              description
                "Name of the executable";
            }
          }
        }
        list location {
          must "executable";
          key "location-name";
          description
            "location specification";
          leaf location-name {
            type xr:Node-id;
            description
              "Fully qualified location specification";
          }
          list executable {
            key "executable-name";
            description
              "Name of the executable";
            leaf executable-name {
              type xr:Cisco-ios-xr-string {
                length "1..800" {
                  description
                    "Name of the executable";
                }
              }
              description
                "Name of the executable";
            }
          }
        }
      }
    }
    container single-crash {
      description
        "Reboot condition for single mandatory process that crashes";
      leaf process {
        type uint32 {
          range "1..500" {
            description
              "Number of crashes for a process to trigger reboot";
          }
        }
        must "../min-uptime";
        description
          "Number of crashes for a process to trigger reboot";
      }
      leaf min-uptime {
        type uint32 {
          range "1..4294967295" {
            description
              "Up time in seconds";
          }
        }
        must "../process";
        description
          "Minimum process up time to reset crash count";
      }
    }
    container multiple-crash {
      presence "Indicates a multiple-crash node is configured.";
      description
        "Reboot condition for multiple mandatory processes that crash";
      leaf number-of-crashes {
        type uint32 {
          range "1..500" {
            description
              "Number of combined process crashes to trigger reboot";
          }
        }
        mandatory true;
        description
          "Reboot condition for multiple mandatory processes that crash";
      }
      leaf time-interval {
        type uint32 {
          range "1..4294967295" {
            description
              "Time interval in seconds";
          }
        }
        mandatory true;
        description
          "Time interval in seconds";
      }
    }
  }
  container isolation {
    if-feature "isolation";
    description
      "Configure Isolation";
    container enable {
      presence "Indicates a enable node is configured.";
      description
        "Enable isolation for RP/DRP nodes";
    }
    container multiple {
      presence "Indicates a multiple node is configured.";
      description
        "Allow the rp isolation feature to handle multiple requests";
    }
  }
}
