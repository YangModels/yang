submodule Cisco-IOS-XR-interface-cem-oper-sub2 {
  belongs-to Cisco-IOS-XR-interface-cem-oper {
    prefix Cisco-IOS-XR-interface-cem-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR interface-cem package operational data.
     
     Copyright (c) 2013-2022 by Cisco Systems, Inc.
     All rights reserved.";

  revision 2022-03-24 {
    description
      "Increase in interface name length";
    semver:module-version "2.0.0";
  }
  revision 2021-08-18 {
    description
      "Configured, operational, in-use fields for dejitter and configured, operational fields for payload are added.
       2021-07-20
          CEM interface payload-dejitter-mapping and capabilities command added.
       2021-06-06
          CEM interface oper command added.";
    semver:module-version "2.0.0";
  }
  revision 2019-04-05 {
    description
      "Establish semantic version baseline.";
    semver:module-version "1.0.0";
  }
  revision 2015-11-09 {
    description
      "IOS XR 6.0 revision.";
  }

  typedef Cem-recovered-clock-status {
    type enumeration {
      enum "null" {
        value 0;
        description
          "Null";
      }
      enum "free-run" {
        value 1;
        description
          "Free run";
      }
      enum "holdover" {
        value 2;
        description
          "Holdover";
      }
      enum "acquiring" {
        value 3;
        description
          "Acquiring";
      }
      enum "acquired" {
        value 4;
        description
          "Acquired";
      }
      enum "disabled" {
        value 5;
        description
          "Disabled";
      }
    }
    description
      "CEM recovered clock status";
  }

  typedef Cem-recovered-clock {
    type enumeration {
      enum "none" {
        value 0;
        description
          "None";
      }
      enum "adaptive" {
        value 1;
        description
          "Adaptive";
      }
      enum "differential" {
        value 2;
        description
          "Differential";
      }
    }
    description
      "CEM recovered clock types";
  }

  grouping CEM-RECOVERED-CLOCK-DATA {
    description
      "CEM recovered clock data";
    leaf interface-name {
      type string;
      description
        "Interface name";
    }
    leaf clock-type {
      type Cem-recovered-clock;
      description
        "Clock Type";
    }
    leaf clock-status {
      type Cem-recovered-clock-status;
      description
        "Clock status";
    }
    leaf frequency-offset {
      type int32;
      description
        "Frequency offset";
    }
  }
}
