module Cisco-IOS-XR-tunnel-nve-cfg {
  namespace "http://cisco.com/ns/yang/Cisco-IOS-XR-tunnel-nve-cfg";
  prefix tunnel-nve-cfg;

  import ietf-inet-types {
    prefix inet;
  }
  import ietf-yang-types {
    prefix yang;
  }
  import cisco-semver {
    prefix semver;
  }
  import Cisco-IOS-XR-ifmgr-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR tunnel-nve package configuration.
     
     This module contains definitions
     for the following management objects:
       nve-global: Global NVE configuration data
     
     This YANG module augments the
       Cisco-IOS-XR-ifmgr-cfg
     module with configuration data.
     
     Copyright (c) 2013-2022 by Cisco Systems, Inc.
     All rights reserved.";

  revision 2022-04-23 {
    description
      "Added static inner mac cli
       2022-02-23
         Added member-vni policer-rate configuration.
       2022-02-17
         Remove static mac address field under vni.
       2022-02-09
         Decap prefix list of object groups added.
       2022-01-31
         Added new command dest-udp-port
       2021-10-28
         Added new sub command for global nve
       2021-10-12
         Added new container in hierarchy for schema to hold the static mac address
       2021-08-13
         New encap";
    semver:module-version "1.0.2m";
  }
  revision 2019-04-05 {
    description
      "Establish semantic version baseline.";
    semver:module-version "1.0.1";
  }
  revision 2016-08-30 {
    description
      "Initial Revision.";
  }
  revision 2015-11-09 {
    description
      "IOS XR 6.0 revision.";
  }

  typedef Host-reach-protocol {
    type enumeration {
      enum "bgp" {
        value 1;
        description
          "Use BGP EVPN for VxLAN tunnel endpoint
           reachability";
      }
    }
    description
      "Host reach protocol";
  }

  typedef Vni-range {
    type uint32 {
      range "1..16777215";
    }
    description
      "Vni range";
  }

  typedef Vxlan-udp-port-enum {
    type enumeration {
      enum "ietf-udp-port" {
        value 4789;
        description
          "IETF defined UDP port for VxLAN";
      }
      enum "ivx-lan-udp-port" {
        value 48879;
        description
          "UDP port for iVxLAN";
      }
    }
    description
      "Vxlan udp port enum";
  }

  typedef Overlay-encap-enum {
    type enumeration {
      enum "vx-lan-encapsulation" {
        value 0;
        description
          "VxLAN Encapsulation";
      }
      enum "soft-gre-encapsulation" {
        value 1;
        description
          "Soft GRE Encapsulation";
      }
      enum "mplsudp-encapsulation" {
        value 2;
        description
          "MPLS UDP Encapsulation";
      }
    }
    description
      "Overlay encap enum";
  }

  typedef Unknown-unicast-flooding-enum {
    type enumeration {
      enum "suppress-uuf" {
        value 1;
        description
          "Suppress unknown unicast flooding";
      }
    }
    description
      "Unknown unicast flooding enum";
  }

  typedef Load-balance-enum {
    type enumeration {
      enum "per-evi" {
        value 1;
        description
          "Per evi load balance mode";
      }
    }
    description
      "Load balance enum";
  }

  typedef Policer-rate-range {
    type uint32 {
      range "4294967295";
    }
    description
      "Policer rate range";
  }

  typedef Ir-protocol-enum {
    type enumeration {
      enum "bgp" {
        value 1;
        description
          "Use BGP Protocol for Ingress-Replication";
      }
    }
    description
      "Ir protocol enum";
  }

  typedef Policer-rate-unit-enum {
    type enumeration {
      enum "rate-unit-none" {
        value 0;
        description
          "Rate Unit None";
      }
      enum "rate-unit-bps" {
        value 1;
        description
          "Rate Unit BPS";
      }
      enum "rate-unit-kbps" {
        value 2;
        description
          "Rate Unit KBPS";
      }
      enum "rate-unit-mbps" {
        value 3;
        description
          "Rate Unit MBPS";
      }
    }
    description
      "Policer rate unit enum";
  }

  augment "/a1:interface-configurations/a1:interface-configuration" {
    description
      "This augment extends the configuration data of
       'Cisco-IOS-XR-ifmgr-cfg'";
    container nve {
      description
        "NVE operational data";
      container anycast {
        description
          "Enable anycast mode for this NVE interface";
        leaf source-interface {
          type string;
          description
            "Name of the Anycast mode source interface";
        }
        leaf sync-group {
          type inet:ipv4-address-no-zone;
          description
            "MCast group for syncing between Anycast
             gateways";
        }
      }
      container redundancy {
        description
          "Redundancy configuration for this NVE";
        container backbone-vx-lan {
          description
            "VXLAN backbone";
          leaf enable {
            type empty;
            description
              "Enable Backbone VxLAN";
          }
          leaf backbone-vx-laniccp {
            type uint32;
            description
              "VxLAN backbone ICCP group";
          }
        }
        container backbone-mpls {
          description
            "MPLS backbone";
          leaf backbone-mplsiccp {
            type uint32;
            description
              "MPLS backbone ICCP group";
          }
          leaf enable {
            type empty;
            description
              "Enable Backbone MPLS";
          }
        }
        leaf enable {
          type empty;
          description
            "Enable Redundancy";
        }
      }
      container member-vnis {
        description
          "VNI configuration Table for this NVE";
        list member-vni {
          key "vni-start vni-end";
          description
            "VNI member attributes";
          container policer-rate {
            description
              "Policer Rate";
            leaf policer-rate {
              type Policer-rate-range;
              description
                "Policer rate";
            }
            leaf policer-rate-unit {
              type Policer-rate-unit-enum;
              description
                "Policer rate unit";
            }
          }
          container multicast {
            presence "enable multicast";
            description
              "Mulitcast core group range associated with
               the VxLAN segment(s)";
            leaf multicast-group-min {
              type inet:ipv4-address-no-zone;
              description
                "IPV4 group address of the tunnel source";
            }
            leaf multicast-group-max {
              type inet:ipv4-address-no-zone;
              description
                "IPV4 group address MAX";
            }
          }
          container static-inner-ether {
            presence "Indicates a static-inner-ether node is configured.";
            description
              "Static Inner Ethernet Configuration";
            leaf source-mac-address {
              type yang:mac-address;
              mandatory true;
              description
                "Configure Source MAC Address";
            }
            leaf enable {
              type empty;
              description
                "Enable Static Inner Ethernet";
            }
          }
          leaf host-reachability {
            type Host-reach-protocol;
            description
              "Control protocol for VxLAN tunnel endpoint
               reachability";
          }
          leaf vrf {
            type string;
            description
              "VRF associated with the VxLAN segment";
          }
          leaf unknown-unicast-flooding {
            type Unknown-unicast-flooding-enum;
            description
              "Suppression of unknown unicast flooding";
          }
          leaf load-balance-per-evi {
            type Load-balance-enum;
            description
              "Per-evi load balance mode";
          }
          leaf enable {
            type empty;
            description
              "Enable VNI";
          }
          leaf vni-start {
            type Vni-range;
            description
              "Single VNI or Range Start";
          }
          leaf vni-end {
            type Vni-range;
            description
              "Range End";
          }
        }
      }
      leaf vx-lan-udp-port {
        type Vxlan-udp-port-enum;
        default "ietf-udp-port";
        description
          "UDP port number in VxLAN encapsulation";
      }
      leaf overlay-encapsulation {
        type Overlay-encap-enum;
        default "vx-lan-encapsulation";
        description
          "The Overlay Encapsulation for this NVE";
      }
      leaf dest-udp-port {
        type uint32;
        default "111111";
        description
          "Dest UDP Port number";
      }
      leaf source-interface {
        type string;
        description
          "Source Interface for this NVE";
      }
      leaf ingress-replication-protocol {
        type Ir-protocol-enum;
        description
          "The Ingress Replication Protocol for this NVE";
      }
    }
  }
  container nve-global {
    description
      "Global NVE configuration data";
    leaf vni-scope-local {
      type empty;
      description
        "Enable Local VNI Scope";
    }
  }
}
