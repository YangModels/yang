module cisco-xr-ietf-yang-library-deviations {

  /*** NAMESPACE / PREFIX DEFINITION ***/

  namespace "http://cisco.com/ns/yang/cisco-xr-ietf-yang-library-deviations";

  prefix "cisco-xr-ietf-yanglib-devs";

  /*** LINKAGE (IMPORTS / INCLUDES) ***/
  import ietf-yang-library { prefix yanglib; }

  /*** META INFORMATION ***/
  organization "Cisco Systems, Inc.";

  contact
    "Cisco Systems, Inc.
     Customer Service

     Postal: 170 West Tasman Drive
     San Jose, CA 95134

     Tel: +1 800 553-NETS

     E-mail: cs-yang@cisco.com";

  description 
    "This module contains a set of deviations of IETF YANG Library data
     model set for Cisco IOS-XR.

     Copyright (c) 2019 by Cisco Systems, Inc.
     All rights reserved.";

  revision "2019-10-21" {
    description
      "Initial revision applicable to IOS-XR 7.2.1 and older releases";
  }

  deviation /yanglib:modules-state {
    deviate not-supported;
  }

  deviation /yanglib:yang-library-update {
    deviate not-supported;
  }

  deviation /yanglib:yang-library-change {
    deviate not-supported;
  }
}
