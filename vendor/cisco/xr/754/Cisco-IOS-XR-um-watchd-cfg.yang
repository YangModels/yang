module Cisco-IOS-XR-um-watchd-cfg {
  namespace "http://cisco.com/ns/yang/Cisco-IOS-XR-um-watchd-cfg";
  prefix um-watchd-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR watchd package configuration.
     
     This YANG module augments the
     modules with configuration data.
     
     Copyright (c) 2020-2021 by Cisco Systems, Inc.
     All rights reserved.";

  revision 2021-06-15 {
    description
      "Initial release";
    semver:module-version "1.0.0";
  }

  container watchd {
    description
      "Watchdog configuration commands";
    leaf timeout {
      type uint32 {
        range "1..10" {
          description
            "Length of timeout in seconds";
        }
      }
      description
        "Timeout";
    }
  }
}
