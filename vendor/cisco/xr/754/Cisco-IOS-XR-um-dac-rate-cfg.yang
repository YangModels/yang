module Cisco-IOS-XR-um-dac-rate-cfg {
  namespace "http://cisco.com/ns/yang/Cisco-IOS-XR-um-dac-rate-cfg";
  prefix um-dac-rate-cfg;

  import Cisco-IOS-XR-um-interface-cfg {
    prefix a1;
  }
  import tailf-common {
    prefix tailf;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR dac-rate package configuration.
     
     This YANG module augments the
     modules with configuration data.
     
     Copyright (c) 2020 by Cisco Systems, Inc.
     All rights reserved.";

  revision 2020-08-31 {
    description
      "Initial release";
    semver:module-version "1.0.0";
  }

  feature optics {
    description
      "optics";
  }

  grouping CONT-BODY {
    leaf dac-rate {
      when "../a1:controller-name[starts-with(text(),'Optics')]" {
        tailf:dependency "../a1:controller-name";
      }
      if-feature "optics";
      type enumeration {
        enum "1x1" {
          value 0;
          description
            "Select 1:1 sampling rate(Sampling off)";
        }
        enum "1x1.25" {
          value 1;
          description
            "Select 1:1.25 sampling rate";
        }
        enum "1x1.50" {
          value 2;
          description
            "Select 1:1.50 sampling rate";
        }
        enum "1x1.75" {
          value 3;
          description
            "Select 1:1.75 sampling rate";
        }
        enum "1x2" {
          value 4;
          description
            "Select 1:2 sampling rate";
        }
      }
      description
        "Configure Sampling rate";
    }
  }

  augment "/a1:interfaces/a1:controller" {
    uses CONT-BODY;
  }
  augment "/a1:interfaces/a1:controller-preconfigure" {
    uses CONT-BODY;
  }
}
