module Cisco-IOS-XR-syslog-act {

    namespace "http://cisco.com/ns/yang/Cisco-IOS-XR-syslog-act";
    
    prefix "syslog-act";
    
    import ietf-syslog-types { prefix "log"; }
    
    organization "Cisco Systems, Inc.";
    
    contact
        "Cisco Systems, Inc.
     Customer Service

     Postal: 170 West Tasman Drive
     San Jose, CA 95134

     Tel: +1 800 553-NETS

     E-mail: cs-yang@cisco.com";
    
    description 
        "This module contains a collection of YANG definitions
     for Cisco IOS-XR action package configuration.

     This module contains definitions
     for the following management objects:
       syslog: Global Syslog messaging data

     Copyright (c) 2016 by Cisco Systems, Inc.
     All rights reserved.";
    
    revision "2016-04-17" {
        description
            "IOS XR 6.1.1 revision.";
    }
    
    rpc logmsg {
        input {
            leaf severity {
                type log:severity;
                description "Set serverity level";
                mandatory true;
            }
            leaf message {
                type string;
                description "Message body.";
                mandatory true;
            }
        }
    }
}
