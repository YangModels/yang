module cisco-xr-openconfig-interfaces-deviations {

  prefix  "ocifdevs";

  namespace "http://cisco.com/ns/yang/cisco-xr-openconfig-interfaces-deviations";

  import openconfig-interfaces { prefix ocif; }

  organization "Cisco Systems, Inc.";

  contact
    "Cisco Systems, Inc.
     Customer Service

     Postal: 170 West Tasman Drive
     San Jose, CA 95134

     Tel: +1 800 553-NETS

     E-mail: cs-yang@cisco.com";

  description
    "This module contains a set of deviations for 
 
     openconfig-interfaces.yang@2015-11-20 

     on Cisco IOS-XR devices.

     Copyright (c) 2016-2017 by Cisco Systems, Inc.
     All rights reserved.";

  revision "2016-05-16" {
    description
      "Initial revision applicable to IOS-XR 6.1.1";
  }


  deviation /ocif:interfaces/ocif:interface/ocif:config/ocif:enabled {
    deviate delete {
        default true;
    }
  }
  
  deviation /ocif:interfaces/ocif:interface/ocif:state/ocif:enabled {
    deviate delete {
        default true;
    }
  }
  
  deviation /ocif:interfaces/ocif:interface/ocif:subinterfaces/ocif:subinterface/ocif:config/ocif:unnumbered {
    deviate not-supported;
  }

  deviation /ocif:interfaces/ocif:interface/ocif:subinterfaces/ocif:subinterface/ocif:state/ocif:unnumbered {
    deviate not-supported;
  }


}
//total deviations:4
