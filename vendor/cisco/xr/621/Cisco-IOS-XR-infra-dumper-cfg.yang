module Cisco-IOS-XR-infra-dumper-cfg {

  /*** NAMESPACE / PREFIX DEFINITION ***/

  namespace "http://cisco.com/ns/yang/Cisco-IOS-XR-infra-dumper-cfg";


  prefix "infra-dumper-cfg";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR infra-dumper package configuration.

     This module contains definitions
     for the following management objects:
       exception: Core dump configuration commands

     Copyright (c) 2013-2016 by Cisco Systems, Inc.
     All rights reserved.";

  revision "2015-11-09" {
    description
      "IOS XR 6.0 revision.";
  }


  container exception {
    description "Core dump configuration commands";

    container choice1 {
      presence "enable choice1";
      description "Preference of the dump location";
      leaf compress {
        type boolean;
        must "../file-path";
        description
          "Specify 'true' to compress core files dumped on
          this path, 'false' to not compress";
      }
      leaf lower-limit {
        type uint32 {
          range "0..4";
        }
        must "../compress and ../file-path and ../filename and ../higher-limit";
        description
          "Lower limit.  This is required if Filename is
          specified.";
      }
      leaf higher-limit {
        type uint32 {
          range "5..64";
        }
        must "../compress and ../file-path and ../filename and ../lower-limit";
        description
          "Higher limit.  This is required if Filename is
          specified.";
      }
      leaf file-path {
        type string;
        must "../compress";
        description "Protocol and directory";
      }
      leaf filename {
        type string;
        must "../compress and ../file-path and ../lower-limit and ../higher-limit";
        description "Dump filename";
      }
    }

    container choice3 {
      presence "enable choice3";
      description "Preference of the dump location";
      leaf compress {
        type boolean;
        must "../file-path";
        description
          "Specify 'true' to compress core files dumped on
          this path, 'false' to not compress";
      }
      leaf lower-limit {
        type uint32 {
          range "0..4";
        }
        must "../compress and ../file-path and ../filename and ../higher-limit";
        description
          "Lower limit.  This is required if Filename is
          specified.";
      }
      leaf higher-limit {
        type uint32 {
          range "5..64";
        }
        must "../compress and ../file-path and ../filename and ../lower-limit";
        description
          "Higher limit.  This is required if Filename is
          specified.";
      }
      leaf file-path {
        type string;
        must "../compress";
        description "Protocol and directory";
      }
      leaf filename {
        type string;
        must "../compress and ../file-path and ../lower-limit and ../higher-limit";
        description "Dump filename";
      }
    }

    container choice2 {
      presence "enable choice2";
      description "Preference of the dump location";
      leaf compress {
        type boolean;
        must "../file-path";
        description
          "Specify 'true' to compress core files dumped on
          this path, 'false' to not compress";
      }
      leaf lower-limit {
        type uint32 {
          range "0..4";
        }
        must "../compress and ../file-path and ../filename and ../higher-limit";
        description
          "Lower limit.  This is required if Filename is
          specified.";
      }
      leaf higher-limit {
        type uint32 {
          range "5..64";
        }
        must "../compress and ../file-path and ../filename and ../lower-limit";
        description
          "Higher limit.  This is required if Filename is
          specified.";
      }
      leaf file-path {
        type string;
        must "../compress";
        description "Protocol and directory";
      }
      leaf filename {
        type string;
        must "../compress and ../file-path and ../lower-limit and ../higher-limit";
        description "Dump filename";
      }
    }
    leaf sparse {
      type boolean;
      description
        "Specify 'true' to enable sparse core dump,
        'false' to disable sparse core dump";
    }
    leaf kernel-debugger {
      type empty;
      description "Enable kernel debugger";
    }
    leaf packet-memory {
      type boolean;
      description
        "Specify 'true' to dump packet memory for all
        process, 'false' to disable dump of packet
        memory";
    }
    leaf sparse-size {
      type uint32 {
        range "1..4095";
      }
      description "Switch to sparse core dump at this size";
    }
  }
}
