submodule Cisco-IOS-XR-fretta-bcm-dpa-drop-stats-oper-sub1 {

  belongs-to Cisco-IOS-XR-fretta-bcm-dpa-drop-stats-oper {
    prefix Cisco-IOS-XR-fretta-bcm-dpa-drop-stats-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR fretta-bcm-dpa-drop-stats package operational data.

     Copyright (c) 2013-2016 by Cisco Systems, Inc.
     All rights reserved.";

  revision "2015-11-09" {
    description
      "IOS XR 6.0 revision.";
  }


  grouping DROP-STATS {
    description "DROP STATS";
    leaf id {
      type uint32;
      description "id";
    }
    leaf name {
      type string;
      description "name";
    }
    leaf count {
      type uint64;
      description "count";
    }
  }
}
