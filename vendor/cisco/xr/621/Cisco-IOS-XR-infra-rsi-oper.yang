module Cisco-IOS-XR-infra-rsi-oper {

  /*** NAMESPACE / PREFIX DEFINITION ***/

  namespace "http://cisco.com/ns/yang/Cisco-IOS-XR-infra-rsi-oper";


  prefix "infra-rsi-oper";

  /*** LINKAGE (IMPORTS / INCLUDES) ***/

  import Cisco-IOS-XR-types { prefix "xr"; }

  include Cisco-IOS-XR-infra-rsi-oper-sub2 {
    revision-date 2015-01-07;
  }

  include Cisco-IOS-XR-infra-rsi-oper-sub1 {
    revision-date 2015-01-07;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR infra-rsi package operational data.

     This module contains definitions
     for the following management objects:
       vrf-group: VRF group operational data
       srlg: srlg
       selective-vrf-download: selective vrf download

     Copyright (c) 2013-2016 by Cisco Systems, Inc.
     All rights reserved.";

  revision "2015-01-07" {
    description
      "IOS XR 5.3.1 revision.";
  }


  container vrf-group {
    config false;
    description "VRF group operational data";

    container nodes {
      description "Node operational data";

      list node {
        key "node-name";
        description "Node details";

        container groups {
          description "Group operational data";

          list group {
            key "group-name";
            description "Group details";
            leaf group-name {
              type xr:Cisco-ios-xr-string {
                length "1..32";
              }
              description "Group name";
            }
            uses RSI-VRFGROUP-GROUP-SHOW;
          }
        }
        leaf node-name {
          type xr:Node-id;
          description "Node";
        }
      }
    }
  }

  container srlg {
    config false;
    description "srlg";

    container srlg-maps {
      description "Set of SRLG name, value maps configured";

      list srlg-map {
        key "srlg-name";
        description "Configured SRLG name details ";
        leaf srlg-name {
          type xr:Cisco-ios-xr-string {
            length "1..64";
          }
          description "SRLG name";
        }
        uses RSI-SRLG-NAME-VALUE-SHOW;
      }
    }

    container nodes {
      description "RSI SRLG operational data";

      list node {
        key "node-name";
        description "RSI SRLG operational data";

        container srlg-maps {
          description "Set of SRLG name, value maps configured";

          list srlg-map {
            key "srlg-name";
            description "Configured SRLG name details ";
            leaf srlg-name {
              type xr:Cisco-ios-xr-string {
                length "1..64";
              }
              description "SRLG name";
            }
            uses RSI-SRLG-NAME-VALUE-SHOW;
          }
        }

        container groups {
          description "Set of Groups configured for SRLG";

          list group {
            key "group-name";
            description "SRLG group details";
            leaf group-name {
              type xr:Cisco-ios-xr-string;
              description "Group name";
            }
            uses RSI-SRLG-GROUP-SHOW;
          }
        }

        container inherit-nodes {
          description
            "Set of inherit locations configured for SRLG";

          list inherit-node {
            key "inherit-node-name";
            description "SRLG inherit location details";
            leaf inherit-node-name {
              type xr:Pq-node-id;
              description "Inherit node";
            }
            uses RSI-SRLG-INHLOC-SHOW;
          }
        }

        container interfaces {
          description "Set of interfaces configured for SRLG";

          list interface {
            key "interface-name";
            description "SRLG interface summary";
            leaf interface-name {
              type xr:Interface-name;
              description "Interface name";
            }
            uses RSI-SRLG-INTF-BRIEF-SHOW;
          }
        }

        container interface-details {
          description "Set of interfaces configured for SRLG";

          list interface-detail {
            key "interface-name";
            description "SRLG interface details";
            leaf interface-name {
              type xr:Interface-name;
              description "Interface name";
            }
            uses RSI-SRLG-INTF-DETAIL-SHOW;
          }
        }

        container srlg-values {
          description "Set of SRLG values configured";

          list srlg-value {
            key "value";
            description "Configured SRLG value details ";
            leaf value {
              type int32;
              description "SRLG value";
            }
            uses RSI-SRLG-INTF-SHOW;
          }
        }

        container interface-srlg-names {
          description "Set of SRLG names configured";

          list interface-srlg-name {
            key "srlg-name";
            description "Configured SRLG name details ";
            leaf srlg-name {
              type xr:Cisco-ios-xr-string {
                length "1..64";
              }
              description "SRLG name";
            }
            uses RSI-SRLG-NAME-INTF-SHOW;
          }
        }
        leaf node-name {
          type xr:Node-id;
          description "Node";
        }
      }
    }

    container interface-srlg-names {
      description "Set of SRLG names configured";

      list interface-srlg-name {
        key "srlg-name";
        description "Configured SRLG name details ";
        leaf srlg-name {
          type xr:Cisco-ios-xr-string {
            length "1..64";
          }
          description "SRLG name";
        }
        uses RSI-SRLG-NAME-INTF-SHOW;
      }
    }
  }

  container selective-vrf-download {
    config false;
    description "selective vrf download";

    container state {
      description "Selective VRF Download feature state details";
      uses RSI-MASTER-STATE;
    }
  }
}
