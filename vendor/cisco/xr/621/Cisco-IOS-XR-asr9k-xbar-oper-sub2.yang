submodule Cisco-IOS-XR-asr9k-xbar-oper-sub2 {

  belongs-to Cisco-IOS-XR-asr9k-xbar-oper {
    prefix Cisco-IOS-XR-asr9k-xbar-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR asr9k-xbar package operational data.

     Copyright (c) 2013-2016 by Cisco Systems, Inc.
     All rights reserved.";

  revision "2015-11-09" {
    description
      "IOS XR 6.0 revision.";
  }

  typedef Q-stats {
    type uint64;
    description "Q stats";
  }

  grouping XBAR-XML-EDM-PORT-STATS {
    description "Bag containing xbar packet stats";
    leaf internal-error-count {
      type uint64;
      description "";
    }
    leaf input-buffer-queued-packet-count-high {
      type Q-stats;
      description "";
    }
    leaf ingress-packet-count-since-last-read-high {
      type Q-stats;
      description "";
    }
    leaf ingress-channel-utilization-count-high {
      type Q-stats;
      description "";
    }
    leaf input-buffer-back-pressure-count-high {
      type Q-stats;
      description "";
    }
    leaf xbar-timeout-drop-count-high {
      type Q-stats;
      description "";
    }
    leaf holdrop-count-high {
      type Q-stats;
      description "";
    }
    leaf null-fpoe-drop-count-high {
      type Q-stats;
      description "";
    }
    leaf diagnostic-packet-count-high {
      type Q-stats;
      description "";
    }
    leaf input-buffer-correctable-ecc-error-count-high {
      type Q-stats;
      description "";
    }
    leaf input-buffer-uncorrectable-ecc-error-count-high {
      type Q-stats;
      description "";
    }
    leaf header-crc-error-count-high {
      type Q-stats;
      description "";
    }
    leaf short-input-header-error-count-high {
      type Q-stats;
      description "";
    }
    leaf packet-crc-error-count-high {
      type Q-stats;
      description "";
    }
    leaf short-packet-error-count-high {
      type Q-stats;
      description "";
    }
    leaf output-buffer-queued-packet-count-high {
      type Q-stats;
      description "";
    }
    leaf egress-packet-count-since-last-read-high {
      type Q-stats;
      description "";
    }
    leaf egress-channel-utilization-count-high {
      type Q-stats;
      description "";
    }
    leaf output-buffer-back-pressure-count-high {
      type Q-stats;
      description "";
    }
    leaf output-buffer-correctable-ecc-error-count-high {
      type Q-stats;
      description "";
    }
    leaf output-buffer-uncorrectable-ecc-error-count-high {
      type Q-stats;
      description "";
    }
    leaf fpoedb-correctable-ecc-error-count-high {
      type Q-stats;
      description "";
    }
    leaf fpoedb-uncorrectable-ecc-error-count-high {
      type Q-stats;
      description "";
    }
    leaf input-buffer-queued-packet-count-low {
      type Q-stats;
      description "";
    }
    leaf ingress-packet-count-since-last-read-low {
      type Q-stats;
      description "";
    }
    leaf ingress-channel-utilization-count-low {
      type Q-stats;
      description "";
    }
    leaf input-buffer-back-pressure-count-low {
      type Q-stats;
      description "";
    }
    leaf xbar-timeout-drop-count-low {
      type Q-stats;
      description "";
    }
    leaf holdrop-count-low {
      type Q-stats;
      description "";
    }
    leaf null-fpoe-drop-count-low {
      type Q-stats;
      description "";
    }
    leaf diagnostic-packet-count-low {
      type Q-stats;
      description "";
    }
    leaf input-buffer-correctable-ecc-error-count-low {
      type Q-stats;
      description "";
    }
    leaf input-buffer-uncorrectable-ecc-error-count-low {
      type Q-stats;
      description "";
    }
    leaf header-crc-error-count-low {
      type Q-stats;
      description "";
    }
    leaf short-input-header-error-count-low {
      type Q-stats;
      description "";
    }
    leaf packet-crc-error-count-low {
      type Q-stats;
      description "";
    }
    leaf short-packet-error-count-low {
      type Q-stats;
      description "";
    }
    leaf output-buffer-queued-packet-count-low {
      type Q-stats;
      description "";
    }
    leaf egress-packet-count-since-last-read-low {
      type Q-stats;
      description "";
    }
    leaf egress-channel-utilization-count-low {
      type Q-stats;
      description "";
    }
    leaf output-buffer-back-pressure-count-low {
      type Q-stats;
      description "";
    }
    leaf output-buffer-correctable-ecc-error-count-low {
      type Q-stats;
      description "";
    }
    leaf output-buffer-uncorrectable-ecc-error-count-low {
      type Q-stats;
      description "";
    }
    leaf fpoedb-correctable-ecc-error-count-low {
      type Q-stats;
      description "";
    }
    leaf fpoedb-uncorrectable-ecc-error-count-low {
      type Q-stats;
      description "";
    }
  }
}
