module Cisco-IOS-XR-ipv6-acl-datatypes {

  /*** NAMESPACE / PREFIX DEFINITION ***/

  namespace "http://cisco.com/ns"+
    "/yang/Cisco-IOS-XR-ipv6-acl-datatypes";


  prefix "ipv6-acl-datatypes";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of generally useful
     derived YANG data types.

     Copyright (c) 2013-2016 by Cisco Systems, Inc.
     All rights reserved.";

  revision "2015-11-09" {
    description
      "IOS XR 6.0 revision.";
  }

  typedef Ipv6-prefix-match-exact-length {
    type enumeration {
      enum match-exact-length {
        value 1;
        description "Prefix Length Exact match";
      }
    }
    description "Ipv6 prefix match exact length";
  }
  typedef Ipv6-acl-grant-enum {
    type enumeration {
      enum deny {
        value 0;
        description "Deny";
      }
      enum permit {
        value 1;
        description "Permit";
      }
    }
    description "Ipv6 acl grant enum";
  }
  typedef Ipv6-acl-logging-enum {
    type enumeration {
      enum log {
        value 1;
        description "Log matches against this entry";
      }
      enum log-input {
        value 2;
        description
          "Log matches against this entry, including input
          interface";
      }
    }
    description "Ipv6 acl logging enum";
  }
  typedef Ipv6-acl-log-threshold-range {
    type uint32 {
      range "1..2147483647";
    }
    description "Ipv6 acl log threshold range";
  }
  typedef Ipv6-acl-protocol-number {
    type union {
      type enumeration {
        enum ip {
          value 0;
          description "Any IP protocol";
        }
        enum icmp {
          value 1;
          description "Internet Control Message Protocol";
        }
        enum igmp {
          value 2;
          description "Internet Gateway Message Protocol";
        }
        enum ip-in-ip {
          value 4;
          description "IP in IP tunneling";
        }
        enum tcp {
          value 6;
          description "Transport Control Protocol";
        }
        enum igrp {
          value 9;
          description "Cisco's IGRP Routing Protocol";
        }
        enum udp {
          value 17;
          description "User Datagram Protocol";
        }
        enum gre {
          value 47;
          description "Cisco's GRE tunneling";
        }
        enum esp {
          value 50;
          description "Encapsulation Security Protocol";
        }
        enum ahp {
          value 51;
          description "Authentication Header Protocol";
        }
        enum eigrp {
          value 88;
          description "Cisco's EIGRP Routing Protocol";
        }
        enum ospf {
          value 89;
          description "OSPF Routing Protocol";
        }
        enum nos {
          value 94;
          description "KA9Q NOS Compatible IP over IP tunneling";
        }
        enum pim {
          value 103;
          description "Protocol Independent Multicast";
        }
        enum pcp {
          value 108;
          description "Payload Compression Protocol";
        }
        enum sctp {
          value 132;
          description "Stream Control Transmission Protocol";
        }
      }
      type uint32 {
        range "0..255";
      }
    }
    description "Ipv6 acl protocol number";
  }
  typedef Ipv6-acl-icmp-code-range {
    type uint32 {
      range "0..255";
    }
    description "Ipv6 acl icmp code range";
  }
  typedef Ipv6-acl-icmp-type-code-enum {
    type enumeration {
      enum no-route-to-destination {
        value 65536;
        description "No route to destination";
      }
      enum administratively-prohibited {
        value 65537;
        description "Administratively prohibited";
      }
      enum beyond-scope-of-source-address {
        value 65538;
        description "Unreachable beyond scope of address";
      }
      enum host-unreachable {
        value 65539;
        description "Host unreachable";
      }
      enum port-unreachable {
        value 65540;
        description "Port unreachable";
      }
      enum unreachable {
        value 131071;
        description "All unreachables";
      }
      enum packet-too-big {
        value 131072;
        description "packet too big";
      }
      enum ttl-exceeded {
        value 196608;
        description "TTL exceeded";
      }
      enum reassembly-timeout {
        value 196609;
        description "Reassembly timeout";
      }
      enum time-exceeded {
        value 262143;
        description "All time exceeds";
      }
      enum erronenous-header-field {
        value 262144;
        description "Erroneous header field";
      }
      enum option-missing {
        value 262145;
        description "Parameter required but not present";
      }
      enum no-room-for-option {
        value 262146;
        description "Parameter required but no room";
      }
      enum parameter-problem {
        value 327679;
        description "All parameter problems";
      }
      enum echo {
        value 8388608;
        description "Echo ping";
      }
      enum echo-reply {
        value 8454144;
        description "Echo reply";
      }
      enum group-membership-query {
        value 8585215;
        description "Multicast listener query";
      }
      enum group-membership-report {
        value 8650751;
        description "Multicast listener report";
      }
      enum group-membership-reduction {
        value 8716287;
        description "Multicast listener done";
      }
      enum router-solicitation {
        value 8716288;
        description "Router discovery solicitations";
      }
      enum router-advertisement {
        value 8781824;
        description "Router discovery advertisements";
      }
      enum neighbor-solicitation {
        value 8847360;
        description "Neighbor discovery neighbor solicitations";
      }
      enum neighbor-advertisement {
        value 8912896;
        description "Neighbor discovery neighbor advertisements";
      }
      enum redirect {
        value 8978432;
        description "All redirects";
      }
      enum rr-command {
        value 9043968;
        description "Router renumbering command";
      }
      enum rr-result {
        value 9043969;
        description "Router renumbering result";
      }
      enum rr-seqnum-reset {
        value 9044223;
        description "Router renumbering seqnum";
      }
      enum router-renumbering {
        value 9109503;
        description "Router renumbering";
      }
      enum query-subject-is-ipv6-address {
        value 9109504;
        description "Query subject is ipv6 address";
      }
      enum query-subject-is-domain-name {
        value 9109505;
        description "Query subject is domain name";
      }
      enum query-subject-is-ipv4-address {
        value 9109506;
        description "Query subject is ipv4 address";
      }
      enum who-are-you-request {
        value 9175039;
        description "Who are you request";
      }
      enum node-information-successful-reply {
        value 9175040;
        description "Node information successful reply";
      }
      enum node-information-request-is-refused {
        value 9175041;
        description "Node information reply rejected";
      }
      enum unknown-query-type {
        value 9175042;
        description "Unknown query type";
      }
      enum who-are-you-reply {
        value 9240575;
        description "Who are you reply";
      }
    }
    description "Ipv6 acl icmp type code enum";
  }
  typedef Ipv6-acl-precedence-number {
    type union {
      type enumeration {
        enum critical {
          value 5;
          description "Match packets with critical precedence";
        }
        enum flash {
          value 3;
          description "Match packets with flash precedence";
        }
        enum flash-override {
          value 4;
          description
            "Match packets with flash override precedence";
        }
        enum immediate {
          value 2;
          description "Match packets with immediate precedence";
        }
        enum internet {
          value 6;
          description
            "Match packets with internetwork control
            precedence";
        }
        enum network {
          value 7;
          description
            "Match packets with network control precedence";
        }
        enum priority {
          value 1;
          description "Match packets with priority precedence";
        }
        enum routine {
          value 0;
          description "Match packets with routine precedence";
        }
      }
      type uint32 {
        range "0..7";
      }
    }
    description "Ipv6 acl precedence number";
  }
  typedef Ipv6-acl-qos-group-number {
    type uint32 {
      range "0..512";
    }
    description "Ipv6 acl qos group number";
  }
  typedef Ipv6-acl-type-enum {
    type enumeration {
      enum acl {
        value 1;
        description "ACL";
      }
      enum prefix-list {
        value 2;
        description "Prefix List";
      }
    }
    description "Ipv6 acl type enum";
  }
  typedef Ipv6-prefix-match-min-length {
    type enumeration {
      enum match-min-length {
        value 2;
        description
          "Enable matching of Prefix Lengths greater than
          MinPrefixLength";
      }
    }
    description "Ipv6 prefix match min length";
  }
  typedef Ipv6-acl-dscp-number {
    type union {
      type enumeration {
        enum default {
          value 0;
          description "Default DSCP";
        }
        enum af11 {
          value 10;
          description "Match packets with AF11 DSCP";
        }
        enum af12 {
          value 12;
          description "Match packets with AF12 DSCP";
        }
        enum af13 {
          value 14;
          description "Match packets with AF13 DSCP";
        }
        enum af21 {
          value 18;
          description "Match packets with AF21 DSCP";
        }
        enum af22 {
          value 20;
          description "Match packets with AF22 DSCP";
        }
        enum af23 {
          value 22;
          description "Match packets with AF23 DSCP";
        }
        enum af31 {
          value 26;
          description "Match packets with AF31 DSCP";
        }
        enum af32 {
          value 28;
          description "Match packets with AF32 DSCP";
        }
        enum af33 {
          value 30;
          description "Match packets with AF33 DSCP";
        }
        enum af41 {
          value 34;
          description "Match packets with AF41 DSCP";
        }
        enum af42 {
          value 36;
          description "Match packets with AF42 DSCP";
        }
        enum af43 {
          value 38;
          description "Match packets with AF43 DSCP";
        }
        enum cs1 {
          value 8;
          description "Match packets with CS1 (precedence 1) DSCP";
        }
        enum cs2 {
          value 16;
          description "Match packets with CS2 (precedence 2) DSCP";
        }
        enum cs3 {
          value 24;
          description "Match packets with CS3 (precedence 3) DSCP";
        }
        enum cs4 {
          value 32;
          description "Match packets with CS4 (precedence 4) DSCP";
        }
        enum cs5 {
          value 40;
          description "Match packets with CS5 (precedence 5) DSCP";
        }
        enum cs6 {
          value 48;
          description "Match packets with CS6 (precedence 6) DSCP";
        }
        enum cs7 {
          value 56;
          description "Match packets with CS7 (precedence 7) DSCP";
        }
        enum ef {
          value 46;
          description "Match packets with EF DSCP";
        }
      }
      type uint32 {
        range "0..64";
      }
    }
    description "Ipv6 acl dscp number";
  }
  typedef Ipv6-acl-max-configurable-sequence-numbers {
    type uint32 {
      range "50000..350000";
    }
    description "Ipv6 acl max configurable sequence numbers";
  }
  typedef Ipv6-acl-log-rate-range {
    type uint32 {
      range "1..1000";
    }
    description "Ipv6 acl log rate range";
  }
  typedef Ipv6-acl-tcp-bits-number {
    type union {
      type enumeration {
        enum established {
          value 20;
          description "Match established connections (0x14)";
        }
        enum ack {
          value 16;
          description "Match on the ACK bit (0x10)";
        }
        enum rst {
          value 4;
          description "Match on the RST bit (0x04)";
        }
        enum fin {
          value 1;
          description "Match on the FIN bit (0x01)";
        }
        enum psh {
          value 8;
          description "Match on the PSH bit (0x08)";
        }
        enum syn {
          value 2;
          description "Match on the SYN bit (0x02)";
        }
        enum urg {
          value 32;
          description "Match on the URG bit (0x20)";
        }
      }
      type uint32 {
        range "0..63";
      }
    }
    description "Ipv6 acl tcp bits number";
  }
  typedef Ipv6-acl-prefix-list-name {
    type xr:Cisco-ios-xr-string {
      length "1..65";
    }
    description "Ipv6 acl prefix list name";
  }
  typedef Ipv6-acl-icmp-type-range {
    type uint32 {
      range "0..255";
    }
    description "Ipv6 acl icmp type range";
  }
  typedef Ipv6-prefix-match-max-length {
    type enumeration {
      enum match-max-length {
        value 3;
        description
          "Enable matching of Prefix Lengths lesser than
          MaxPrefixLength";
      }
    }
    description "Ipv6 prefix match max length";
  }
  typedef Ipv6-acl-plen-range {
    type uint32 {
      range "0..65535";
    }
    description "Ipv6 acl plen range";
  }
  typedef Ipv6-acl-ttl-range {
    type uint32 {
      range "0..255";
    }
    description "Ipv6 acl ttl range";
  }
  typedef Ipv6-acl-port-number {
    type union {
      type enumeration {
        enum echo {
          value 7;
          description "Match on the 'echo' port number";
        }
        enum discard {
          value 9;
          description "Match on the 'discard' port number";
        }
        enum daytime {
          value 13;
          description
            "Match on the 'daytime' port number (TCP/SCTP
            only)";
        }
        enum char-gen {
          value 19;
          description
            "Match on the 'chargen' port number (TCP/SCTP
            only)";
        }
        enum ftp-data {
          value 20;
          description
            "Match on the FTP data connections port number
            (TCP/SCTP only)";
        }
        enum ftp {
          value 21;
          description
            "Match on the 'ftp' port number (TCP/SCTP only)";
        }
        enum telnet {
          value 23;
          description
            "Match on the 'telnet' port number (TCP/SCTP
            only)";
        }
        enum smtp {
          value 25;
          description
            "Match on the 'smtp' port number (TCP/SCTP
            only)";
        }
        enum time {
          value 37;
          description "Match on the 'time' port number";
        }
        enum name-server {
          value 42;
          description
            "Match on the IEN116 name service port number
            (UDP only)";
        }
        enum who-is {
          value 43;
          description
            "Match on the 'nicname' port number (TCP/SCTP
            only)";
        }
        enum tacacs {
          value 49;
          description "Match on the 'tacacs' port number";
        }
        enum dns {
          value 53;
          description "Match on the 'dns' port number";
        }
        enum boot-ps {
          value 67;
          description
            "Match on the Bootstrap Protocol server port
            number (UDP only)";
        }
        enum boot-pc {
          value 68;
          description
            "Match on the Bootstrap Protocol client port
            number (UDP only)";
        }
        enum tftp {
          value 69;
          description "Match on the 'tftp' port number (UDP only)";
        }
        enum gopher {
          value 70;
          description
            "Match on the 'gopher' port number (TCP/SCTP
            only)";
        }
        enum finger {
          value 79;
          description
            "Match on the 'finger' port number (TCP/SCTP
            only)";
        }
        enum www {
          value 80;
          description
            "Match on the 'http' port number (TCP/SCTP
            only)";
        }
        enum host-name {
          value 101;
          description
            "Match on the NIC hostname server port number
            (TCP/SCTP only)";
        }
        enum pop2 {
          value 109;
          description
            "Match on the 'pop2' port number (TCP/SCTP
            only)";
        }
        enum pop3 {
          value 110;
          description
            "Match on the 'pop3' port number (TCP/SCTP
            only)";
        }
        enum sun-rpc {
          value 111;
          description "Match on the Sun RPC port number";
        }
        enum ident {
          value 113;
          description
            "Match on the 'ident' port number (TCP/SCTP
            only)";
        }
        enum nntp {
          value 119;
          description
            "Match on the 'nntp' port number (TCP/SCTP
            only)";
        }
        enum ntp {
          value 123;
          description "Match on the 'ntp' port number (UDP only)";
        }
        enum net-bios-ns {
          value 137;
          description
            "Match on the NetBIOS name service port number
            (UDP only)";
        }
        enum net-bios-dgs {
          value 138;
          description
            "Match on the NetBIOS datagram service port
            number (UDP only)";
        }
        enum net-bios-ss {
          value 139;
          description
            "Match on the NetBIOS session service port
            number (UDP only)";
        }
        enum snmp {
          value 161;
          description "Match on the 'snmp' port number (UDP only)";
        }
        enum snmp-trap {
          value 162;
          description
            "Match on the SNMP traps port number (UDP only)";
        }
        enum xdmcp {
          value 177;
          description "Match on the 'xdmcp' port number (UDP only)";
        }
        enum bgp {
          value 179;
          description
            "Match on the 'bgp' port number (TCP/SCTP only)";
        }
        enum irc {
          value 194;
          description
            "Match on the 'irc' port number (TCP/SCTP only)";
        }
        enum dnsix {
          value 195;
          description
            "Match on the DNSIX security protocol auditing
            port number (UDP only)";
        }
        enum mobile-ip {
          value 434;
          description
            "Match on the mobile IP registration port
            number (UDP only)";
        }
        enum pim-auto-rp {
          value 496;
          description "Match on the PIM Auto-RP port number";
        }
        enum isakmp {
          value 500;
          description
            "Match on the 'isakmp' port number (UDP only)";
        }
        enum exec-or-biff {
          value 512;
          description
            "Match on the port used by TCP/SCTP for 'exec'
            and by UDP for 'biff'";
        }
        enum login-or-who {
          value 513;
          description
            "Match on the port used by TCP/SCTP for 'login'
            and by UDP for 'rwho'";
        }
        enum cmd-or-syslog {
          value 514;
          description
            "Match on the port used by TCP/SCTP for 'rcmd'
            and by UDP for 'syslog'";
        }
        enum lpd {
          value 515;
          description
            "Match on the 'lpd' port number (TCP/SCTP only)";
        }
        enum talk {
          value 517;
          description "Match on the 'talk' port number";
        }
        enum rip {
          value 520;
          description "Match on the 'rip' port number (UDP only)";
        }
        enum uucp {
          value 540;
          description
            "Match on the 'uucp' port number (TCP/SCTP
            only)";
        }
        enum klogin {
          value 543;
          description
            "Match on the Kerberos login port number
            (TCP/SCTP only)";
        }
        enum kshell {
          value 544;
          description
            "Match on the Kerberos shell port number
            (TCP/SCTP only)";
        }
        enum ldp {
          value 646;
          description "Match on the LDP port";
        }
      }
      type uint32 {
        range "0..65535";
      }
    }
    description "Ipv6 acl port number";
  }
  typedef Ipv6-acl-status-enum {
    type enumeration {
      enum disabled {
        value 0;
        description "Disabled";
      }
      enum enabled {
        value 1;
        description "Enabled";
      }
    }
    description "Ipv6 acl status enum";
  }
  typedef Ipv6-acl-max-configurable-acl {
    type uint32 {
      range "1000..16000";
    }
    description "Ipv6 acl max configurable acl";
  }
  typedef Ipv6-acl-operator-enum {
    type enumeration {
      enum equal {
        value 1;
        description "Match only packets on a given port number";
      }
      enum greater-than {
        value 2;
        description "Match only packet with a greater port number";
      }
      enum less-than {
        value 3;
        description "Match only packet with a lower port number";
      }
      enum not-equal {
        value 4;
        description "Match only packets not on a given port number";
      }
      enum range {
        value 5;
        description
          "Match only packets in the range of port numbers";
      }
    }
    description "Ipv6 acl operator enum";
  }
  typedef Ipv6-acl-tcp-match-operator-enum {
    type enumeration {
      enum match-all {
        value 1;
        description "Match only packet with all the given TCP bits";
      }
      enum match-any {
        value 3;
        description
          "Match only packet with any of the given TCP
          bits";
      }
    }
    description "Ipv6 acl tcp match operator enum";
  }
}
