submodule Cisco-IOS-XR-fib-common-oper-sub1 {

  belongs-to Cisco-IOS-XR-fib-common-oper {
    prefix Cisco-IOS-XR-fib-common-oper;
  }

  /*** LINKAGE (IMPORTS / INCLUDES) ***/

  import ietf-inet-types { prefix "inet"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR fib-common package operational data.

     Copyright (c) 2013-2016 by Cisco Systems, Inc.
     All rights reserved.";

  revision "2017-01-20" {
    description
      "IOS XR 6.2.1 revision";
  }

  revision "2015-11-09" {
    description
      "IOS XR 6.0 revision.";
  }

  typedef Mgmt-fib-mpls-frr-state {
    type enumeration {
      enum partial {
        value 0;
        description "Partial";
      }
      enum active {
        value 1;
        description "Active";
      }
      enum ready {
        value 2;
        description "Ready";
      }
      enum complete {
        value 3;
        description "Complete";
      }
      enum any {
        value 4;
        description "Any";
      }
    }
    description "MPLS FRR entry state";
  }
  typedef Mgmt-fib-mpls-lsp-role {
    type enumeration {
      enum head {
        value 0;
        description "Head";
      }
      enum midpoint {
        value 1;
        description "Midpoint";
      }
    }
    description "MPLS FRR entry role";
  }

  grouping FIB-MPLS-FRR-DB-MCAST-LEGS {
    description "FIB MPLS FRR DB MCAST LEGS";

    container frr-entry-id {
      description "FRR entry ID";
      uses FIB-MPLS-FRR-DB-ENTRY-GEN-ID;
    }
    leaf tunnel-interface-name {
      type xr:Interface-name;
      description "Tunnel interface";
    }
    leaf input-label {
      type uint32;
      description "Input label";
    }
    leaf outgoing-interface {
      type xr:Interface-name;
      description "Outgoing interface";
    }
    leaf outgoing-label {
      type uint32;
      description "Outgoing label";
    }
    leaf frr-interface-name {
      type xr:Interface-name;
      description "FRR interface";
    }
    leaf frr-label {
      type uint32;
      description "FRR output label";
    }
    leaf entry-frr-state {
      type Mgmt-fib-mpls-frr-state;
      description "MPLS FRR entry state";
    }
    leaf frr-next-hop-ipv4-address {
      type inet:ipv4-address;
      description "Next hop IPv4 address";
    }
    leaf is-mldp-lsp {
      type boolean;
      description "MLDP or P2MP-TE";
    }
  }

  grouping FIB-MPLS-FRR-DB-ENTRY-MID-ID {
    description "FIB MPLS FRR DB ENTRY MID ID";
    leaf source-address {
      type inet:ipv4-address;
      description "Source IPv4 address";
    }
    leaf lspid {
      type uint32;
      description "LSP ID";
    }
    leaf tunnel-id {
      type uint32;
      description "Tunnel ID";
    }
  }

  grouping FIB-MPLS-FRR-DB-ENTRY-HEAD-ID {
    description "FIB MPLS FRR DB ENTRY HEAD ID";
    leaf destination-prefix {
      type inet:ipv4-address;
      description "Destination prefix";
    }
    leaf destination-prefix-length {
      type uint32;
      description "Destination prefix length";
    }
  }

  grouping FIB-MPLS-FRR-DB-ENTRY-GEN-ID {
    description "FIB MPLS FRR DB ENTRY GEN ID";

    container head {
      when "../role = 'head'" {
        description "../Role = 'Head'";
      }
      description "head";
      uses FIB-MPLS-FRR-DB-ENTRY-HEAD-ID;
    }

    container midpoint {
      when "../role = 'midpoint'" {
        description "../Role = 'Midpoint'";
      }
      description "midpoint";
      uses FIB-MPLS-FRR-DB-ENTRY-MID-ID;
    }
    leaf role {
      type Mgmt-fib-mpls-lsp-role;
      description "Role";
    }
  }

  grouping FIB-MPLS-FRR-DB-ENTRY {
    description "FIB MPLS FRR DB ENTRY";

    container frr-entry-id {
      description "FRR entry ID";
      uses FIB-MPLS-FRR-DB-ENTRY-GEN-ID;
    }
    leaf tunnel-interface-name {
      type xr:Interface-name;
      description "Tunnel interface";
    }
    leaf input-label {
      type uint32;
      description "Input label";
    }
    leaf outgoing-interface {
      type xr:Interface-name;
      description "Outgoing interface";
    }
    leaf outgoing-label {
      type uint32;
      description "Outgoing label";
    }
    leaf frr-interface-name {
      type xr:Interface-name;
      description "FRR interface";
    }
    leaf frr-label {
      type uint32;
      description "FRR output label";
    }
    leaf entry-frr-state {
      type Mgmt-fib-mpls-frr-state;
      description "MPLS FRR entry state";
    }
    leaf frr-next-hop-ipv4-address {
      type inet:ipv4-address;
      description "Next hop IPv4 address";
    }
    leaf is-mldp-lsp {
      type boolean;
      description "MLDP or P2MP-TE";
    }
    leaf is-multicast-tunnel {
      type boolean;
      description "Multicast tunnel";
    }
    leaf multicast-tunnel-legs {
      type uint32;
      description "Number of legs in MCAST tunnel";
    }

    list multicast-leg {
      description "MCAST legs";
      uses FIB-MPLS-FRR-DB-MCAST-LEGS;
    }
  }

  grouping FIB-MPLS-FRR-DB-SUM {
    description "FIB MPLS FRR DB SUM";
    leaf active {
      type uint32;
      description "Number of FRR rewrites in Active state";
    }
    leaf ready {
      type uint32;
      description "Number of FRR rewrites in Ready state";
    }
    leaf partial {
      type uint32;
      description "Number of FRR rewrites in Partial state";
    }
    leaf other {
      type uint32;
      description "Number of FRR rewrites in an unrecognized state";
    }
  }

  grouping FIB-MPLS-SH-TUN-INFO {
    description "Information about TE-head tunnel LI";
    leaf tunnel-interface-name {
      type xr:Interface-name;
      description "Tunnel interface";
    }
    leaf tunnel-local-label {
      type uint32;
      description "Tunnel Local label";
    }
    leaf tunnel-fwd-class {
      type uint8;
      description "Tunnel Forward Class";
    }
    leaf tunnel-load-metric {
      type uint8;
      description " Tunnel Load Metric";
    }
    leaf tunnel-is-srte {
      type boolean;
      description "Is Tunnel SRTE";
    }
    leaf tunnel-resolution-incomplete {
      type boolean;
      description "Tunnel head resolution is incomplete";
    }
    leaf tunnel-resolution-inconsistent {
      type boolean;
      description
        "Tunnel head resolition is inconsitent b/w TEhead
        and Local label";
    }
    leaf tunnel-is-programmed-to-drop {
      type boolean;
      description "Is Tunnel programmed as drop";
    }
    leaf tli-type {
      type uint32;
      description "Th tunnel LI type";
    }
    leaf tli-pointer {
      type uint32;
      description "The pointer to the Tun LI object";
    }
    leaf tli-reference-count {
      type uint32;
      description "The Tunnel LI object refcounter";
    }
    leaf tli-flags {
      type uint32;
      description "Tunnel LI flags";
    }
    leaf tli-flags-extended {
      type uint32;
      description "Tunnel LI extended flags";
    }
  }

  grouping FIB-MPLS-TIMESPEC {
    description "FIB MPLS TIMESPEC";
    leaf seconds {
      type int32;
      units "second";
      description "Seconds part of time valueiin UTC";
    }
    leaf nanoseconds {
      type int32;
      units "nanosecond";
      description "Nanoseconds part of time value";
    }
  }

  grouping FIB-MPLS-FRR-EVENT {
    description "FIB MPLS FRR EVENT";

    container start-time {
      description
        "Time of FRR event processing start, Seconds in
        UTC, and Nano Seconds";
      uses FIB-MPLS-TIMESPEC;
    }
    leaf protected-frr-interface-name {
      type xr:Interface-name;
      description "Interface";
    }
    leaf next-hop {
      type uint32;
      description "Next Hop";
    }
    leaf number-of-rewrites-affected {
      type uint32;
      description "Number of rewrites affected";
    }
    leaf switching-time-nsecs {
      type uint32;
      units "nanosecond";
      description "Time to switch rewrites [nsecs]";
    }
    leaf main-processing {
      type uint32;
      description "Main Processing for FRR";
    }
    leaf fast-bundle-member-down-interface {
      type uint32;
      description "Fast Bundle Member Down Interface";
    }
    leaf frr-event-node-id {
      type xr:Node-id;
      description "Node on which the FRR event happened";
    }
  }
}
