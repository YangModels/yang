submodule Cisco-IOS-XR-ipv4-ospf-oper-sub2 {

  belongs-to Cisco-IOS-XR-ipv4-ospf-oper {
    prefix Cisco-IOS-XR-ipv4-ospf-oper;
  }

  /*** LINKAGE (IMPORTS / INCLUDES) ***/

  import ietf-inet-types { prefix "inet"; }

  import ietf-yang-types { prefix "yang"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ipv4-ospf package operational data.

     Copyright (c) 2013-2016 by Cisco Systems, Inc.
     All rights reserved.";

  revision "2017-01-02" {
    description
      "IOS XR 6.2.1 revision.";
  }

  revision "2015-11-09" {
    description
      "IOS XR 6.0 revision.";
  }

  typedef Ospf-sh-opq-ri-pce-addr-types {
    type enumeration {
      enum mgmt-ospf-opq-pce-addr-type-invalid {
        value 0;
        description "Invalid PCE Address";
      }
      enum mgmt-ospf-opq-pce-addr-type-ipv4 {
        value 1;
        description "IPv4 PCE Address";
      }
      enum mgmt-ospf-opq-pce-addr-type-ipv6 {
        value 2;
        description "IPv6 PCE Address";
      }
    }
    description "OSPF PCE Address Type";
  }
  typedef Ospf-sh-opq-ri-tlv-types {
    type enumeration {
      enum mgmt-ospf-opq-ri-tlv-type-unknown {
        description "Unknown";
      }
      enum mgmt-ospf-opq-ri-tlv-type-rtrcap {
        description "Router Capabilities";
      }
      enum mgmt-ospf-opq-ri-tlv-type-pce-discovery {
        description "PCE Discovery";
      }
      enum mgmt-ospf-opq-ri-tlv-type-sr-algo {
        description "Segment Routing Algorithm";
      }
      enum mgmt-ospf-opq-ri-tlv-type-sr-range {
        description "Segment Routing SID Range";
      }
    }
    description "OSPF Router Information TLV types";
  }
  typedef Ospf-lsa-opq-ri-scope {
    type enumeration {
      enum mgmt-lsa-opq-ri-scope-link {
        value 9;
        description "Link-local Router Information LSA";
      }
      enum mgmt-lsa-opq-ri-scope-area {
        value 10;
        description "Area-scope Router Information LSA";
      }
      enum mgmt-lsa-opq-ri-scope-as {
        value 11;
        description "AS-scope Router Information LSA";
      }
    }
    description "OSPF Router Information LSA scope types";
  }
  typedef Ospf-gr-reason {
    type enumeration {
      enum mgmt-gr-reason-unknown {
        description "Unknown";
      }
      enum mgmt-gr-reason-sw-restart {
        description "Software restart";
      }
      enum mgmt-gr-reason-sw-upgrade {
        description "Software reload/upgrade";
      }
      enum mgmt-gr-reason-switchover {
        description "Switch to redundant control processor";
      }
    }
    description "Ospf gr reason";
  }
  typedef Stlv {
    type enumeration {
      enum mgmt-rrr-link-type {
        value 1;
        description "Link Type";
      }
      enum mgmt-rrr-link-id {
        value 2;
        description "Link ID";
      }
      enum mgmt-rrr-link-local-if-addr {
        value 3;
        description "Local interface IP address";
      }
      enum mgmt-rrr-link-remote-if-addr {
        value 4;
        description "Remote interface IP address";
      }
      enum mgmt-rrr-link-metric {
        value 5;
        description "Traffic Engineering metric";
      }
      enum mgmt-rrr-link-max-bw {
        value 6;
        description "Maximum Link Bandwidth";
      }
      enum mgmt-rrr-link-max-reservable-bw {
        value 7;
        description "Maximum Reservable bandwidth";
      }
      enum mgmt-rrr-link-unreserved-bw {
        value 8;
        description "Unreserved Bandwidth";
      }
      enum mgmt-rrr-link-re-source-class {
        value 9;
        description "Administrative group";
      }
      enum mgmt-rrr-link-in-out-if-id {
        value 11;
        description "Link Local/Remote Identifiers";
      }
      enum mgmt-rrr-link-if-switching-cap-desc {
        value 15;
        description "Interface Switching Capability Descriptor";
      }
      enum mgmt-ospf-rrr-link-srlg {
        value 16;
        description "Shared Risk Link Group";
      }
      enum mgmt-rrr-link-bw-constraints-sub {
        value 17;
        description "Bandwidth constraints";
      }
      enum mgmt-ospf-rrr-link-uni-delay {
        value 27;
        description "Unidirectional link delay";
      }
      enum mgmt-ospf-rrr-link-max-reservable-bw-sub {
        value 32768;
        description "Maximum reservable sub-pool bandwidth";
      }
      enum mgmt-ospf-rrr-link-unreserved-bw-sub {
        value 32769;
        description "Unreserved sub-pool bandwidth";
      }
      enum mgmt-rrr-link-igp-metric {
        value 32770;
        description "IGP Link Metric";
      }
      enum mgmt-ospf-rrr-link-ext-admin-sub {
        value 32771;
        description "Extended admin";
      }
    }
    description "OSPF Opaque-area Type 1 sub TLV types";
  }
  typedef Ex-metric {
    type enumeration {
      enum mgmt-ex-metric-type-none {
        value 0;
        description "No metric type";
      }
      enum mgmt-ex-metric-type-1 {
        value 1;
        description "Type 1 External";
      }
      enum mgmt-ex-metric-type-2 {
        value 2;
        description "Type 2 External";
      }
    }
    description "Ex metric";
  }
  typedef Ospf-link-types {
    type enumeration {
      enum mgmt-rtr-link {
        value 1;
        description "Link to a Router";
      }
      enum mgmt-trans-link {
        value 2;
        description "Link to a transit network";
      }
      enum mgmt-stub-net {
        value 3;
        description "Link to Stub network";
      }
      enum mgmt-vitural-link {
        value 4;
        description "Link to Virtual Link";
      }
    }
    description "Type of router LSA links";
  }
  typedef Ospf-internal-lsa-types {
    type enumeration {
      enum mgmt-rtr-type {
        value 1;
        description "Router LSA";
      }
      enum mgmt-ntwk-type {
        value 2;
        description "Network LSA";
      }
      enum mgmt-sum-type {
        value 3;
        description "Summary and ASBR summary LSA";
      }
      enum mgmt-ext-type {
        value 4;
        description "Type 5 and NSSA external LSA";
      }
      enum mgmt-opq-type {
        value 5;
        description "Generic AS/Area Opaque LSA";
      }
      enum mgmt-opq-link-type {
        value 6;
        description "Generic Link Opaque LSA";
      }
      enum mgmt-opq-rrr-type {
        value 7;
        description "Opaque Area type 1 LSA";
      }
      enum mgmt-opq-gr-type {
        value 8;
        description "Opaque link type 1 LSA";
      }
      enum mgmt-opq-ri-type {
        value 9;
        description "Opaque Router Information LSA";
      }
      enum mgmt-opq-epl-type {
        value 10;
        description "Opaque Area type 128";
      }
      enum mgmt-opq-ell-type {
        value 11;
        description "Opaque Area type 8";
      }
    }
    description "OSPF LSA format types";
  }
  typedef Timer {
    type enumeration {
      enum mgmt-db-stop {
        description "Timer stopped";
      }
      enum mgmt-db-refresh {
        description "Refresh";
      }
      enum mgmt-db-checksum {
        description "Checksum";
      }
      enum mgmt-db-max-age {
        description "Maxage";
      }
    }
    description
      "The LSA timer running can be refresh, checksum or
      maxage";
  }
  typedef Timer-table {
    type enumeration {
      enum mgmt-db-no-table {
        description "Not in time table";
      }
      enum mgmt-db-sec-table {
        description "In second table";
      }
      enum mgmt-db-buffer-table {
        description "In buffer table";
      }
      enum mgmt-db-min-table {
        description "In minute table";
      }
    }
    description
      "The throttled LSA can be in second, buffer or
      minute timer table";
  }
  typedef Ospf-srgb-status {
    type enumeration {
      enum not-allocated {
        value 0;
        description "Not allocated";
      }
      enum pending {
        value 1;
        description "Allocation pending";
      }
      enum allocated {
        value 2;
        description "Allocated";
      }
    }
    description "Ospf srgb status";
  }
  typedef Uloop-avoidance {
    type enumeration {
      enum none {
        value 0;
        description "No uloop avoidance";
      }
      enum protected-prefixes {
        value 1;
        description
          "Apply Local uloop avoidance only for protected
          prefixes";
      }
      enum all-prefixes {
        value 2;
        description "Apply Local uloop avoidance for all prefixes";
      }
      enum segment-routing-uloop {
        value 3;
        description "Apply segment routing uloop avoidance";
      }
    }
    description "Uloop avoidance";
  }
  typedef Gs-state {
    type enumeration {
      enum mgmt-gs-init {
        description "Process in initialization ";
      }
      enum mgmt-gs-normal {
        description "Graceful Shutdown not running";
      }
      enum mgmt-gs-delay {
        description "Delaying  before Graceful Shutdown";
      }
      enum mgmt-gs-flush {
        description "Flushing self originated LSAs";
      }
      enum mgmt-gs-hello {
        description "Sending empty hellos";
      }
      enum mgmt-gs-quiet {
        description "Shutdown mode.";
      }
    }
    description "Gs state";
  }
  typedef Max-metric-unset-reason {
    type enumeration {
      enum mgmt-max-metric-unset-none {
        description "none";
      }
      enum mgmt-max-metric-unset-bgp {
        description "BGP converged";
      }
      enum mgmt-max-metric-unset-timer {
        description "timer expired";
      }
      enum mgmt-max-metric-unset-cfg {
        description "unconfigured";
      }
      enum mgmt-max-metric-unset-process-cleared {
        description "process cleared";
      }
      enum mgmt-max-metric-unset-over-write {
        description "set for other reason";
      }
    }
    description "Max metric unset reason";
  }
  typedef Ospf-max-metric-abr-off-reasons {
    type enumeration {
      enum ospf-max-metric-abr-off-reason-none {
        value 0;
        description "No reason";
      }
      enum ospf-max-metric-abr-off-reason-no-nbr {
        value 1;
        description "No neighbors seen yet";
      }
      enum ospf-max-metric-abr-off-reason-new-nbr {
        value 2;
        description "New neighbor seen recently";
      }
      enum ospf-max-metric-abr-off-reason-nbr-full {
        value 4;
        description "Adjacency FULL seen recently";
      }
      enum ospf-max-metric-abr-off-reason-flush-p-end {
        value 8;
        description "LSA flushes pending";
      }
    }
    description "Ospf max metric abr off reasons";
  }
  typedef Max-metric-set-reason {
    type enumeration {
      enum mgmt-max-metric-on-proc-migration {
        description "proc migration";
      }
      enum mgmt-max-metric-on-proc-restart {
        description "proc restart";
      }
      enum mgmt-max-metric-on-switchover {
        description "switch over";
      }
      enum mgmt-max-metric-on-startup {
        description "start up";
      }
      enum mgmt-max-metric-always {
        description "always";
      }
      enum mgmt-max-metric-reason-none {
        description "none";
      }
    }
    description "Max metric set reason";
  }
  typedef Sr-uloop-event {
    type enumeration {
      enum none {
        value 0;
        description "No SR uloop event";
      }
      enum link-down {
        value 1;
        description "SR Uloop Event Link Down";
      }
      enum link-up {
        value 2;
        description "SR Uloop Event Link Up";
      }
    }
    description "Sr uloop event";
  }
  typedef Ospf-br {
    type enumeration {
      enum mgmt-d-type-abr-asbr {
        description "Both Area Border Router and AS Border Router";
      }
      enum mgmt-d-type-asbr {
        description "AS Border Router";
      }
      enum mgmt-d-type-abr {
        description "Area Border Router";
      }
    }
    description "Ospf br";
  }
  typedef Ipfrr-tbrkr {
    type enumeration {
      enum downstream {
        value 0;
        description "Downsteram";
      }
      enum line-card-disjoint {
        value 1;
        description "LC Disjoint";
      }
      enum backup-metric {
        value 2;
        description "Backup metric";
      }
      enum node-protect {
        value 3;
        description "Node protection";
      }
      enum primary-path {
        value 4;
        description "Primary path";
      }
      enum secondary-path {
        value 5;
        description "Secondary path";
      }
      enum srlg-disjoint {
        value 6;
        description "SRLG disjoint";
      }
      enum tunnel {
        value 7;
        description "Tunnel";
      }
      enum post-convergence {
        value 8;
        description "Post Convergence";
      }
    }
    description "FRR Tiebreakers";
  }
  typedef Ipfrr {
    type enumeration {
      enum none {
        value 0;
        description "Disabled";
      }
      enum per-link {
        value 1;
        description "Per link";
      }
      enum per-prefix {
        value 2;
        description "Per prefix";
      }
    }
    description "FRR Types";
  }
  typedef Interface-state {
    type enumeration {
      enum mgmt-ifs-unknown {
        description "Interface state unknown";
      }
      enum mgmt-ifs-admin-down {
        description "Interface is administratively down";
      }
      enum mgmt-ifs-down {
        description "Interface is down";
      }
      enum mgmt-ifs-up {
        description "Interface is up";
      }
      enum mgmt-ifs-shutdown {
        description "Interface is administratively down";
      }
    }
    description "Interface state";
  }
  typedef Authentication {
    type enumeration {
      enum mgmt-ospf-auth-none {
        value 0;
        description "No Authentication";
      }
      enum mgmt-ospf-auth-ct {
        value 1;
        description "Clear Text";
      }
      enum mgmt-ospf-auth-md {
        value 2;
        description "MD5";
      }
      enum mgmt-ospf-auth-kc {
        value 3;
        description "Keychain";
      }
    }
    description "Authentication";
  }
  typedef Ospf-interface-state {
    type enumeration {
      enum mgmt-ospf-ifs-down {
        value 0;
        description "Down";
      }
      enum mgmt-ospf-ifs-loop-back {
        value 1;
        description "Loopback";
      }
      enum mgmt-ospf-ifs-waiting {
        value 2;
        description "Waiting";
      }
      enum mgmt-ospf-ifs-point-to-m-point {
        value 3;
        description "Point to multipoint";
      }
      enum mgmt-ospf-ifs-point-to-point {
        value 4;
        description "Point to point";
      }
      enum mgmt-ospf-ifs-dr {
        value 5;
        description "DesignatedRouter";
      }
      enum mgmt-ospf-ifs-backup {
        value 6;
        description "Backup Designated Router";
      }
      enum mgmt-ospf-ifs-other {
        value 7;
        description "Designated Router Other";
      }
    }
    description "Ospf interface state";
  }
  typedef String1 {
    type string;
    description "String1";
  }
  typedef Redist-protocol {
    type enumeration {
      enum mgmt-rib-protocol-all {
        description "Unknown";
      }
      enum mgmt-rib-protocol-connected {
        description "Connected";
      }
      enum mgmt-rib-protocol-local {
        description "Local";
      }
      enum mgmt-rib-protocol-static {
        description "Static";
      }
      enum mgmt-rib-protocol-bgp {
        description "BGP";
      }
      enum mgmt-rib-protocol-rip {
        description "RIP";
      }
      enum mgmt-rib-protocol-isis {
        description "ISIS";
      }
      enum mgmt-rib-protocol-ospf {
        description "OSPF";
      }
      enum mgmt-rib-protocol-eigrp {
        description "EIGRP";
      }
      enum mgmt-rib-protocol-dagr {
        description "DAGR";
      }
      enum mgmt-rib-protocol-subscriber {
        description "Subscriber";
      }
      enum mgmt-rib-protocol-application {
        description "Application";
      }
      enum mgmt-rib-protocol-mobile {
        description "Mobile";
      }
    }
    description "Redist protocol";
  }
  typedef Ospf-route {
    type enumeration {
      enum mgmt-r-type-none {
        value 0;
        description "No route type";
      }
      enum mgmt-r-type-other {
        value 1;
        description "Not set";
      }
      enum mgmt-r-type-intra {
        value 2;
        description "Intra-area route";
      }
      enum mgmt-r-type-inter {
        value 4;
        description "Inter-area route";
      }
      enum mgmt-r-type-extern1 {
        value 8;
        description "Type 1 External route";
      }
      enum mgmt-r-type-extern2 {
        value 16;
        description "Type 2 External route";
      }
      enum mgmt-r-type-isis-sum {
        value 32;
        description "IS-IS summary route";
      }
      enum mgmt-r-type-isis-l1 {
        value 64;
        description "IS-IS level 1 route";
      }
      enum mgmt-r-type-isis-l2 {
        value 128;
        description "IS-IS level 2 route";
      }
      enum mgmt-r-type-isis-l1-ia {
        value 256;
        description "IS-IS level 1 inter-area route";
      }
      enum mgmt-r-type-bgp-int {
        value 512;
        description "iBGP route";
      }
      enum mgmt-r-type-bgp-ext {
        value 1024;
        description "eBGP route";
      }
      enum mgmt-r-type-bgp-loc {
        value 2048;
        description "BGP local route";
      }
      enum mgmt-r-type-nssa1 {
        value 4096;
        description "Type 1 NSSA route";
      }
      enum mgmt-r-type-nssa2 {
        value 8192;
        description "Type 2 NSSA route";
      }
      enum mgmt-r-type-i-grp2-int {
        value 16384;
        description "EIGRP internal route";
      }
      enum mgmt-r-type-i-grp2-ext {
        value 32768;
        description "EIGRP external route";
      }
    }
    description "Ospf route";
  }
  typedef Nsf-rtr {
    type enumeration {
      enum mgmt-nsf-rtr-none {
        description "None";
      }
      enum mgmt-nsf-rtr-requester {
        description "Requester";
      }
      enum mgmt-nsf-rtr-receiver {
        description "Receiver";
      }
    }
    description "Nsf rtr";
  }
  typedef Interface {
    type enumeration {
      enum mgmt-if-broadcast {
        value 1;
        description "Broadcast";
      }
      enum mgmt-if-nonbroadcast {
        value 2;
        description "Non broadcast multi access";
      }
      enum mgmt-if-point-to-point {
        value 3;
        description "Point to Point";
      }
      enum mgmt-if-point-to-m-point {
        value 4;
        description "Point to multipoint";
      }
      enum mgmt-if-p2mp-non-bcast {
        value 5;
        description "Non broadcast point to multipoint";
      }
      enum mgmt-if-virtual-link {
        value 6;
        description "Virtual link";
      }
      enum mgmt-if-sham-link {
        value 7;
        description "Sham link";
      }
      enum mgmt-if-loop-back {
        value 8;
        description "Loopback";
      }
    }
    description "Interface";
  }
  typedef Dr-bdr-state {
    type enumeration {
      enum mgmt-dbdr-none {
        description "None";
      }
      enum mgmt-dbdr-dr {
        description "Designated Router";
      }
      enum mgmt-dbdr-bdr {
        description "Backup Designated Router";
      }
      enum mgmt-dbdr-dr-other {
        description "Designated Router Other";
      }
    }
    description "Dr bdr state";
  }
  typedef Neighbor-state {
    type enumeration {
      enum mgmt-nbr-down {
        value 0;
        description "Down";
      }
      enum mgmt-nbr-attempt {
        value 1;
        description "Attempt";
      }
      enum mgmt-nbr-init {
        value 2;
        description "Init";
      }
      enum mgmt-nbr-2way {
        value 3;
        description "2 Way";
      }
      enum mgmt-nbr-ex-start {
        value 4;
        description "Exstart";
      }
      enum mgmt-nbr-ex-change {
        value 5;
        description "Exchange";
      }
      enum mgmt-nbr-load-ing {
        value 6;
        description "Loading";
      }
      enum mgmt-nbr-full {
        value 7;
        description "Full";
      }
      enum mgmt-nbr-sc-virtual {
        value 8;
        description "SCvirtual";
      }
    }
    description "Neighbor state";
  }
  typedef Mpls-te-opt-tlv {
    type enumeration {
      enum mpls-te-opt-tlv-type-none {
        value 0;
        description "None";
      }
      enum mpls-te-opt-tlv-type-srlg {
        value 1;
        description "SRLGs";
      }
      enum mpls-te-opt-tlv-type-bc {
        value 2;
        description "Bandwidth Constraints";
      }
      enum mpls-te-opt-tlv-type-ixcd {
        value 3;
        description "Intarface Switching Capability Descriptor";
      }
      enum mpls-te-opt-tlv-type-uni-delay {
        value 4;
        description "Unidirectional Link Delay";
      }
    }
    description "Mpls te opt tlv";
  }
  typedef Igpte-lib-bw-model {
    type enumeration {
      enum rdm {
        value 0;
        description "Russian Dolls Model";
      }
      enum mam {
        value 1;
        description "Maximum Allocation Model";
      }
      enum not-set {
        value 2;
        description "No model set";
      }
    }
    description "Bandwidth model";
  }
  typedef Link-subnet {
    type enumeration {
      enum mgmt-igp-subnet-type-none {
        value 0;
        description "None";
      }
      enum mgmt-igp-subnet-type-p2p {
        value 1;
        description "Point to Point";
      }
      enum mgmt-igp-subnet-type-broadcast {
        value 2;
        description "Broadcast";
      }
      enum mgmt-igp-subnet-type-nbma {
        value 3;
        description "Non Broadcast Multi Access";
      }
      enum mgmt-igp-subnet-type-p2mp {
        value 4;
        description "Point to multipoint";
      }
      enum mgmt-igp-subnet-type-loop-back {
        value 5;
        description "Loopback";
      }
      enum mgmt-igp-subnet-type-max {
        value 6;
        description "Unsupported";
      }
    }
    description "Link subnet";
  }
  typedef Lsa {
    type enumeration {
      enum mgmt-lsa-type-rtr {
        value 1;
        description "Router LSA";
      }
      enum mgmt-lsa-type-net {
        value 2;
        description "Network LSA";
      }
      enum mgmt-lsa-type-sum-net {
        value 3;
        description "Summary LSA";
      }
      enum mgmt-lsa-type-sum-asb {
        value 4;
        description "Summary-ASBR LSA";
      }
      enum mgmt-lsa-type-ext {
        value 5;
        description "AS external LSA";
      }
      enum mgmt-lsa-type-mospf {
        value 6;
        description "MOSPF LSA";
      }
      enum mgmt-lsa-type-7-ase {
        value 7;
        description "Type-7 External LSA";
      }
      enum mgmt-lsa-type-8-ignore {
        value 8;
        description "Invalid type";
      }
      enum mgmt-lsa-type-opq-link {
        value 9;
        description "Opaque link LSA";
      }
      enum mgmt-lsa-type-opq-area {
        value 10;
        description "Opaque Area LSA";
      }
      enum mgmt-lsa-type-opq-as {
        value 11;
        description "Opaque AS LSA";
      }
    }
    description "Lsa";
  }

  grouping OSPF-SH-IPFRR-TOPO-ENTRY {
    description "OSPF_IPFRR Topology Entry";
    leaf node-id {
      type inet:ipv4-address;
      description "IPFRR Topology Node ID";
    }
    leaf distance {
      type uint32;
      description "IPFRR Topology Distance";
    }
    leaf distance-reverse {
      type uint32;
      description "IPFRR Topology Reverse Distance";
    }
    leaf type4 {
      type boolean;
      description "IPFRR Topoogy Type-4 entry";
    }
    leaf revision {
      type uint32;
      description "IPFRR Topology Revision";
    }
    leaf neighbor-sourced {
      type boolean;
      description "IPFRR Topology Neighbor Sourced";
    }
    leaf dr {
      type boolean;
      description "IPFRR Topology DR entry";
    }
    leaf poison {
      type boolean;
      description "IPFRR Topology rSPT poison";
    }
  }

  grouping OSPF-SH-IPFRR-TOPO {
    description "OSPF IPFRR Topology Information";
    leaf ipfrr-topo-area-id {
      type string {
        length "0..16";
      }
      description
        "Area ID string in decimal or dotted decimal
        format";
    }
    leaf ipfrr-router-id {
      type inet:ipv4-address;
      description "OSPF Router ID";
    }
    leaf ipfrr-area-revision {
      type uint32;
      description "IPFRR Topology Revision";
    }

    list ipfrr-topo {
      description "IPFRR Topology entries";
      uses OSPF-SH-IPFRR-TOPO-ENTRY;
    }
  }

  grouping OSPF-SH-STATS-AGGT {
    description "OSPF SH STATS AGGT";
    leaf sa-num-nbrs {
      type uint32;
      description "sa num nbrs";
    }
    leaf sa-num-nbrs-up {
      type uint32;
      description "sa num nbrs up";
    }
    leaf sa-num-intf {
      type uint32;
      description "sa num intf";
    }
    leaf sa-num-intf-up {
      type uint32;
      description "sa num intf up";
    }
    leaf sa-num-vintf-up {
      type uint32;
      description "sa num vintf up";
    }
    leaf sa-num-slintf-up {
      type uint32;
      description "sa num slintf up";
    }
    leaf sa-num-areas {
      type uint32;
      description "sa num areas";
    }
    leaf sa-lsa-cnt-type-rtr {
      type uint32;
      description "sa lsa cnt type rtr";
    }
    leaf sa-lsa-cnt-type-net {
      type uint32;
      description "sa lsa cnt type net";
    }
    leaf sa-lsa-cnt-type-sum-net {
      type uint32;
      description "sa lsa cnt type sum net";
    }
    leaf sa-lsa-cnt-type-sum-asb {
      type uint32;
      description "sa lsa cnt type sum asb";
    }
    leaf sa-lsa-cnt-type-ase {
      type uint32;
      description "sa lsa cnt type ase";
    }
    leaf sa-lsa-cnt-type-mospf {
      type uint32;
      description "sa lsa cnt type mospf";
    }
    leaf sa-lsa-cnt-type-7ase {
      type uint32;
      description "sa lsa cnt type 7ase";
    }
    leaf sa-lsa-cnt-type-8-ignore {
      type uint32;
      description "sa lsa cnt type 8 ignore";
    }
    leaf sa-lsa-cnt-type-opq-link {
      type uint32;
      description "sa lsa cnt type opq link";
    }
    leaf sa-lsa-cnt-type-opq-area {
      type uint32;
      description "sa lsa cnt type opq area";
    }
    leaf sa-lsa-cnt-type-opq-as {
      type uint32;
      description "sa lsa cnt type opq as";
    }
  }

  grouping OSPF-SH-SUMMARY-ADDRESS {
    description "OSPF Summary Address";
    leaf summary-prefix {
      type inet:ipv4-address;
      description "Summary prefix";
    }
    leaf summary-mask {
      type inet:ipv4-address;
      description "Summary Netmask";
    }
    leaf summary-metric {
      type uint32;
      description "Cost of Summary";
    }
    leaf summary-metric-type {
      type Ex-metric;
      description "Type of Metric";
    }
    leaf summary-tag {
      type uint32;
      description "Tag associated with this summary prefix";
    }
  }

  grouping OSPF-SH-DB-AS-SUM {
    description "OSPF AS Scope LSA Database Summary counters";

    list as-lsa-counter {
      description "Summary counter for AS scope LSAs";
      uses OSPF-SH-DB-SUM-CNTR;
    }
  }

  grouping OSPF-SH-DB-SUM-CNTR {
    description "OSPF Summary counters for a type";
    leaf lsa-type {
      type Lsa;
      description "Type of LSAs";
    }
    leaf lsa-count {
      type int32;
      description "Number of LSAs of this type";
    }
    leaf lsa-delete-count {
      type int32;
      description "Number of deleted LSAs of this type";
    }
    leaf lsa-maxage-count {
      type int32;
      description "Number of MaxAged LSAs of this type";
    }
    leaf lsa-self-count {
      type int32;
      description "Number of self-generated LSAs";
    }
  }

  grouping OSPF-SH-DB-AREA-SUM {
    description "OSPF Area Scope Database Summary counters";
    leaf dbase-sum-area-id-string {
      type string {
        length "0..16";
      }
      description "Area id";
    }

    list area-lsa-counter {
      description "Summary counters for Area scope LSAs";
      uses OSPF-SH-DB-SUM-CNTR;
    }
  }

  grouping OSPF-SH-DATABASE {
    description "OSPF Database Information";

    container lsa-header {
      description "LSA header information";
      uses OSPF-SH-DB-HEADER;
    }
    leaf external-tag {
      type uint32;
      description "Route Tag";
    }
    leaf link-count {
      type uint16;
      description "Number of links";
    }
  }

  grouping OSPF-SH-LSA-OPQ-ELL {
    description
      "OSPF Opaque-area type 8 ExtendedLink LSA
      Information";

    list tlv {
      description "List of TLVs";
      uses OSPF-SH-OPQ-TLV;
    }
  }

  grouping OSPF-SH-LSA-OPQ-EPL {
    description
      "OSPF Opaque-area type 128 ExtendedPrefix LSA
      Information";

    list tlv {
      description "List of TLVs";
      uses OSPF-SH-OPQ-TLV;
    }
  }

  grouping OSPF-SH-SR-SID-STLV {
    description "OSPF PCE-Discovery PCE Scope SubTLV";
    leaf sr-sid-length {
      type uint16;
      description "Length of sub-TLV";
    }
    leaf sr-sid-value {
      type uint32;
      description "SID Value";
    }
  }

  grouping OSPF-SH-OPQ-RI-SR-RANGE-TLV {
    description "OSPF SR Range TLV";

    container sidtlv {
      description "SID sub-TLV";
      uses OSPF-SH-SR-SID-STLV;
    }
    leaf sr-range-length {
      type uint16;
      description "Length of TLV";
    }
    leaf sr-range-size {
      type uint32;
      description "SR Range Size";
    }
  }

  grouping OSPF-SH-OPQ-RI-SR-ALGO-TLV {
    description "OSPF SR Algorithm TLV";
    leaf sr-algo-length {
      type uint16;
      description "Length of TLV";
    }
    leaf sr-algo-value {
      type yang:hex-string;
      description "SR Algorithms";
    }
  }

  grouping OSPF-SH-OPQ-RI-PCED-SCOPE-STLV {
    description "OSPF PCE-Discovery PCE Scope SubTLV";
    leaf lbit {
      type boolean;
      description "L Bit";
    }
    leaf rbit {
      type boolean;
      description "R Bit";
    }
    leaf rd-bit {
      type boolean;
      description "Rd Bit";
    }
    leaf sbit {
      type boolean;
      description "S Bit";
    }
    leaf sd-bit {
      type boolean;
      description "Sd Bit";
    }
    leaf ybit {
      type boolean;
      description "Y Bit";
    }
    leaf pref-l {
      type uint8;
      description "Pref L";
    }
    leaf pref-r {
      type uint8;
      description "Pref R";
    }
    leaf pref-s {
      type uint8;
      description "Pref S";
    }
    leaf pref-y {
      type uint8;
      description "Pref Y";
    }
    leaf all-scope-info-bits {
      type uint32;
      description "PCE Scope Information";
    }
  }

  grouping OSPF-SH-OPQ-RI-PCE-IPV6-ADDR-STLV {
    description "PCE IPv6 Address SubTLV";
    leaf pceipv6-addr {
      type inet:ipv6-address;
      description "PCE IPv6 Address";
    }
  }

  grouping OSPF-SH-OPQ-RI-PCE-IPV4-ADDR-STLV {
    description "PCE IPv4 Address SubTLV";
    leaf pceipv4-addr {
      type inet:ipv4-address;
      description "PCE IPv4 Address";
    }
  }

  grouping OSPF-SH-OPQ-RI-PCE-ADDR-STLVS-UNION {
    description "OSPF PCE Address SubTLVs";

    container pce-addr-unknown-tlv {
      when "../pce-addr-type ="+
        " 'mgmt-ospf-opq-pce-addr-type-invalid'" {
          description
            "../PCEAddrType =
            'MGMT_OSPF_OPQ_PCE_ADDR_TYPE_INVALID'";
      }
      description "Unknown PCE Addr TLV";
      uses OSPF-SH-OPQ-RI-UNKNOWN-TLV;
    }

    container ipv4pce-addr {
      when "../pce-addr-type = 'mgmt-ospf-opq-pce-addr-type-ipv4'" {
        description
          "../PCEAddrType =
          'MGMT_OSPF_OPQ_PCE_ADDR_TYPE_IPV4'";
      }
      description "IPv4 PCE Address";
      uses OSPF-SH-OPQ-RI-PCE-IPV4-ADDR-STLV;
    }

    container ipv6pce-addr {
      when "../pce-addr-type = 'mgmt-ospf-opq-pce-addr-type-ipv6'" {
        description
          "../PCEAddrType =
          'MGMT_OSPF_OPQ_PCE_ADDR_TYPE_IPV6'";
      }
      description "IPv6 PCE Address";
      uses OSPF-SH-OPQ-RI-PCE-IPV6-ADDR-STLV;
    }
    leaf pce-addr-type {
      type Ospf-sh-opq-ri-pce-addr-types;
      description "PCEAddrType";
    }
  }

  grouping OSPF-SH-OPQ-RI-PCED-TLV {
    description "OSPF PCE Discovery TLV";

    container pced-addr {
      description "PCE Address";
      uses OSPF-SH-OPQ-RI-PCE-ADDR-STLVS-UNION;
    }

    container pced-scope {
      description "PCE Scope Information";
      uses OSPF-SH-OPQ-RI-PCED-SCOPE-STLV;
    }
    leaf pcedtlv-length {
      type uint16;
      description "Length of TLV";
    }
  }

  grouping OSPF-SH-OPQ-RI-RTRCAP-TLV {
    description "OSPF Router Capabilities TLV";
    leaf rtr-cap-tlv-length {
      type uint16;
      description "Length of TLV";
    }
    leaf rtr-cap-graceful-restart {
      type boolean;
      description "Graceful Restart Capability";
    }
    leaf rtr-cap-graceful-restart-helper {
      type boolean;
      description "Graceful Restart Helper Capability";
    }
    leaf rtr-cap-stub-rtr {
      type boolean;
      description "Stub Router capability";
    }
    leaf rtr-cap-area-te {
      type boolean;
      description "Traffic Engineering capability of area";
    }
    leaf rtr-cap-p2plan {
      type boolean;
      description "P2P LAN Capability";
    }
    leaf rtr-cap-te-exp {
      type boolean;
      description "TE Experimental bit";
    }
    leaf rtr-cap-all-bits {
      type uint32;
      description "All capability bits";
    }
    leaf rtr-cap-additional-info {
      type yang:hex-string;
      description "Additional Information in TLV";
    }
  }

  grouping OSPF-SH-OPQ-RI-UNKNOWN-TLV {
    description "OSPF Opaque Router Information TLV";
    leaf ri-gen-tlv-type {
      type uint16;
      description "Type of TLV";
    }
    leaf ri-gen-tlv-length {
      type uint16;
      description "Length of TLV";
    }
    leaf ri-genvalue {
      type yang:hex-string;
      description "Data in TLV";
    }
  }

  grouping OSPF-SH-OPQ-RI-TLVS-UNION {
    description "OSPF Router Information TLVs";

    container unknown-tlv {
      when "../ritlv-internal-type ="+
        " 'mgmt-ospf-opq-ri-tlv-type-unknown'" {
          description
            "../RITLVInternalType =
            'MGMT_OSPF_OPQ_RI_TLV_TYPE_UNKNOWN'";
      }
      description "Unknown Rtr Info TLV";
      uses OSPF-SH-OPQ-RI-UNKNOWN-TLV;
    }

    container rtr-cap-tlv {
      when "../ritlv-internal-type ="+
        " 'mgmt-ospf-opq-ri-tlv-type-rtrcap'" {
          description
            "../RITLVInternalType =
            'MGMT_OSPF_OPQ_RI_TLV_TYPE_RTRCAP'";
      }
      description "Rtr Cap TLV";
      uses OSPF-SH-OPQ-RI-RTRCAP-TLV;
    }

    container pcedtlv {
      when "../ritlv-internal-type ="+
        " 'mgmt-ospf-opq-ri-tlv-type-pce-discovery'" {
          description
            "../RITLVInternalType =
            'MGMT_OSPF_OPQ_RI_TLV_TYPE_PCEDISCOVERY'";
      }
      description "PCE Discovery TLV";
      uses OSPF-SH-OPQ-RI-PCED-TLV;
    }

    container sr-algo-tlv {
      when "../ritlv-internal-type ="+
        " 'mgmt-ospf-opq-ri-tlv-type-sr-algo'" {
          description
            "../RITLVInternalType =
            'MGMT_OSPF_OPQ_RI_TLV_TYPE_SR_ALGO'";
      }
      description "SR Algorithm TLV";
      uses OSPF-SH-OPQ-RI-SR-ALGO-TLV;
    }

    container sr-range-tlv {
      when "../ritlv-internal-type ="+
        " 'mgmt-ospf-opq-ri-tlv-type-sr-range'" {
          description
            "../RITLVInternalType =
            'MGMT_OSPF_OPQ_RI_TLV_TYPE_SR_RANGE'";
      }
      description "SR Range TLV";
      uses OSPF-SH-OPQ-RI-SR-RANGE-TLV;
    }
    leaf ritlv-internal-type {
      type Ospf-sh-opq-ri-tlv-types;
      description "RITLVInternalType";
    }
  }

  grouping OSPF-SH-LSA-OPQ-RI {
    description "OSPF Router Information LSA";
    leaf opaque-rilsa-scope {
      type Ospf-lsa-opq-ri-scope;
      description
        "Opaque LSA flooding scope, a.k.a., Opaque LSA
        Type";
    }
    leaf opaque-ri-interface-name {
      type xr:Interface-name;
      description
        "Interface on which this Link-Local Opaque link
        LSA is received";
    }

    list opaque-ritlv {
      description "Router Information TLV";
      uses OSPF-SH-OPQ-RI-TLVS-UNION;
    }
  }

  grouping OSPF-SH-LSA-OPQ-GRACE {
    description "OSPF Opaque-link type 3 grace LSA Information";
    leaf grace-period {
      type uint32;
      description
        "The amount of time the router's neighbor should
        advertise it fully adjacent (s)";
    }
    leaf grace-reason {
      type Ospf-gr-reason;
      description "Reason for router restart";
    }
    leaf ip-address {
      type inet:ipv4-address;
      description
        "IP interface address on the subnet associated
        with the grace LSA";
    }
  }

  grouping OSPF-SH-OPQ-SUBTLV {
    description "OSPF Opaque LSA Sub-TLV Information";
    leaf sub-tlv-type {
      type Stlv;
      description "Type of sub TLV";
    }
    leaf sub-tlv-length {
      type uint16;
      description "Length of sub TLV";
    }
    leaf sub-tlv-value {
      type yang:hex-string;
      description "Value of sub TLV";
    }
  }

  grouping OSPF-SH-OPQ-TLV {
    description "OSPF Opaque LSA TLV Information";
    leaf tlv-type {
      type uint16;
      description "Type of top-level TLV";
    }
    leaf tlv-length {
      type uint16;
      description "Length of top-level TLV";
    }
    leaf mpls-router-id {
      type uint32;
      description "MPLS-TE Router ID";
    }
    leaf mpls-dste-link {
      type boolean;
      description "MPLS DS-TE supported";
    }
    leaf tlv-data {
      type yang:hex-string;
      description "TLV direct data";
    }

    list te-link-sub-tlv {
      description "List of Sub-TLVs";
      uses OSPF-SH-OPQ-SUBTLV;
    }
  }

  grouping OSPF-SH-LSA-OPQ-RRR {
    description "OSPF Opaque-area type 1 MPLS-TE LSA Information";

    list tlv {
      description "List of TLVs";
      uses OSPF-SH-OPQ-TLV;
    }
  }

  grouping OSPF-SH-LSA-OPQ-LINK {
    description "OSPF Opaque-link LSA Information";
    leaf opaque-interface-name {
      type xr:Interface-name;
      description
        "Interface on which the Opaque link LSA is
        received";
    }
  }

  grouping OSPF-SH-LSA-EX-TOS {
    description
      "OSPF External Type of service specific
      Information";
    leaf external-metric {
      type uint32;
      description "Cost of this route";
    }
    leaf external-metric-type {
      type Ex-metric;
      description "External LSA metric type";
    }
    leaf external-tos {
      type uint32;
      description "Type of Service";
    }
    leaf forwarding-address {
      type inet:ipv4-address;
      description "Forwarding Address";
    }
    leaf external-tag {
      type uint32;
      description "Route Tag";
    }
  }

  grouping OSPF-SH-LSA-EXTERNAL {
    description "OSPF External LSA";
    leaf external-prefix-length {
      type uint32;
      description "Prefix length";
    }
    leaf internal-external-lsa {
      type boolean;
      description "If true, internal max-metric LSA";
    }

    list external-tos-metric {
      description "Type of service information";
      uses OSPF-SH-LSA-EX-TOS;
    }
  }

  grouping OSPF-SH-LSA-SUMMARY {
    description "OSPF Summary LSA";
    leaf summary-prefix-length {
      type uint32;
      description "Summary LSA prefix length";
    }
    leaf internal-sum-lsa {
      type boolean;
      description "If true, internal max-metric LSA";
    }
    leaf-list summary-lsa-metric {
      type uint32;
      description "Metric";
    }
  }

  grouping OSPF-SH-LSA-NETWORK {
    description "OSPF Network LSA";
    leaf network-prefix-length {
      type uint32;
      description "Network prefix length";
    }
    leaf-list neighbor-router {
      type inet:ipv4-address;
      description "Neighbor router list";
    }
  }

  grouping OSPF-SH-TOS-METRIC {
    description "OSPF Router LSA TOS Metric";
    leaf router-tos {
      type uint16;
      description "Type of Service";
    }
    leaf tos-cost {
      type uint16;
      description "Type of service specific metric";
    }
  }

  grouping OSPF-SH-LINK {
    description "OSPF Router LSA Links";
    leaf link-id {
      type inet:ipv4-address;
      description "Link ID";
    }
    leaf link-data {
      type inet:ipv4-address;
      description "Link Data";
    }
    leaf link-type {
      type Ospf-link-types;
      description "Type of link";
    }
    leaf link-metric {
      type uint16;
      description "Cost for using this link";
    }

    list link-tos {
      description "List of type of service metrics";
      uses OSPF-SH-TOS-METRIC;
    }
  }

  grouping OSPF-SH-LSA-ROUTER {
    description "OSPF Router LSA";
    leaf router-asbr {
      type boolean;
      description
        "If True, router is an Autonomous system Border
        Router";
    }
    leaf router-abr {
      type boolean;
      description "If True, router is an Area Border Router";
    }
    leaf internal-lsa {
      type boolean;
      description "If true, internal LSA";
    }

    list link {
      description "List of links in this LSA";
      uses OSPF-SH-LINK;
    }

    list internal-link {
      description "List of links for internal LSA";
      uses OSPF-SH-LINK;
    }
  }

  grouping OSPF-LSA-INTERNAL-UNION {
    description "LSA internal information for an LSA";

    container router-lsa-type {
      when "../internal-lsa-type = 'mgmt-rtr-type'" {
        description "../InternalLSAType = 'MGMT_RTR_TYPE'";
      }
      description "Router LSA";
      uses OSPF-SH-LSA-ROUTER;
    }

    container network-lsa-type {
      when "../internal-lsa-type = 'mgmt-ntwk-type'" {
        description "../InternalLSAType = 'MGMT_NTWK_TYPE'";
      }
      description "Network LSA";
      uses OSPF-SH-LSA-NETWORK;
    }

    container summary-lsa-type {
      when "../internal-lsa-type = 'mgmt-sum-type'" {
        description "../InternalLSAType = 'MGMT_SUM_TYPE'";
      }
      description "Summary LSA";
      uses OSPF-SH-LSA-SUMMARY;
    }

    container external-lsa-type {
      when "../internal-lsa-type = 'mgmt-ext-type'" {
        description "../InternalLSAType = 'MGMT_EXT_TYPE'";
      }
      description "External LSA";
      uses OSPF-SH-LSA-EXTERNAL;
    }

    container opaque-link-lsa-type {
      when "../internal-lsa-type = 'mgmt-opq-link-type'" {
        description "../InternalLSAType = 'MGMT_OPQ_LINK_TYPE'";
      }
      description "Opaque-Link LSA";
      uses OSPF-SH-LSA-OPQ-LINK;
    }

    container opaque-mpls-te-lsa-type {
      when "../internal-lsa-type = 'mgmt-opq-rrr-type'" {
        description "../InternalLSAType = 'MGMT_OPQ_RRR_TYPE'";
      }
      description "Opaque-Area, opaque type 1 LSA";
      uses OSPF-SH-LSA-OPQ-RRR;
    }

    container opaque-grace-lsa {
      when "../internal-lsa-type = 'mgmt-opq-gr-type'" {
        description "../InternalLSAType = 'MGMT_OPQ_GR_TYPE'";
      }
      description "Opaque-link, opaque type 3 Grace LSA";
      uses OSPF-SH-LSA-OPQ-GRACE;
    }

    container opaque-router-info-lsa-type {
      when "../internal-lsa-type = 'mgmt-opq-ri-type'" {
        description "../InternalLSAType = 'MGMT_OPQ_RI_TYPE'";
      }
      description "Opaque Router Information LSA";
      uses OSPF-SH-LSA-OPQ-RI;
    }

    container opaque-ep-lsa-type {
      when "../internal-lsa-type = 'mgmt-opq-epl-type'" {
        description "../InternalLSAType = 'MGMT_OPQ_EPL_TYPE'";
      }
      description "Extende Prefix LSA type";
      uses OSPF-SH-LSA-OPQ-EPL;
    }

    container opaque-el-lsa-type {
      when "../internal-lsa-type = 'mgmt-opq-ell-type'" {
        description "../InternalLSAType = 'MGMT_OPQ_ELL_TYPE'";
      }
      description "Extended Link LSA type";
      uses OSPF-SH-LSA-OPQ-ELL;
    }
    leaf internal-lsa-type {
      type Ospf-internal-lsa-types;
      description "InternalLSAType";
    }
  }

  grouping OSPF-SH-DB-NOT-DELETE {
    description "Reason why LSA is not deleted";
    leaf free-time {
      type uint32;
      description
        "The amount of time since the last check was made
        to free this LSA (s)";
    }
    leaf no-delete {
      type boolean;
      description
        "If true, the reason not to delete this LSA is
        because delete flag not set on this LSA";
    }
    leaf neighbor-exchange {
      type boolean;
      description
        "If true, the reason  not to delete this LSA is
        because neighbor is in exchange state";
    }
    leaf routing-table {
      type boolean;
      description
        "If true, the reason  not to delete this LSA is
        because it has a contributing entry in the
        routing table";
    }
    leaf acknowledgement {
      type boolean;
      description
        "If true, the reason not to delete this LSA is
        because it's Acknowledgement list is not empty";
    }
    leaf maximum-age {
      type boolean;
      description
        "If true, the reason not to delete this LSA is
        because it is in Maxage Queue";
    }
    leaf partial-spf {
      type boolean;
      description
        "If true, the reason not to delete this LSA is
        because it is in partial SPF queue";
    }
    leaf flood-pending {
      type boolean;
      description
        "If true, the reason not to delete this LSA is
        because waiting for flooding or retransmission";
    }
    leaf rate-limit {
      type boolean;
      description
        "If true, the reason not to delete this LSA is
        because waiting for next wait-interval to expire";
    }
    leaf nsr-ack-pending {
      type boolean;
      description
        "If true, the reason not to delete this LSA is
        because NSR ACK from standby is pending";
    }
    leaf sum-orig-pending {
      type boolean;
      description
        "If true, the reason not to delete this LSA is
        because it is pending summary LSA originating";
    }
    leaf nsr-flood-required {
      type boolean;
      description
        "If true, the reason not to delete this LSA is
        because it is pending flooding on switchover";
    }
  }

  grouping OSPF-SH-DB-THROTTLE-TIMER {
    description "OSPF LSA throttle timer table information";
    leaf timer-location {
      type Timer-table;
      description "Timer table";
    }
    leaf timer-type {
      type Timer;
      description "Timer type";
    }
    leaf second-table-index {
      type uint8;
      description "Second table index";
    }
    leaf minute-table-index {
      type uint8;
      description "Minute table index";
    }
    leaf last-inst-second-table-index {
      type uint8;
      description "Last Second table index processed";
    }
    leaf last-inst-minute-table-index {
      type uint8;
      description "Last Minute table index processed";
    }
  }

  grouping OSPF-SH-DB-DETAIL {
    description "OSPF Detailed LSA Database Information";

    container lsa-throttle-timer {
      description "LSA throttle timer table information";
      uses OSPF-SH-DB-THROTTLE-TIMER;
    }

    container lsa-last-updated-time {
      description "Time LSA was last updated";
      uses OSPF-SH-TIME;
    }

    container lsadb-base-time-stamp {
      description "Current time stamp";
      uses OSPF-SH-TIME;
    }

    container not-delete {
      description "Reason why LSA is not deleted";
      uses OSPF-SH-DB-NOT-DELETE;
    }
    leaf tos-capable {
      type boolean;
      description
        "If true, type of service capable indicated by
        LSA's option field";
    }
    leaf nssa-translation {
      type boolean;
      description
        "If true,  capable of type 7 to 5 translation
        indicated by LSA's option field";
    }
    leaf demand-circuit {
      type boolean;
      description
        "If true, capable of demand circuit as indicated
        by LSA's option field";
    }
    leaf dn-bit {
      type boolean;
      description
        "if true, DN bit set on the summary LSA indicated
        by LSA's option field";
    }
    leaf lsa-rate-limit-due-time {
      type uint32;
      description "Due time for rate-limit timer (ms)";
    }
    leaf lsadb-base-clock {
      type uint64;
      description "Clock stamp since boot";
    }
    leaf routing-bit {
      type boolean;
      description "If true, Routing Bit set on the LSA";
    }
    leaf advertising-router-reachable {
      type boolean;
      description "If true, Advertising Router is reachable";
    }
    leaf length {
      type uint16;
      description "Length of the LSA";
    }
    leaf sum-origin {
      type uint16;
      description "Summary Origin";
    }
    leaf ase-origin {
      type uint16;
      description "External Origin";
    }
    leaf in-sync {
      type uint8;
      description "Not In Sync With Active";
    }
    leaf lsa-prefix-priority {
      type uint8;
      description "Current LSA prefix priority";
    }
    leaf new-lsa-prefix-priority {
      type uint8;
      description "New LSA prefix priority";
    }
    leaf lsa-flood-required-post-fail-over {
      type boolean;
      description "LSA flood required after FO";
    }
  }

  grouping OSPF-SH-DB-HEADER {
    description "OSPF LSA Database Header";
    leaf ls-type {
      type Lsa;
      description "LSA type";
    }
    leaf lsid {
      type inet:ipv4-address;
      description "LS ID";
    }
    leaf advertising-router {
      type inet:ipv4-address;
      description "Router ID of Advertising Router";
    }
    leaf lsa-area-id {
      type string {
        length "0..16";
      }
      description "Area ID in decimal or dotted-decimal format";
    }
    leaf lsa-age {
      type uint16;
      description "LSA's Age (s)";
    }
    leaf dn-age-lsa {
      type boolean;
      description "If true, Do Not Age this LSA";
    }
    leaf nsf {
      type boolean;
      description "If true,  LSA received from neighbor during NSF";
    }
    leaf sequence-number {
      type uint32;
      description "Current Sequence number";
    }
    leaf checksum {
      type uint16;
      description "Checksum value";
    }
  }

  grouping OSPF-SH-DATABASE-DETAIL {
    description "OSPF Database Information";

    container lsa-header {
      description "Header information";
      uses OSPF-SH-DB-HEADER;
    }

    container lsa-detail-data {
      description "Detailed LSA Information";
      uses OSPF-SH-DB-DETAIL;
    }

    container lsa-internal-data {
      description "Information pertaining to a specific LSA type";
      uses OSPF-LSA-INTERNAL-UNION;
    }
  }

  grouping OSPF-SH-SLINK-NEIGHBOR {
    description "Sham Link Neighbor Information";

    container sham-link-retransmissoin {
      description "Neighbor retransmission info";
      uses OSPF-SH-NEIGHBOR-RETRANS;
    }
    leaf sham-link-suppress-hello {
      type boolean;
      description "If true Hellos suppressed";
    }
    leaf sham-link-state {
      type Neighbor-state;
      description "Adjacency state";
    }
  }

  grouping OSPF-SH-SHAM-LINKS {
    description "OSPF Sham Link";

    container sham-link-neighbor {
      description "Neighbor information";
      uses OSPF-SH-SLINK-NEIGHBOR;
    }
    leaf sham-link-name-xr {
      type string;
      description "Sham link name";
    }
    leaf sham-link-neighbor-id {
      type inet:ipv4-address;
      description "Neighbor on other end of this sham link";
    }
    leaf sham-link-source-address {
      type inet:ipv4-address;
      description "Sham-link source";
    }
    leaf sham-link-dest-address {
      type inet:ipv4-address;
      description "Sham-link dest";
    }
    leaf sham-link-state {
      type Ospf-interface-state;
      description "OSPF interface state for the sham link";
    }
    leaf sham-link-demand-circuit {
      type boolean;
      description "If true, the link runs as demand circuit";
    }
    leaf sham-link-dc-bitless-lsa {
      type uint32;
      description "Number of LSA's with demand circuit bit not set";
    }
    leaf sham-link-ifindex {
      type uint32;
      description "Sham-link ifindex";
    }
    leaf sham-link-area {
      type string;
      description "Area id";
    }
    leaf sham-link-cost {
      type uint16;
      description "Cost of the sham link";
    }
    leaf sham-link-transmission-delay {
      type uint16;
      units "second";
      description "Transmission delay in seconds";
    }
    leaf sham-link-hello-interval {
      type uint32;
      description "Hello interval (s)";
    }
    leaf sham-link-hello-interval-ms {
      type uint32;
      description "Hello interval (ms)";
    }
    leaf sham-link-dead-interval {
      type uint32;
      description "Dead interval (s)";
    }
    leaf sham-link-wait-interval {
      type uint32;
      description "Wait interval (s)";
    }
    leaf sham-link-retransmission-interval {
      type uint32;
      description "Retransmission interval (s)";
    }
    leaf sham-link-next-hello {
      type uint32;
      description "Time until next hello (s)";
    }
    leaf sham-link-next-hello-ms {
      type uint32;
      description "Time until next hello (ms)";
    }
    leaf sham-link-passive {
      type boolean;
      description "If true, interface is passive";
    }
    leaf sham-link-authentication-type {
      type Authentication;
      description "Authentication type";
    }
    leaf sham-link-youngest-md-key {
      type boolean;
      description "If true, MD key configured";
    }
    leaf sham-link-youngest-md-key-id {
      type uint16;
      description "Youngest MD key ID";
    }
    leaf sham-link-old-md-key-count {
      type uint32;
      description
        "Number of neighbors still using the old key
        (rollover in progress)";
    }
    leaf sham-link-keychain-id {
      type uint64;
      description "Sham Link Keychain ID";
    }
    leaf sham-link-nsf-enabled {
      type boolean;
      description "If true, NSF enabled";
    }
    leaf sham-link-nsf {
      type boolean;
      description
        "If true, NSF restart in progress on the sham
        link";
    }
    leaf sham-link-last-nsf {
      type uint32;
      units "second";
      description "Time in seconds since last NSF";
    }
    leaf-list sham-link-md-key {
      type uint16;
      description "List of old MD keys (if any)";
    }
  }

  grouping OSPF-SH-DOMAIN-ID-ENTRY {
    description "OSPF Domain ID";
    leaf domain-id-type {
      type uint16;
      description "Domain ID Type";
    }
    leaf domain-id-value {
      type yang:hex-string;
      description "Domain ID value";
    }
  }

  grouping OSPF-SH-DOMAIN-ID {
    description "OSPF Domain ID entries";

    container primary-domain-id {
      description "Primary Domain ID";
      uses OSPF-SH-DOMAIN-ID-ENTRY;
    }

    list secondary-domain-id {
      description "List of secondary domain IDs";
      uses OSPF-SH-DOMAIN-ID-ENTRY;
    }
  }

  grouping OSPF-SH-MAX-METRIC {
    description "OSPF Max-metric Information";

    container maximum-metric-time-unset {
      description "Time max-metric condition was cleared";
      uses OSPF-SH-TIME;
    }
    leaf max-metric-reason {
      type uint8;
      description "Max-metric reason";
    }
    leaf max-metric-enabled {
      type boolean;
      description "Max-metric enabled";
    }
    leaf unset-maximum-metric {
      type boolean;
      description
        "If true, BGP is up, no maximum metric Router LSA";
    }
    leaf saved-unset-maximum-metric {
      type boolean;
      description "Saved UnsetMaximumMetric";
    }
    leaf maximum-metric-start-time {
      type uint32;
      description
        "Time remaining until we will start using normal
        metrics (s)";
    }
    leaf saved-startup-time {
      type uint32;
      description "Hold time configured (s)";
    }
    leaf maximum-metric-include-stubs {
      type boolean;
      description "If true, set max-metric in stub links";
    }
    leaf maximum-metric-summary-lsa {
      type boolean;
      description "If true, advertise max-metric in summary-LSAs";
    }
    leaf maximum-metric-summary-lsa-metric {
      type uint32;
      description "Max-metric value to advertise in summary-LSAs";
    }
    leaf maximum-metric-external-lsa {
      type boolean;
      description "If true, advertise max-metric in external-LSAs";
    }
    leaf maximum-metric-external-lsa-metric {
      type uint32;
      description "Max-metric value to advertise in external-LSAs";
    }
    leaf maximum-metric-originated-for {
      type uint32;
      description "Time max-metric was used for";
    }
    leaf maximum-metric-unset-reason {
      type Max-metric-unset-reason;
      description "Max-metric unset reason";
    }
  }

  grouping OSPF-SH-SUMMARY {
    description "OSPF Summary";

    container domain-id {
      description "Domain ID information";
      uses OSPF-SH-DOMAIN-ID;
    }
    leaf role-standby {
      type boolean;
      description "If true, Role is Standby, Active otherwise";
    }
    leaf role {
      type uint32;
      description "Role, V1/V2 Active/Standby";
    }
    leaf nsr-enabled {
      type boolean;
      description "If true, NSR is enabled";
    }
    leaf nsr-switchover-on-restart {
      type boolean;
      description
        "Trigger RP Switchover on detectable process
        restart";
    }
    leaf igp-intact-on {
      type boolean;
      description "If true, running in IGP-Intact mode";
    }
    leaf router-id {
      type inet:ipv4-address;
      description "Router ID";
    }
    leaf tos-options {
      type uint8;
      description "Type of Service supported";
    }
    leaf opaque-capable {
      type boolean;
      description "Opaque LSA capable";
    }
    leaf area-border-router {
      type boolean;
      description "If true, is an Area Border Router";
    }
    leaf as-border-router {
      type boolean;
      description "If true, is an AS Border Router";
    }
    leaf vrf-lite-enabled {
      type boolean;
      description "If true, vrf lite is enabled";
    }
    leaf maximum-metric-start {
      type boolean;
      description
        "If true, originate Router LSA with maximum
        metric";
    }
    leaf maximum-metric-start-timer {
      type uint32;
      description "Time remaining for hold down timer (s)";
    }
    leaf maximum-metric-set-reason {
      type Max-metric-set-reason;
      description "Max-metric set reason";
    }
    leaf maximum-metric-abr-off-mode {
      type boolean;
      description "If true, ABR duties temporarily disabled";
    }
    leaf maximum-metric-abr-off-reasons {
      type Ospf-max-metric-abr-off-reasons;
      description
        "Reasons for ABR duties being temporarily
        disabled";
    }
    leaf maximum-metric-abr-off-buffer-time {
      type uint32;
      units "second";
      description
        "Buffer time in seconds since last neighbor
        activity, to remain in max-metric ABR off state";
    }
    leaf spf-start-time {
      type uint16;
      description
        "Scheduling delay for SPF (ms) This is valid if
        configured below 64k Deprecated by
        SPFStartTimeU32]";
    }
    leaf spf-hold-time {
      type uint16;
      description
        "Minimum delay time between SPF runs (ms) This is
        valid if configured below 64k Deprecated by
        SPFHoldTimeU32]";
    }
    leaf spf-maximum-time {
      type uint16;
      description
        "Maximum delay time between SPF runs (ms) This is
        valid if configured below 64k Deprecated by
        SPFMaximumTimeU32]";
    }
    leaf spf-start-time-u32 {
      type uint32;
      description "Scheduling delay for SPF (ms)";
    }
    leaf spf-hold-time-u32 {
      type uint32;
      description "Minimum delay time between SPF runs (ms)";
    }
    leaf spf-maximum-time-u32 {
      type uint32;
      description "Maximum delay time between SPF runs (ms)";
    }
    leaf spf-prefix-priority {
      type boolean;
      description "If true, prefix-priority policy is configured";
    }
    leaf spf-prefix-priority-route-policy {
      type string;
      description "SPF Prefix-priority route policy";
    }
    leaf lsa-start-time {
      type int32;
      description "Inital LSA throttle delay (ms)";
    }
    leaf lsa-hold-time {
      type uint32;
      description "Second delay before generating next LSA (ms)";
    }
    leaf lsa-maximum-time {
      type uint32;
      description "Maximum delay before generating an LSA (ms)";
    }
    leaf minimum-lsa-interval {
      type uint16;
      description
        "Minimum time between LSA regeneration (ms) Rel 4
        .0.1, deprecated by MinimumLSAIntervalU32]";
    }
    leaf minimum-lsa-interval-u32 {
      type uint32;
      description "Minimum time between LSA regeneration (ms)";
    }
    leaf lsa-refresh-interval {
      type uint32;
      description "LSA refresh interval (sec)";
    }
    leaf minimum-lsa-arrival-interval {
      type uint16;
      description
        "Minimum time between accepting LSAs (ms) Rel 4.0
        .1, deprecated by MinimumLSAArrivalIntervalU32]";
    }
    leaf minimum-lsa-arrival-interval-u32 {
      type uint32;
      description "Minimum time between accepting LSAs (ms)";
    }
    leaf if-flood-pacing-interval {
      type uint16;
      description "Flood pacing timer (ms)";
    }
    leaf if-retrans-pacing-interval {
      type uint16;
      description "Retransmission pacing timer (ms)";
    }
    leaf adj-stag-init-num-nbr {
      type uint16;
      description "Num of nbrs brought up initially per area";
    }
    leaf adj-stag-max-num-nbr {
      type uint16;
      description
        "Max num of nbrs brought up simultaneously per
        OSPF instance";
    }
    leaf adj-stagger-enabled {
      type boolean;
      description
        "If true, OSPF Adjacency Staggering is configured";
    }
    leaf adj-stag-num-nbr-forming {
      type uint16;
      description "Num of nbrs currently forming for OSPF instance";
    }
    leaf number-nbrs-full {
      type uint16;
      description "Num of full nbrs";
    }
    leaf as-lsa-count {
      type uint32;
      description "Number of AS scope LSAs";
    }
    leaf as-lsa-checksum {
      type uint32;
      description "Sum of AS scope LSA checksum";
    }
    leaf opaque-lsa-count {
      type uint32;
      description "Number of Opaque LSAs";
    }
    leaf opaque-lsa-checksum {
      type uint32;
      description "Sum of opaque LSA checksum";
    }
    leaf as-dc-bitless-lsa-count {
      type uint32;
      description
        "Number of External and AS Opaque LSAs with
        demand circut bit not set";
    }
    leaf as-dna-lsa-count {
      type uint32;
      description
        "Number of External and AS Opaque LSAs with
        DoNotAge set ";
    }
    leaf area-count {
      type uint16;
      description "Number of areas";
    }
    leaf normal-area-count {
      type uint16;
      description "Number of normal Areas";
    }
    leaf stub-area-count {
      type uint16;
      description "Number of Stub and Total Stub Areas";
    }
    leaf nssa-area-count {
      type uint16;
      description "Number of NSSA Areas";
    }
    leaf maximum-interfaces {
      type uint32;
      description "Maximum number of interfaces";
    }
    leaf as-lsa-flood-list-length {
      type uint32;
      description "Length of AS LSAs flood list";
    }
    leaf nsf-enabled {
      type boolean;
      description "If true, NSF enabled";
    }
    leaf last-nsf-time {
      type uint32;
      description " Length of time since the last NSF (s)";
    }
    leaf nsf-time {
      type uint32;
      description "Total time to complete NSF (s)";
    }
    leaf redistribution-limit {
      type uint32;
      description "The number of redistributed prefixes allowed";
    }
    leaf redistribution-threshold {
      type uint32;
      description
        "When the number of redistributed prefixes
        reaches this threshold, a warning message is
        issued";
    }
    leaf redistribution-limit-warn {
      type boolean;
      description
        "If true, only a syslog message is printed when
        redistribution prefix limit is reached";
    }
    leaf graceful-shutdown-retention-time {
      type uint32;
      description
        "Amount of time routes are retained after
        graceful shutdown (s)";
    }
    leaf graceful-shutdown-state {
      type Gs-state;
      description "State of graceful shutdown";
    }
    leaf table-prefix-limit-reached {
      type boolean;
      description
        "If true, prefix limit for table has been 
        reached";
    }
    leaf non-self-lsa-count {
      type uint32;
      description "Non self-generated LSA count";
    }
    leaf max-lsa-enabled {
      type boolean;
      description "If true, max-lsa protection enabled";
    }
    leaf max-lsa-limit {
      type uint32;
      description
        "Maximum allowed number of non self-generated
        LSAs";
    }
    leaf max-lsa-treshold {
      type uint32;
      description "max-lsa protection warning threshold";
    }
    leaf max-lsa-warning-only {
      type boolean;
      description "Warning only when max-lsa reached";
    }
    leaf max-lsa-ignore-time {
      type uint32;
      description "Time ignoring new LSAs after max-lsa reached";
    }
    leaf max-lsa-reset-time {
      type uint32;
      description
        "Time after which LSA protection counter is reset";
    }
    leaf max-lsa-ignore-limit {
      type uint32;
      description "Max allowed number of entering ignore state";
    }
    leaf max-lsa-ignore-count {
      type uint32;
      description "How many times ignore state has been entered";
    }
    leaf max-lsa-ignore-timer {
      type uint32;
      description "Remaining time when ignore timer is running";
    }
    leaf max-lsa-reset-timer {
      type uint32;
      description "Remaining time when reset timer is running";
    }
    leaf context-name {
      type string {
        length "0..32";
      }
      description "Context name";
    }
    leaf snmp-trap-enabled {
      type boolean;
      description "If true, snmp trap is enabled";
    }
    leaf ucmp {
      type boolean;
      description "If true, UCMP is enabled";
    }
    leaf ucmp-prefix-list {
      type string;
      description "UCMP Prefix-list";
    }
    leaf ucmp-variance {
      type int32;
      description "UCMP Variance";
    }
    leaf ucmp-delay {
      type uint32;
      description
        "Delay between end of SPF and start of UCMP
        calculation (ms)";
    }
    leaf microloop-avoidance-type {
      type Uloop-avoidance;
      description "Microloop avoidance type configured";
    }
    leaf microloop-avoidance-delay {
      type uint32;
      description
        "Microloop delay time after which actual         
        post convergence paths are given to RIB (s)";
    }
    leaf microloop-avoidance-active {
      type boolean;
      description "If true, Uloop is active";
    }
    leaf microloop-avoidance-delay-expiry {
      type uint32;
      description
        "Remaining time for uloop delay timer            
        to expire (s)";
    }
    leaf lsd-connected {
      type boolean;
      description "True if connected to LSD";
    }
    leaf lsd-registered {
      type boolean;
      description "True if registered with LSD";
    }
    leaf lsd-bound {
      type boolean;
      description "True if bound to LSD";
    }
    leaf lsd-connection-revision {
      type uint32;
      description "LSD Connection Revision";
    }
    leaf srgb-configured {
      type boolean;
      description "True if Segment Routing Global Block configured";
    }
    leaf srgb-start {
      type uint32;
      description "Segment Routing Global Block start label value";
    }
    leaf srgb-end {
      type uint32;
      description "Segment Routing Global Block end label value";
    }
    leaf srgb-status {
      type Ospf-srgb-status;
      description "Segment Routing Global Block allocation status";
    }
    leaf sr-strict-spf-cap {
      type boolean;
      description "True if Segment Routing Strict-SPF capable";
    }

    list maximum-metric {
      description "Max-metric list";
      uses OSPF-SH-MAX-METRIC;
    }

    list redistribution {
      description "Redistribution list";
      uses OSPF-SH-REDIST;
    }
  }

  grouping OSPF-SH-AREA-RANGE {
    description "OSPF Area Range Information";
    leaf range-prefix {
      type inet:ipv4-address;
      description "IP prefix for summarization";
    }
    leaf range-mask {
      type inet:ipv4-address;
      description "Network mask";
    }
    leaf cost {
      type uint32;
      description "Cost";
    }
    leaf advertise-flag {
      type boolean;
      description
        "Whether to advertise Summary LSAs for this range";
    }
  }

  grouping OSPF-SH-AREA {
    description "OSPF Area Summary Information";
    leaf area-id-string {
      type string {
        length "0..16";
      }
      description "Area ID string";
    }
    leaf backbone-area-active {
      type boolean;
      description "If true, Backbone area is active";
    }
    leaf area-interface-count {
      type uint16;
      description "Number of interfaces in the area";
    }
    leaf area-stub {
      type boolean;
      description "If true, stub area";
    }
    leaf area-total-stub {
      type boolean;
      description "If true, totally stubby area";
    }
    leaf stub-default-cost {
      type uint16;
      description "Default cost for Stub or NSSA area";
    }
    leaf area-nssa {
      type boolean;
      description "If true, area is a NSSA";
    }
    leaf nssa-no-redistribution {
      type boolean;
      description "If true, No redistribution into this NSSA area";
    }
    leaf nssa-translate {
      type boolean;
      description "If true, perform 7/5 translation";
    }
    leaf nssa-default {
      type boolean;
      description "If true, generate NSSA default route";
    }
    leaf te-enabled {
      type boolean;
      description "If true, MPLS-TE enabled";
    }
    leaf te-topology-version {
      type uint32;
      description "TE area topology version number";
    }
    leaf external-out {
      type boolean;
      description
        "If true, advertise intra-area prefixes as
        external";
    }
    leaf summary-in {
      type boolean;
      description
        "If true, advertise redistributedprefixes as
        summary";
    }
    leaf segment-routing {
      type uint32;
      description "If true, Segment Routing enabled";
    }
    leaf sr-strict-spf-cap {
      type boolean;
      description
        "If true, All routers in Area are SR Strict-SPF
        Capable";
    }
    leaf sr-strict-spfsids-available {
      type boolean;
      description
        "If true, All routers in Area have SR Strict-SPF
        SIDs";
    }
    leaf sr-microloop-avoidance-active {
      type boolean;
      description
        "If true, Segment routing Uloop avoidance        
        is currently active in this area";
    }
    leaf sr-microloop-avoidance-event-type {
      type Sr-uloop-event;
      description
        "Event for which SR uloop is triggered           
        Link Up/Link Down";
    }
    leaf sr-microloop-avoidance-near-end-id {
      type inet:ipv4-address;
      description
        "Link State ID of the near end                   
        of the topology change";
    }
    leaf sr-microloop-avoidance-far-end-id {
      type inet:ipv4-address;
      description
        "Link State ID of the far end                    
        of the topology change";
    }
    leaf sr-microloop-avoidance-pseudonode-id {
      type inet:ipv4-address;
      description
        "Link State ID of the pseudo node,               
        if the change is on a broadcast link";
    }
    leaf authentication-type {
      type Authentication;
      description "Authentication type";
    }
    leaf spf-count {
      type uint32;
      description "Number of SPF calculations run";
    }
    leaf area-policy-in {
      type boolean;
      description "If true, inbound policy is configured";
    }
    leaf area-policy-in-name {
      type string;
      description "Inbound summary lsa filtering policy";
    }
    leaf area-policy-out {
      type boolean;
      description "If true, outbound policy is configured";
    }
    leaf area-policy-out-name {
      type string;
      description "Outbound summary lsa filtering policy";
    }
    leaf area-lsa-count {
      type uint32;
      description "Number of LSAs in the Area";
    }
    leaf area-lsa-checksum {
      type uint32;
      description "Sum of all area LSAs checksum";
    }
    leaf area-opaque-lsa-count {
      type uint32;
      description "Number of Opaque LSAs in the Area";
    }
    leaf area-opaque-lsa-checksum {
      type uint32;
      description "Sum of opaque LSA checksums";
    }
    leaf area-dc-bitless-lsa-count {
      type uint32;
      description "Number of LSA with demand circuit bit not set";
    }
    leaf indication-lsa-count {
      type uint32;
      description "Number of indication LSAs";
    }
    leaf dna-lsa-count {
      type uint32;
      description "Number of DoNotAge LSAs";
    }
    leaf flood-list-length {
      type uint32;
      description "Number of LSAs which need to be flooded";
    }
    leaf area-lfa-interface-count {
      type uint32;
      description "Number of LFA enabled interfaces";
    }
    leaf area-per-prefix-lfa-interface-count {
      type uint32;
      description "Number of Per Prefix LFA enabled interfaces";
    }
    leaf area-lfa-revision {
      type uint32;
      description "Area LFA revision";
    }
    leaf area-adj-stag-num-nbr-forming {
      type uint16;
      description "Num of nbrs currently forming";
    }
    leaf area-num-nbr-full {
      type uint16;
      description "Num of full nbrs in area";
    }

    list area-range {
      description "List of ranges to summarize";
      uses OSPF-SH-AREA-RANGE;
    }
  }

  grouping OSPF-SH-REDIST {
    description "OSPF Redistribution Information";

    container redistribution-protocol {
      description "Protocol Information";
      uses OSPF-SH-REDIST-PROTO;
    }
    leaf metric-flag {
      type boolean;
      description "If true, Metric configured";
    }
    leaf metric {
      type uint32;
      description "Route metric";
    }
    leaf classless {
      type boolean;
      description "Whether to use CIDR";
    }
    leaf nssa-only {
      type boolean;
      description "To NSSA areas only";
    }
  }

  grouping OSPF-SH-PROTOCOL {
    description "OSPF Protocol Information";
    leaf protocol-router-id {
      type inet:ipv4-address;
      description "Router ID";
    }
    leaf protocol-distance {
      type uint32;
      description "Administrative distance";
    }
    leaf administrative-distance-inter-area {
      type uint32;
      description "Administrative Distance for Inter Area routes";
    }
    leaf administrative-distance-external {
      type uint32;
      description "Administrative Distance for External routes";
    }
    leaf protocol-nsf {
      type boolean;
      description "True if NSF enabled";
    }
    leaf dist-list-in {
      type string;
      description "Distribute List In";
    }
  }

  grouping OSPF-SH-PROTO-INTF {
    description "OSPF Protocol Interface Information";
    leaf protocol-interface-name {
      type xr:Interface-name;
      description "Interface";
    }
    leaf protocol-authentication-type {
      type Authentication;
      description "Authentication type";
    }
    leaf protocol-interface-dist-list-in {
      type string;
      description "Distribute List In";
    }
  }

  grouping OSPF-SH-PROTO-AREA {
    description "OSPF Protocol Area Information";
    leaf protcol-area {
      type string {
        length "0..16";
      }
      description
        "Area ID string in decimal and dotted-decimal
        format";
    }
    leaf protocol-mpls {
      type boolean;
      description "MPLS-TE enabled";
    }
    leaf protocol-area-dist-list-in {
      type string;
      description "Distribute List In";
    }

    list protocol-interface {
      description "Interface list";
      uses OSPF-SH-PROTO-INTF;
    }
  }

  grouping OSPF-SH-BR-PATH {
    description "OSPF Border Router Path";
    leaf border-router-route-type {
      type Ospf-route;
      description "Route type";
    }
    leaf border-router-route-metric {
      type uint32;
      description "Metric";
    }
    leaf border-router-next-hop {
      type inet:ipv4-address;
      description "Next hop address";
    }
    leaf border-router-next-hop-interface-name {
      type xr:Interface-name;
      description "Next hop Interface";
    }
    leaf border-router-type {
      type Ospf-br;
      description "Border router type";
    }
    leaf border-router-area-id {
      type string {
        length "0..16";
      }
      description "Area string in decimal or dotted-decimal format";
    }
    leaf spf-version {
      type uint64;
      description "SPF run instance count";
    }
  }

  grouping OSPF-SH-BORDER-ROUTER {
    description "OSPF Border Router";
    leaf border-router-id-xr {
      type inet:ipv4-address;
      description "Router ID of Border Router";
    }

    list border-router-path {
      description "List of Border Router paths";
      uses OSPF-SH-BR-PATH;
    }
  }

  grouping OSPF-SH-IPFRR-TB {
    description "OSPF IPFRR Tiebreakers";
    leaf tiebreaker-type {
      type Ipfrr-tbrkr;
      description "Tiebreaker Type";
    }
    leaf tiebreaker-index {
      type uint32;
      description "Tiebreaker Index";
    }
  }

  grouping OSPF-SH-INTERFACE-UP {
    description "OSPF Interface Up-only Information";
    leaf wait-time {
      type uint32;
      description "Wait time for DR/BDR selection (s)";
    }
    leaf interface-area-flood-index {
      type uint32;
      description "Area scope LSAs flood index";
    }
    leaf interface-as-flood-index {
      type uint32;
      description "AS scope LSAs flood index";
    }
    leaf interface-flood-length {
      type uint32;
      description "Flood queue length";
    }
    leaf interface-area-next-flood {
      type uint32;
      description "Next LSA to flood (Area scope)";
    }
    leaf interface-area-next-flood-index {
      type uint32;
      description "Index of next LSA to flood (Area scope)";
    }
    leaf interface-as-next-flood {
      type uint32;
      description "Next LSA to flood (AS scope)";
    }
    leaf interface-as-next-flood-index {
      type uint32;
      description "Index of next LSA to flood (AS scope)";
    }
    leaf flood-scan-length {
      type uint32;
      description "Last flood scan length";
    }
    leaf maximum-flood-length {
      type uint32;
      description "Maximum flood length";
    }
    leaf last-flood-time {
      type uint32;
      description "Last flood scan time (ms)";
    }
    leaf maximum-flood-time {
      type uint32;
      description "Maximum flood time (ms)";
    }
    leaf interface-flood-pacing-timer {
      type uint32;
      description "Time until next flood pacing timer (ms)";
    }
    leaf interface-neighbor-count {
      type uint16;
      description "Total number of Neighbors";
    }
    leaf suppress-hello-count {
      type uint16;
      description
        "Number of neighbors for which hellos are
        suppressed";
    }
    leaf interface-authentication-type {
      type Authentication;
      description "Authentication type";
    }
    leaf youngest-md-key {
      type boolean;
      description "If true, MD key is configured";
    }
    leaf old-md5-key-neighbor-count {
      type uint32;
      description
        "Number of neighbors using the old key (if
        rollover in progress)";
    }
    leaf youngest-md-key-id {
      type uint16;
      description "Youngest MD key ID";
    }
    leaf keychain-id {
      type uint64;
      description "Keychain ID";
    }
    leaf-list md-keys {
      type uint16;
      description "List of old MD keys";
    }
  }

  grouping OSPF-SH-INTERFACE-BFD {
    description "Interface BFD information";
    leaf bfd-intf-enable-mode {
      type uint32;
      description "BFD enable mode - Default/Strict";
    }
    leaf interval {
      type uint32;
      description "BFD interval (ms)";
    }
    leaf detection-multiplier {
      type uint32;
      description "BFD detection multiplier";
    }
  }

  grouping OSPF-SH-INTERFACE-NBR {
    description "OSPF Interface Neighbor Information";
    leaf interface-neighbor-id {
      type inet:ipv4-address;
      description "Neighbor Router ID";
    }
    leaf interface-neighbor-cost {
      type uint32;
      description "Cost of link to neighbor";
    }
    leaf neighbor-dr {
      type boolean;
      description "If true, Designated router";
    }
    leaf neighbor-bdr {
      type boolean;
      description "If true, Backup designated router";
    }
    leaf suppress-hello {
      type boolean;
      description "If true, hellos suppressed";
    }
  }

  grouping OSPF-SH-INTERFACE {
    description "OSPF Interface Information";

    container interface-bfd-information {
      description "BFD information";
      uses OSPF-SH-INTERFACE-BFD;
    }

    container active-interface {
      description "Active interface details";
      uses OSPF-SH-INTERFACE-UP;
    }
    leaf interface-name-xr {
      type xr:Interface-name;
      description "Interface";
    }
    leaf interface-state {
      type Interface-state;
      description "Interface state";
    }
    leaf interface-line-state {
      type boolean;
      description "If true, line protocol is up";
    }
    leaf interface-address {
      type inet:ipv4-address;
      description "Interface IP Address";
    }
    leaf interface-mask {
      type uint32;
      description "Interface IP Mask";
    }
    leaf interface-area {
      type string {
        length "0..16";
      }
      description
        "Area ID string in decimal or dotted-decimal
        format";
    }
    leaf interface-sid {
      type uint32;
      description "Interface SID";
    }
    leaf interface-sid-php-off {
      type boolean;
      description "SID PHP Off";
    }
    leaf interface-sid-n-flag-clear {
      type boolean;
      description "SID N-Flag Clear";
    }
    leaf interface-strict-spf-sid {
      type uint32;
      description "Interface Strict-SPF SID";
    }
    leaf interface-strict-spf-sid-php-off {
      type boolean;
      description "Strict-SPF SID PHP Off";
    }
    leaf interface-strict-spf-sid-n-flag-clear {
      type boolean;
      description "Strict-SPF SID N-Flag Clear";
    }
    leaf interface-router-id {
      type inet:ipv4-address;
      description "Interface Router ID";
    }
    leaf network-type {
      type Interface;
      description "Network type";
    }
    leaf ip-mtu {
      type uint16;
      description "IP MTU";
    }
    leaf maximum-packet-size {
      type uint16;
      description "Maximum Packet Size";
    }
    leaf interface-tunnel-flags {
      type uint32;
      description "Interface tunnel flags";
    }
    leaf interface-link-cost {
      type uint16;
      description "Interface link cost";
    }
    leaf interface-bandwidth {
      type uint32;
      description "Interface bandwidth";
    }
    leaf cfg-cost-fallback {
      type boolean;
      description "If true, cost fallback is configured";
    }
    leaf interface-cost-fallback {
      type uint16;
      description "Interface fallback cost";
    }
    leaf cost-fallback-active {
      type boolean;
      description "If true, cost fallback is active";
    }
    leaf configured-ldp-sync {
      type boolean;
      description "If true, configured as LDP sync";
    }
    leaf configured-ldp-sync-igp-shortcuts {
      type boolean;
      description "If true, sync igp shortcuts";
    }
    leaf interface-ldp-sync {
      type boolean;
      description "If true, interface LDP sync is achieved";
    }
    leaf configured-demand-circuit {
      type boolean;
      description "If true, configured as demand circuit";
    }
    leaf interface-demand-circuit {
      type boolean;
      description "If true, interface running as demand circuit";
    }
    leaf interface-dc-bitless-lsa-count {
      type uint32;
      description
        "Number of LSAs with demand circuit bit not set
        for the area in which the interface is running";
    }
    leaf transmission-delay {
      type uint16;
      description "Interface Transmission delay";
    }
    leaf ospf-interface-state {
      type Ospf-interface-state;
      description "Interface OSPF state";
    }
    leaf interface-priority {
      type uint8;
      description "Interface priority";
    }
    leaf designated-router {
      type boolean;
      description "If true, designated router";
    }
    leaf designated-router-id {
      type inet:ipv4-address;
      description "Designated router ID";
    }
    leaf designated-router-address {
      type inet:ipv4-address;
      description "Designated router interface address";
    }
    leaf backup-designated-router {
      type boolean;
      description "If true, backup designated router";
    }
    leaf backup-designated-router-id {
      type inet:ipv4-address;
      description "Backup designated router ID";
    }
    leaf backup-designated-router-address {
      type inet:ipv4-address;
      description "Backup designated router interface address";
    }
    leaf network-lsa-flush-timer {
      type uint32;
      units "second";
      description
        "The amount of time in seconds before flush timer
        for old network LSA expires";
    }
    leaf interface-lsa-filter {
      type boolean;
      description "Filter is configured for out going LSAs";
    }
    leaf hello-interval {
      type uint32;
      description "Configured hello interval (s)";
    }
    leaf hello-interval-ms {
      type uint32;
      description "Configured hello interval (ms)";
    }
    leaf dead-interval {
      type uint32;
      description "Configured dead interval (s)";
    }
    leaf wait-interval {
      type uint32;
      description "Configured wait interval (s)";
    }
    leaf interface-retransmission-interrval {
      type uint32;
      description "Configured retransmit interval (s)";
    }
    leaf interface-nsf-enabled {
      type boolean;
      description "If true, NSF is enabled";
    }
    leaf interface-nsf {
      type boolean;
      description
        "If true, NSF restart in progress on this
        interface";
    }
    leaf interface-last-nsf {
      type uint32;
      description "Time since last NSF restart (s)";
    }
    leaf passive-interface {
      type boolean;
      description "If true, passive interface";
    }
    leaf next-hello-time {
      type uint32;
      description "Time until next Hello (s)";
    }
    leaf next-hello-time-ms {
      type uint32;
      description "Time until next Hello (ms)";
    }
    leaf ttl-security-enabled {
      type boolean;
      description "TTL security enabled on the interface";
    }
    leaf ttl-security-hop-count {
      type uint32;
      description "TTL security hop counts";
    }
    leaf interfaceis-madj {
      type boolean;
      description "If true, interface is multi-area";
    }
    leaf interface-madj-count {
      type uint16;
      description "Total number of multi-area";
    }
    leaf prefix-suppress-primary-addresses {
      type boolean;
      description "Prefix Suppression for primary addresses";
    }
    leaf prefix-suppress-secondary-addresses {
      type boolean;
      description "Prefix Suppression for secondary addresses";
    }
    leaf is-loopback-stub-network {
      type boolean;
      description
        "If true, loopback interface is advertised as a
        stub network";
    }
    leaf interface-ack-list-count {
      type uint32;
      description "Ack List Count";
    }
    leaf interface-ack-list-high-watermark {
      type uint32;
      description "Ack List High Watermark";
    }
    leaf registered-for-link-down-fast-detection {
      type boolean;
      description "Registered for Link Down Fast Detection";
    }
    leaf fast-detect-hold-down-time {
      type uint32;
      description "Hold-down time in ms for fast-detect event";
    }
    leaf interface-fast-detect-hold-down {
      type boolean;
      description
        "Link in hold-down state due to fast detect event";
    }
    leaf fast-detect-hold-down-time-remaining {
      type uint32;
      description "Remaining hold down time in ms";
    }
    leaf fast-reroute-type {
      type Ipfrr;
      description "IP Fast Reroute Type";
    }
    leaf fast-reroute-topology-independent-lfa {
      type boolean;
      description "Topology Independent LFA";
    }
    leaf-list srlg {
      type uint32;
      description "SRLG Values";
    }

    list interface-neighbor {
      description "Information for neighbors on the interface";
      uses OSPF-SH-INTERFACE-NBR;
    }

    list interface-madj {
      description "Information for multi-area on the interface";
      uses OSPF-SH-INTERFACE-MADJ;
    }

    list ipfrr-tiebreakers {
      description "IPFRR-Tiebreakers list";
      uses OSPF-SH-IPFRR-TB;
    }
  }

  grouping OSPF-SH-VLINK-NEIGHBOR {
    description "Virtual Link Neighbor Information";

    container virtual-link-retransmissoin {
      description "Neighbor retransmission info";
      uses OSPF-SH-NEIGHBOR-RETRANS;
    }
    leaf virtual-link-suppress-hello {
      type boolean;
      description "If true Hellos suppressed";
    }
    leaf virtual-link-state {
      type Neighbor-state;
      description "Adjacency state";
    }
  }

  grouping OSPF-SH-VIRTUAL-LINKS {
    description "OSPF Virtual Link";

    container virtual-link-neighbor {
      description "Neighbor information";
      uses OSPF-SH-VLINK-NEIGHBOR;
    }
    leaf virtual-link-name-xr {
      type string;
      description "Virtual link name";
    }
    leaf virtual-link-neighbor-id {
      type inet:ipv4-address;
      description "Neighbor on other end of this virtual link";
    }
    leaf virtual-link-state {
      type Ospf-interface-state;
      description "OSPF interface state for the virtual link";
    }
    leaf virtual-link-demand-circuit {
      type boolean;
      description "If true, the link runs as demand circuit";
    }
    leaf virtual-link-dc-bitless-lsa {
      type uint32;
      description "Number of LSA's with demand circuit bit not set";
    }
    leaf transit-area {
      type string;
      description "Transit area id";
    }
    leaf virtual-link-interface-name {
      type xr:Interface-name;
      description "Interface on which this virtual link is formed";
    }
    leaf virtual-link-cost {
      type uint16;
      description "Cost of the virtual link";
    }
    leaf virual-link-transmission-delay {
      type uint16;
      units "second";
      description "Transmission delay in seconds";
    }
    leaf virtual-link-hello-interval {
      type uint32;
      description "Hello interval (s)";
    }
    leaf virtual-link-hello-interval-ms {
      type uint32;
      description "Hello interval (ms)";
    }
    leaf virtual-link-dead-interval {
      type uint32;
      description "Dead interval (s)";
    }
    leaf virtual-link-wait-interval {
      type uint32;
      description "Wait interval (s)";
    }
    leaf virtaul-link-retransmission-interval {
      type uint32;
      description "Retransmission interval (s)";
    }
    leaf virtual-link-next-hello {
      type uint32;
      description "Time until next hello (s)";
    }
    leaf virtual-link-next-hello-ms {
      type uint32;
      description "Time until next hello (ms)";
    }
    leaf virtual-link-passive {
      type boolean;
      description "If true, interface is passive";
    }
    leaf virtual-link-authentication-type {
      type Authentication;
      description "Authentication type";
    }
    leaf virtual-link-youngest-md-key {
      type boolean;
      description "If true, MD key configured";
    }
    leaf virtual-link-youngest-md-key-id {
      type uint16;
      description "Youngest MD key ID";
    }
    leaf virtual-link-old-md-key-count {
      type uint32;
      description
        "Number of neighbors still using the old key
        (rollover in progress)";
    }
    leaf virtual-link-keychain-id {
      type uint64;
      description "Virtual Link Keychain ID";
    }
    leaf virtual-link-nsf-enabled {
      type boolean;
      description "If true, NSF enabled";
    }
    leaf virtual-link-nsf {
      type boolean;
      description
        "If true, NSF restart in progress on the virtual
        link";
    }
    leaf virtual-link-last-nsf {
      type uint32;
      units "second";
      description "Time in seconds since last NSF";
    }
    leaf-list virtual-link-md-key {
      type uint16;
      description "List of old MD keys (if any)";
    }
  }

  grouping OSPF-SH-INTERFACE-MADJ {
    description "OSPF Interface Multi-Area Information";
    leaf interface-area {
      type string {
        length "0..16";
      }
      description
        "Area ID string in decimal or dotted-decimal
        format";
    }
    leaf madj-area-id {
      type uint32;
      description "Area ID";
    }
    leaf interface-neighbor-count {
      type uint16;
      description "Number of Neighbors";
    }
    leaf interface-adj-neighbor-count {
      type uint16;
      description "Total number of Adjacent Neighbors";
    }
    leaf interface-link-cost {
      type uint16;
      description "Interface link cost";
    }
    leaf ospf-interface-state {
      type Ospf-interface-state;
      description "Interface OSPF state";
    }
  }

  grouping OSPF-SH-IF-BRIEF {
    description "OSPF Interface Brief Information";
    leaf interface-name-xr {
      type xr:Interface-name;
      description "Interface name";
    }
    leaf interface-area {
      type string {
        length "0..16";
      }
      description
        "Area ID string in decimal or dotted-decimal
        format";
    }
    leaf interface-address {
      type inet:ipv4-address;
      description "Interface IP Address";
    }
    leaf interface-mask {
      type uint32;
      description "Interface IP Mask";
    }
    leaf interface-link-cost {
      type uint16;
      description "Interface link cost";
    }
    leaf ospf-interface-state {
      type Ospf-interface-state;
      description "Interface OSPF state";
    }
    leaf interface-fast-detect-hold-down {
      type boolean;
      description "Interface in fast detect hold down state";
    }
    leaf interface-neighbor-count {
      type uint16;
      description "Total number of Neighbors";
    }
    leaf interface-adj-neighbor-count {
      type uint16;
      description "Total number of Adjacent Neighbors";
    }
    leaf interfaceis-madj {
      type boolean;
      description "If true, interface is multi-area";
    }
    leaf interface-madj-count {
      type uint16;
      description "Total number of multi-area";
    }

    list interface-madj {
      description "Information for multi-area on the interface";
      uses OSPF-SH-INTERFACE-MADJ;
    }
  }

  grouping OSPF-SH-ROUTE-EXTENDED-COMM {
    description
      "OSPF External Route Extended Community
      Information";
    leaf extended-community-domain-id-value {
      type yang:hex-string;
      description "Domain ID value";
    }
    leaf extended-communityl-domain-id-type {
      type uint16;
      description "Domain ID type";
    }
    leaf extended-community-area-id {
      type uint32;
      description "Area id";
    }
    leaf extended-community-router-id {
      type inet:ipv4-address;
      description "Router id";
    }
    leaf extended-community-route-type {
      type uint8;
      description "Route type";
    }
    leaf extended-community-options {
      type uint8;
      description "Route Options";
    }
  }

  grouping OSPF-SH-REDIST-PROTO {
    description "Redistributed protocol instance";
    leaf protocol-type {
      type Redist-protocol;
      description "ProtocolType";
    }
    leaf isis-instance-id {
      when "../protocol-type = 'mgmt-rib-protocol-isis'" {
        description "../ProtocolType = 'MGMT_RIB_PROTOCOL_ISIS'";
      }
      type String1;
      description "ISIS instance identifier";
    }
    leaf ospf-process-id {
      when "../protocol-type = 'mgmt-rib-protocol-ospf'" {
        description "../ProtocolType = 'MGMT_RIB_PROTOCOL_OSPF'";
      }
      type String1;
      description "OSPF process identifier";
    }
    leaf bgp-as-number {
      when "../protocol-type = 'mgmt-rib-protocol-bgp'" {
        description "../ProtocolType = 'MGMT_RIB_PROTOCOL_BGP'";
      }
      type String1;
      description "BGP Autonomous System Number";
    }
    leaf eigrp-as-number {
      when "../protocol-type = 'mgmt-rib-protocol-eigrp'" {
        description "../ProtocolType = 'MGMT_RIB_PROTOCOL_EIGRP'";
      }
      type String1;
      description "Autonomous System Number";
    }
    leaf connected-instance {
      when "../protocol-type = 'mgmt-rib-protocol-connected'" {
        description
          "../ProtocolType = 'MGMT_RIB_PROTOCOL_CONNECTED'";
      }
      type String1;
      description "Connected instance name";
    }
  }

  grouping OSPF-SH-ROUTE-EXT {
    description "OSPF External Route Information";

    container route-information {
      description "Route information";
      uses OSPF-SH-TOPOLOGY;
    }

    container protocol-name {
      description
        "Name of protocol from which the external route
        was redistributed";
      uses OSPF-SH-REDIST-PROTO;
    }

    container route-extended-community {
      description "Extended communities in the route";
      uses OSPF-SH-ROUTE-EXTENDED-COMM;
    }
  }

  grouping OSPF-SH-ROUTE-SUMM-COMMON {
    description "OSPF Route Summary Common Information";
    leaf external-type1s {
      type uint32;
      description "External type 1 count";
    }
    leaf external-type2s {
      type uint32;
      description "External type 2 count";
    }
    leaf external-nssa-type1s {
      type uint32;
      description "External NSSA type 1 count";
    }
    leaf external-nssa-type2s {
      type uint32;
      description "External NSSA type 2 count";
    }
    leaf inter-areas {
      type uint32;
      description "Inter-area count";
    }
    leaf intra-areas {
      type uint32;
      description "Intra-area count";
    }
    leaf total {
      type uint32;
      description "Total count";
    }
  }

  grouping OSPF-SH-ROUTE-SUMMARY {
    description "OSPF Route Summary Information";

    container failure-time {
      description "Last time failed";
      uses OSPF-SH-TIME;
    }

    container common {
      description "OSPF route summary Information";
      uses OSPF-SH-ROUTE-SUMM-COMMON;
    }
    leaf failures {
      type uint32;
      description "RIB failure count";
    }
    leaf failure-address {
      type inet:ipv4-address;
      description "Last failed address";
    }
  }

  grouping OSPF-SH-TOP-PATH {
    description "OSPF Route Path Information";

    container sr-microloop-avoidance-path {
      description "SR Microloop avoidance Path Info";
      uses OSPF-SH-SR-ULOOP-PATH;
    }
    leaf route-interface-name {
      type xr:Interface-name;
      description "Next hop Interface";
    }
    leaf route-next-hop-address {
      type inet:ipv4-address;
      description "Nexthop IP address";
    }
    leaf route-source {
      type inet:ipv4-address;
      description "IP address of source of route";
    }
    leaf route-lsaid {
      type inet:ipv4-address;
      description "LSA ID, see RFC2328";
    }
    leaf route-path-is-mcast-intact {
      type boolean;
      description "Multicast-intact path";
    }
    leaf route-path-is-ucmp-path {
      type boolean;
      description "UCMP path";
    }
    leaf route-metric {
      type uint32;
      description "Metric";
    }
    leaf lsa-type {
      type uint8;
      description "LSA type, see RFC2328 etc.";
    }
    leaf area-id {
      type uint32;
      description "Area ID";
    }
    leaf area-format {
      type boolean;
      description "Area format IP or uint32";
    }
  }

  grouping OSPF-SH-TOPOLOGY {
    description "OSPF Route Information";

    container route-info {
      description "Route information";
      uses OSPF-SH-TOP-COMMON;
    }
    leaf route-prefix {
      type inet:ipv4-address;
      description "Prefix";
    }
    leaf route-prefix-length {
      type uint32;
      description "Prefix length";
    }
    leaf route-metric {
      type uint32;
      description "Metric";
    }
    leaf route-type {
      type Ospf-route;
      description "Route type";
    }
    leaf route-connected {
      type boolean;
      description "If true, connected route";
    }

    list route-path {
      description "List of paths to this route";
      uses OSPF-SH-TOP-PATH;
    }
  }

  grouping OSPF-SH-SR-ULOOP-PATH {
    description "OSPF Route SR Uloop Path Information";
    leaf microloop-repair-list-size {
      type uint32;
      description "Microloop Repair List Size";
    }
    leaf microloop-tunnel-interface-name {
      type xr:Interface-name;
      description "Microloop Tunnel Interface name";
    }
    leaf microloop-strict-spf {
      type boolean;
      description "Strict SPF SID";
    }

    list microloop-repair {
      max-elements "10";
      description "Microloop Repair List";
      uses OSPF-SH-REP-EL;
    }
  }

  grouping OSPF-SH-REP-EL {
    description "OSPF Repair Element";
    leaf repair-element-id {
      type inet:ipv4-address;
      description "Repair Element ID";
    }
    leaf repair-label {
      type uint32;
      description "Repair Label";
    }
    leaf repair-element-type {
      type uint32;
      description "Repair Element Type";
    }
  }

  grouping OSPF-SH-BACKUP-PATH {
    description "OSPF Route Backup Path Information";
    leaf backup-route-interface-name {
      type xr:Interface-name;
      description "Next hop Interface";
    }
    leaf backup-route-next-hop-address {
      type inet:ipv4-address;
      description "Nexthop IP address";
    }
    leaf backup-route-source {
      type inet:ipv4-address;
      description "IP address of source of route";
    }
    leaf backup-metric {
      type uint32;
      description "Metric";
    }
    leaf primary-path {
      type boolean;
      description "Primary Path";
    }
    leaf line-card-disjoint {
      type boolean;
      description "Line Card Disjoint";
    }
    leaf downstream {
      type boolean;
      description "Downstream";
    }
    leaf node-protect {
      type boolean;
      description "Node Protect";
    }
    leaf srlg-disjoint {
      type boolean;
      description "SRLG Disjoint";
    }
    leaf backup-remote-lfa {
      type inet:ipv4-address;
      description "IP address of remote LFA";
    }
    leaf backup-repair-list-size {
      type uint32;
      description "Repair List Size";
    }
    leaf backup-tunnel-interface-name {
      type xr:Interface-name;
      description "Backup Tunnel Interface";
    }

    list backup-repair {
      max-elements "10";
      description "Backup Repair List";
      uses OSPF-SH-REP-EL;
    }
  }

  grouping OSPF-SH-TOP-PATH-BACKUP {
    description "OSPF Route Path Wit Backup Path Information";

    container route-backup-path {
      description "Backup Path Info";
      uses OSPF-SH-BACKUP-PATH;
    }

    container sr-microloop-avoidance-path {
      description "SR Microloop avoidance Path Info";
      uses OSPF-SH-SR-ULOOP-PATH;
    }
    leaf route-interface-name {
      type xr:Interface-name;
      description "Next hop Interface";
    }
    leaf route-next-hop-address {
      type inet:ipv4-address;
      description "Nexthop IP address";
    }
    leaf route-source {
      type inet:ipv4-address;
      description "IP address of source of route";
    }
    leaf route-lsaid {
      type inet:ipv4-address;
      description "LSA ID, see RFC2328";
    }
    leaf route-path-is-mcast-intact {
      type boolean;
      description "Multicast-intact path";
    }
    leaf route-path-is-ucmp-path {
      type boolean;
      description "UCMP path";
    }
    leaf route-metric {
      type uint32;
      description "Metric";
    }
    leaf route-path-id {
      type uint16;
      description "Path ID of path";
    }
    leaf lsa-type {
      type uint8;
      description "LSA type, see RFC2328 etc.";
    }
  }

  grouping OSPF-SH-TOP-COMMON {
    description "OSPF Common Route Information";

    container route-update-time {
      description "Last time updated";
      uses OSPF-SH-TIME;
    }

    container route-fail-time {
      description "Last time update failed";
      uses OSPF-SH-TIME;
    }
    leaf route-area-id {
      type uint32;
      description "Area ID";
    }
    leaf route-te-metric {
      type uint32;
      description "TE metric";
    }
    leaf route-rib-version {
      type uint32;
      description "RIB version";
    }
    leaf route-spf-version {
      type uint64;
      description "SPF version";
    }
    leaf route-forward-distance {
      type uint32;
      description "Forward distance";
    }
    leaf route-source {
      type uint16;
      description "Protocol source";
    }
    leaf route-spf-priority {
      type uint8;
      description "SPF priority";
    }
    leaf route-auto-excluded {
      type boolean;
      description "If true, exclude from TE paths";
    }
    leaf route-srte-prefix-registered {
      type boolean;
      description "If true, SRTE registered prefix route";
    }
    leaf route-srte-nbr-registered {
      type uint16;
      description "SRTE registered neigbhor count on route";
    }
  }

  grouping OSPF-SH-TOPOLOGY-BACKUP {
    description "OSPF Route Information With Backup Path";

    container route-info {
      description "Route information";
      uses OSPF-SH-TOP-COMMON;
    }
    leaf route-prefix {
      type inet:ipv4-address;
      description "Prefix";
    }
    leaf route-prefix-length {
      type uint32;
      description "Prefix length";
    }
    leaf route-metric {
      type uint32;
      description "Metric";
    }
    leaf route-type {
      type Ospf-route;
      description "Route type";
    }
    leaf route-connected {
      type boolean;
      description "If true, connected route";
    }

    list route-path {
      description "List of paths to this route";
      uses OSPF-SH-TOP-PATH-BACKUP;
    }
  }

  grouping OSPF-SH-NEIGHBOR-RETRANS {
    description "OSPF Neighbor Retransmission Information";
    leaf dbd-retransmission-count {
      type uint32;
      description
        "Number of DBD retransmissions during last
        exchange";
    }
    leaf dbd-retransmission-total-count {
      type uint32;
      description
        "Total number of DBD retransmissions for this
        neighbor";
    }
    leaf area-flooding-index {
      type uint32;
      description "Area scope LSA's flood index";
    }
    leaf as-flood-index {
      type uint32;
      description "AS scope LSA's flood index";
    }
    leaf neighbor-retransmission-count {
      type uint32;
      description "Retransmission queue length";
    }
    leaf number-of-retransmissions {
      type uint32;
      description "Number of retransmissions for this neighbor";
    }
    leaf area-first-flood-information {
      type uint32;
      description "First flood item for area scope LSAs";
    }
    leaf area-first-flood-information-index {
      type uint32;
      description
        "Index of the first flood item for area scope
        LSAs";
    }
    leaf as-first-flood-information {
      type uint32;
      description "First flood item for AS scope LSAs";
    }
    leaf as-first-flood-information-index {
      type uint32;
      description "Index for first flood item for AS scope LSAs";
    }
    leaf area-next-flood-information {
      type uint32;
      description "Next flood item for area scope LSAs";
    }
    leaf area-next-flood-information-index {
      type uint32;
      description "Index of next flood item for Area scope LSAs";
    }
    leaf as-next-flood-information {
      type uint32;
      description "Next flood item for AS scope LSAs";
    }
    leaf as-next-flood-information-index {
      type uint32;
      description "Index of next flood item for AS scope LSAs";
    }
    leaf last-retransmission-length {
      type uint32;
      description "Number of LSAs sent in last retransmission";
    }
    leaf maximum-retransmission-length {
      type uint32;
      description "Maximum number of LSAs sent in a retransmission";
    }
    leaf last-retransmission-time {
      type uint32;
      description "Last retransmission scan time (ms)";
    }
    leaf maximum-retransmission-time {
      type uint32;
      description "Maximum retransmission scan time (ms)";
    }
    leaf lsa-retransmission-timer {
      type uint32;
      description "Time until next LSA retransmission (ms)";
    }
  }

  grouping OSPF-SH-NEIGHBOR-DETAIL {
    description "OSPF Neighbor Detailed Information";

    container neighbor-summary {
      description "Neighbor summary information";
      uses OSPF-SH-NEIGHBOR;
    }

    container neighbor-bfd-information {
      description "Neighbor BFD information";
      uses OSPF-SH-NEIGHBOR-BFD;
    }

    container neighbor-retransmission-information {
      description "Retransmission information with this neighbor";
      uses OSPF-SH-NEIGHBOR-RETRANS;
    }
    leaf neighbor-area-id {
      type string {
        length "0..16";
      }
      description
        "Area ID string in decimal or dotted-decimal
        format";
    }
    leaf state-change-count {
      type uint16;
      description "Number of state changes";
    }
    leaf neighbor-cost {
      type uint16;
      description "Cost of path to this neighbor";
    }
    leaf neighbor-filter {
      type boolean;
      description "If true, filter outgoing LSAs";
    }
    leaf neighbor-designated-router-address {
      type inet:ipv4-address;
      description "Address of designated router";
    }
    leaf neighbor-backup-designated-router-address {
      type inet:ipv4-address;
      description "Address of backup designated router";
    }
    leaf interface-type {
      type Interface;
      description "Interface type";
    }
    leaf poll-interval {
      type uint32;
      description "Poll interval (s)";
    }
    leaf next-poll-interval {
      type uint32;
      units "second";
      description
        "For NBMA networks, amount of time remaining in
        seconds before the next poll interval expires
        and Hello is sent (s)";
    }
    leaf neighbor-option {
      type uint8;
      description
        " This is bitmaks of neighbor's option field
        received";
    }
    leaf pending-events {
      type uint16;
      description "Number of pending events";
    }
    leaf neighbor-lls-option {
      type uint16;
      description
        "This is a bitmask of Link Local signalling
        options received from the neighbor";
    }
    leaf oob-resynchronization {
      type boolean;
      description "Out-Of-Bound resynchronization in progress";
    }
    leaf nsf-router-state {
      type Nsf-rtr;
      description
        "For cisco NSF, the router is either Requester or
        Receiver";
    }
    leaf last-oob-time {
      type uint32;
      units "second";
      description
        "The amount of time in seconds since last time
        Out-Of-Band resynchronization was done with this
        neighbor";
    }
    leaf lfa-interface {
      type xr:Interface-name;
      description "LFA Interface";
    }
    leaf lfa-next-hop {
      type inet:ipv4-address;
      description "LFA Next Hop";
    }
    leaf lfa-neighbor-id {
      type inet:ipv4-address;
      description "LFA Neighbor ID";
    }
    leaf lfa-neighbor-revision {
      type uint32;
      description "LFA Neighbor Revision";
    }
    leaf neighbor-ack-list-count {
      type uint32;
      description "Ack List Count";
    }
    leaf neighbor-ack-list-high-watermark {
      type uint32;
      description "Ack List High Watermark";
    }
    leaf adjacency-sid-label {
      type uint32;
      description "SR Adjacency SID Label";
    }
    leaf adjacency-sid-protected {
      type boolean;
      description "SR Adjacency SID Protected";
    }
    leaf adjacency-sid-unprotected-label {
      type uint32;
      description "SR Adjacency SID Unprotected Label";
    }
  }

  grouping OSPF-SH-RETRANS-LIST {
    description "OSPF Retransmission List";
    leaf retransmission-neighbor-id {
      type inet:ipv4-address;
      description "Neighbor ID";
    }
    leaf retransmission-neighbor-ip-address {
      type inet:ipv4-address;
      description "Neighbor IP Address";
    }
    leaf retransmission-interface-name {
      type xr:Interface-name;
      description "Retransmission list interface";
    }
    leaf retransmission-timer {
      type uint32;
      description
        "Amount of time remaining on retransmission timer
        (ms)";
    }
    leaf retransmission-count {
      type uint32;
      description "Retransmission queue length";
    }

    list retransmission-area-db {
      description "List of Area scope entries";
      uses OSPF-SH-LSA-SUM;
    }

    list retransmission-asdb {
      description "List of AS Scope entries";
      uses OSPF-SH-LSA-SUM;
    }
  }

  grouping OSPF-SH-REQUEST-LIST {
    description "OSPF Request List Information";
    leaf request-neighbor-id {
      type inet:ipv4-address;
      description "Neighbor ID";
    }
    leaf request-neighbor-address {
      type inet:ipv4-address;
      description "Neighbor IP address";
    }
    leaf request-interface-name {
      type xr:Interface-name;
      description "Request list interface";
    }

    list request {
      description "List of request list entries";
      uses OSPF-SH-LSA-SUM;
    }
  }

  grouping OSPF-SH-NEIGHBOR-BFD {
    description "OSPF Neighbor BFD information";
    leaf bfd-intf-enable-mode {
      type uint32;
      description "BFD enable mode - Default/Strict";
    }
    leaf bfd-status-flag {
      type uint8;
      description "Status of the BFD Session";
    }
  }

  grouping OSPF-SH-NEIGHBOR {
    description "OSPF Neighbor Summary Information";

    container neighbor-bfd-information {
      description "Neighbor BFD information";
      uses OSPF-SH-NEIGHBOR-BFD;
    }
    leaf neighbor-id {
      type inet:ipv4-address;
      description "Neighbor ID";
    }
    leaf neighbor-address-xr {
      type inet:ipv4-address;
      description "Neighbor IP Address";
    }
    leaf neighbor-interface-name {
      type xr:Interface-name;
      description "Interface via which the neighbor is seen";
    }
    leaf neighbor-dr-priority {
      type uint8;
      description "Neighbor's DR priority";
    }
    leaf neighbor-state {
      type Neighbor-state;
      description "Neighbor's state";
    }
    leaf dr-bdr-state {
      type Dr-bdr-state;
      description "Designated Router state";
    }
    leaf neighbor-dead-timer {
      type uint32;
      description "Time until neighbor's dead timer expires (s)";
    }
    leaf neighbor-up-time {
      type uint32;
      description "Amount of time since the adjacency is up (s)";
    }
    leaf neighbor-madj-interface {
      type boolean;
      description "Interface is MADJ";
    }
  }

  grouping OSPF-SH-TIME {
    description "OSPF SH TIME";
    leaf second {
      type uint32;
      description "Second";
    }
    leaf nanosecond {
      type uint32;
      description "Nanosecond";
    }
  }

  grouping OSPF-SH-MPLS-FRAGMENT {
    description "OSPF MPLS-TE Fragment Information";
    leaf fragment-instance {
      type uint32;
      description "Fragment instance";
    }
    leaf fragment-id {
      type uint32;
      description "Fragment ID";
    }
    leaf dste-model-id {
      type uint8;
      description "DS-TE Allocation Model ID";
    }
    leaf same-fragment-count {
      type uint8;
      description
        "Number of fragment links which haven't changed
        since the last update";
    }

    list mpls-te-link {
      description "List of fragment links";
      uses OSPF-SH-MPLS-LINK;
    }
  }

  grouping OSPF-SH-MPLS-EAG {
    description "EXTENDED administrative group TLVs";
    leaf extended-admin-size {
      type uint32;
      description "Size of the extended admin group";
    }
    leaf-list ext-admin-data {
      type uint32;
      description "Value of Extended Admin Group";
    }
  }

  grouping MPLS-TEL-OPT-UNID-VAL {
    description "MPLS TE Link Optional TLV IXCD Data";
    leaf uni-dir-delay {
      type uint32;
      description "Uni Dir Delay";
    }
  }

  grouping BW-FLEX-SUBTLV-VALUE {
    description "Value of Flex Sub TLV";

    container flex-sub-tlv-value-common {
      description "Flex Sub TLV Value";
      uses BW-SUB-TLV-VALUE-COMMON;
    }
    leaf-list unres-lspbw {
      type uint64;
      max-elements "8";
      description "Array of Unres LSP BW";
    }
    leaf-list max-lspbw {
      type uint64;
      max-elements "8";
      description "Max LSP BW Array";
    }
  }

  grouping BW-SUB-TLV-VALUE-COMMON {
    description "Common values in both Fixed and Flex Sub TLV";
    leaf signal-type {
      type uint8;
      description "Signal Type";
    }
    leaf num-stages {
      type uint8;
      description "Number of stages";
    }
    leaf tbit {
      type uint8;
      description "T Bit";
    }
    leaf sbit {
      type uint8;
      description "S Bit";
    }
    leaf tsg {
      type uint8;
      description "TSG";
    }
    leaf res {
      type uint8;
      description "Res";
    }
    leaf priority-bit0 {
      type uint8;
      description "Priority 0";
    }
    leaf priority-bit1 {
      type uint8;
      description "Priority 1";
    }
    leaf priority-bit2 {
      type uint8;
      description "Priority 2";
    }
    leaf priority-bit3 {
      type uint8;
      description "Priority 3";
    }
    leaf priority-bit4 {
      type uint8;
      description "Priority 4";
    }
    leaf priority-bit5 {
      type uint8;
      description "Priority 5";
    }
    leaf priority-bit6 {
      type uint8;
      description "Priority 6";
    }
    leaf priority-bit7 {
      type uint8;
      description "Priority 7";
    }
    leaf stage {
      type yang:hex-string;
      description "Array of Stages";
    }
  }

  grouping BW-FIXED-SUBTLV-VALUE {
    description "Value of Fixed Sub TLV";

    container fixed-sub-tlv-value {
      description "Value of Fixed Sub TLV";
      uses BW-SUB-TLV-VALUE-COMMON;
    }
    leaf-list unres-oduj-prio {
      type uint32;
      max-elements "8";
      description "Array of Unres Oduj Prio";
    }
  }

  grouping IXCD-BW-SUB-TLV-VALUE-UNION {
    description "Sub Tlv values for IXCD Bandwidth";

    container fixed-bw-sub-tlv-value {
      when "../ixcdbw-sub-tlv-type = '1'" {
        description "../IXCDBWSubTLVType = '1'";
      }
      description "Value of Fixed Sub TLV";
      uses BW-FIXED-SUBTLV-VALUE;
    }

    container flex-bw-sub-tlv-value {
      when "../ixcdbw-sub-tlv-type = '2'" {
        description "../IXCDBWSubTLVType = '2'";
      }
      description "Value of Flex Sub TLV";
      uses BW-FLEX-SUBTLV-VALUE;
    }
    leaf ixcdbw-sub-tlv-type {
      type uint16;
      description "IXCDBWSubTLVType";
    }
  }

  grouping IXCD-BW-SUB-TLV {
    description "IXCD BW sub tlv";

    container bw-sub-tlv-value {
      description "Value of BW Sub TLV";
      uses IXCD-BW-SUB-TLV-VALUE-UNION;
    }
    leaf bw-sub-tlv-type {
      type uint16;
      description "Type of Sub TLV";
    }
    leaf bw-sub-tlv-length {
      type uint16;
      description "Length of BW Sub TLV";
    }
  }

  grouping IXCD-BW-SUB-TLV-ARR {
    description "Array of BW Sub TLVs";

    list arr-bw-sub-tlv {
      description "Array of sub tlvs";
      uses IXCD-BW-SUB-TLV;
    }
  }

  grouping IXCD-LE-PSC-INFO {
    description "IXCD LE PSC information";
    leaf min-lsp-bandwidth {
      type uint64;
      description "Min LSP bandwidth";
    }
    leaf psc-interface-mtu {
      type uint16;
      description " Interface MTU";
    }
  }

  grouping IXCD-TLV-SWITCHINGCAP-VALUE-UNION {
    description "Switching Cap values";

    container ixcdpsc-info {
      when "../switching-cap-type = 'rrr-proto-l-switch-cap-psc4'" {
        description
          "../SwitchingCapType =
          'RRR_PROTO_LSWITCH_CAP_PSC4'";
      }
      description "IXCD PSC information";
      uses IXCD-LE-PSC-INFO;
    }

    container ixcdbw-sub-tlv {
      when "../switching-cap-type ="+
        " 'rrr-proto-l-switch-cap-otn-tdm'" {
          description
            "../SwitchingCapType =
            'RRR_PROTO_LSWITCH_CAP_OTN_TDM'";
      }
      description "Sub TLVs";
      uses IXCD-BW-SUB-TLV-ARR;
    }
    leaf switching-cap-type {
      type uint8;
      description "SwitchingCapType";
    }
  }

  grouping MPLS-TEL-OPT-IXCD-VAL {
    description "MPLS TE Link Optional TLV IXCD Data";

    container ixcd-switching-cap-type {
      description "Switching Cap type";
      uses IXCD-TLV-SWITCHINGCAP-VALUE-UNION;
    }
    leaf switching-cap {
      type uint8;
      description "SCap";
    }
    leaf rile-len-code {
      type uint8;
      description "Rile LenCode";
    }
    leaf fixed-scsi-count {
      type uint32;
      description "Fixed SCSI count";
    }
    leaf flex-scsi-count {
      type uint32;
      description "Flexible SCSI count";
    }
    leaf-list max-lspbw {
      type int64;
      max-elements "8";
      description "Max LSP bandwidth array";
    }
  }

  grouping MPLS-TEL-OPT-SRLG-VAL {
    description "MPLS TE Link Optional TLV SRLG Data";
    leaf srlg-len {
      type uint32;
      description "Length of SRLG TLV";
    }
    leaf num-srl-gs {
      type uint32;
      description "Number of SRLG TLVs";
    }
    leaf-list mplste-link-srlg-data {
      type uint32;
      description "Value of SRLG TLV";
    }
  }

  grouping MPLS-TEL-OPT-BC-VAL {
    description "MPLS TE Link Optional TLV BC Data";
    leaf model-id {
      type uint8;
      description "Allocation Model ID";
    }
    leaf num-b-cs {
      type uint32;
      description "Number of BC TLVs";
    }
    leaf-list mplste-link-bc-bandwidth {
      type uint64;
      description "Value of BC TLV";
    }
  }

  grouping MPLSTEL-TLV-VALUE-UNION {
    description "Value of TLVs";

    container bctlv-value {
      when "../opaque-tlv-type = 'mpls-te-opt-tlv-type-bc'" {
        description "../OpaqueTLVType = 'MPLS_TE_OPT_TLV_TYPE_BC'";
      }
      description "Value of Bandwidth Constraints TLV";
      uses MPLS-TEL-OPT-BC-VAL;
    }

    container srlgtlv-value {
      when "../opaque-tlv-type = 'mpls-te-opt-tlv-type-srlg'" {
        description
          "../OpaqueTLVType = 'MPLS_TE_OPT_TLV_TYPE_SRLG'";
      }
      description "Value of SRLG TLV";
      uses MPLS-TEL-OPT-SRLG-VAL;
    }

    container ixcdtlv-value {
      when "../opaque-tlv-type = 'mpls-te-opt-tlv-type-ixcd'" {
        description
          "../OpaqueTLVType = 'MPLS_TE_OPT_TLV_TYPE_IXCD'";
      }
      description "Value of IXCD TLV";
      uses MPLS-TEL-OPT-IXCD-VAL;
    }

    container unidtlv-value {
      when "../opaque-tlv-type = 'mpls-te-opt-tlv-type-uni-delay'" {
        description
          "../OpaqueTLVType =
          'MPLS_TE_OPT_TLV_TYPE_UNI_DELAY'";
      }
      description "Value of Uni Delay TLV";
      uses MPLS-TEL-OPT-UNID-VAL;
    }
    leaf opaque-tlv-type {
      type Mpls-te-opt-tlv;
      description "OpaqueTLVType";
    }
  }

  grouping OSPF-SH-MPLS-TEL-OPT-TLV {
    description "MPLS TE Link Optional TLVs";
    leaf mplste-link-opt-tlv-type {
      type Mpls-te-opt-tlv;
      description "Type of Opt TLV";
    }
    leaf mplste-link-opt-tlv-len {
      type uint16;
      description "Length of Opt TLV";
    }

    list mplste-link-opt-tlv-value {
      description "Value of Opt TLV";
      uses MPLSTEL-TLV-VALUE-UNION;
    }
  }

  grouping OSPF-SH-MPLS-IXCD-CAP {
    description "Link switching capability";
    leaf link-switching-capability {
      type uint8;
      description "Link Switching Capability";
    }
    leaf link-encoding {
      type uint8;
      description "Link Encoding";
    }
    leaf minimum-lsp-bw {
      type uint64;
      units "byte/s";
      description "Minimum LSP bandwidth (bytes/s)";
    }
    leaf link-mtu {
      type uint16;
      units "byte";
      description "Link MTU size (bytes)";
    }
    leaf-list maximum-lsp-bw-per-priority {
      type uint64;
      units "byte/s";
      max-elements "8";
      description
        "Maximum LSP bandwidth for each priority
        (bytes/s)";
    }
  }

  grouping OSPF-SH-MPLS-LINK-PROTOPRIO {
    description "Link protocol and priority capability";
    leaf link-protocol-capability {
      type uint8;
      description "Link protocol capability";
    }
    leaf link-protocol-priority {
      type uint8;
      description "Link protocol priority";
    }
  }

  grouping OSPF-SH-MPLS-BW {
    description "Available bandwidth for each priority level";
    leaf-list bw-per-priority {
      type uint64;
      units "byte/s";
      max-elements "8";
      description
        "Unreserved bandwidth for each priority (bytes/s)";
    }
  }

  grouping OSPF-SH-MPLS-LINK {
    description "OSPF MPLS-TE link Information";

    container global-unreserve-bw-per-priority {
      description
        "Global pool unreserved bandwidth for each
        priority (bytes/s)";
      uses OSPF-SH-MPLS-BW;
    }

    container sub-pool-unreserve-bw-per-priority {
      description
        "Sub pool unreserved bandwidth for each priority
        (bytes/s)";
      uses OSPF-SH-MPLS-BW;
    }

    container link-protocol-priority-capability {
      description "Link protocol and protocol priority capability";
      uses OSPF-SH-MPLS-LINK-PROTOPRIO;
    }

    container link-sw-capability {
      description "Link switching capability";
      uses OSPF-SH-MPLS-IXCD-CAP;
    }

    container extended-admin-group-list {
      description "Extended Admin Group";
      uses OSPF-SH-MPLS-EAG;
    }
    leaf new-link {
      type boolean;
      description "If true, Link is new";
    }
    leaf fragment-id {
      type uint32;
      description "Fragment ID for this link";
    }
    leaf mpls-link-instance {
      type uint32;
      description "Link instance";
    }
    leaf mpls-link-type {
      type Link-subnet;
      description "Type of link";
    }
    leaf neighbor-system-id {
      type inet:ipv4-address;
      description "Neighbor system ID";
    }
    leaf link-address {
      type inet:ipv4-address;
      description "The local interface address";
    }
    leaf neighbor-ip-address {
      type inet:ipv4-address;
      description "Neighbor IP address.";
    }
    leaf igp-metric {
      type uint32;
      description "Link IGP metric";
    }
    leaf te-metric {
      type uint32;
      description "Link TE metric";
    }
    leaf maximum-link-bw {
      type uint32;
      units "byte/s";
      description "Maximum link bandwidth (bytes/s)";
    }
    leaf maximum-link-reservable-bw {
      type uint32;
      units "byte/s";
      description
        "Maximum link global pool reservable bandwidth
        (bytes/s)";
    }
    leaf maximum-link-sub-reservable-bw {
      type uint32;
      units "byte/s";
      description
        "Maximum link subpool reservable bandwidth
        (bytes/s)";
    }
    leaf priority-count {
      type int32;
      description "Number of priorities.";
    }
    leaf affinity {
      type uint32;
      description "Affinity";
    }
    leaf output-interface-id {
      type uint32;
      description "Output interface ID";
    }
    leaf input-interface-id {
      type uint32;
      description "Input interface ID";
    }
    leaf dste-in-use {
      type boolean;
      description "A DS-TE Allocation Model in use";
    }
    leaf dste-allocation-model-id {
      type Igpte-lib-bw-model;
      description "DS-TE Allocation Model ID";
    }
    leaf number-of-optional-tl-vs {
      type uint8;
      description "Number of Optional TLVs";
    }

    list mplste-link-opt-tlv {
      description "List of Optional TLVs";
      uses OSPF-SH-MPLS-TEL-OPT-TLV;
    }
  }

  grouping OSPF-SH-MPLS {
    description "OSPF MPLS-TE Information";
    leaf mpls-te-router-id {
      type inet:ipv4-address;
      description "OSPF MPLS-TE router ID";
    }
    leaf mpls-te-enabled {
      type boolean;
      description "If true, MPLS-TE enabled in area";
    }
    leaf mpls-te-initialized {
      type boolean;
      description "If true, MPLS-TE initialized in the area";
    }
    leaf mpls-te-area-id {
      type string {
        length "0..16";
      }
      description
        "Area ID string in decimal or dotted decimal
        format";
    }
    leaf mpls-te-area-instance {
      type uint32;
      description "Area information instance";
    }
    leaf mpls-te-router-address {
      type inet:ipv4-address;
      description "MPLS-TE router address";
    }
    leaf mpls-te-next-fragment-id {
      type uint32;
      description "Next MPLS-TE fragment ID";
    }
    leaf spacious-fragment {
      type boolean;
      description "If true, fragment has space for next link";
    }

    list mpls-te-link {
      description "MPLS-TE links in the area";
      uses OSPF-SH-MPLS-LINK;
    }

    list mpls-te-fragment {
      description "MPLS TE fragments in the area";
      uses OSPF-SH-MPLS-FRAGMENT;
    }
  }

  grouping OSPF-SH-LSA-SUM {
    description "LSA Summary Entry";
    leaf header-lsa-type {
      type Lsa;
      description "LSA Type";
    }
    leaf header-lsa-age {
      type uint16;
      description "Age of the LSA (s)";
    }
    leaf header-ls-id {
      type inet:ipv4-address;
      description "LSA ID";
    }
    leaf header-advertising-router {
      type inet:ipv4-address;
      description "Router ID of the Advertising Router";
    }
    leaf header-sequence-number {
      type uint32;
      description "Current LSA sequence number";
    }
    leaf header-lsa-checksum {
      type uint16;
      description "Checksum of the LSA";
    }
  }

  grouping OSPF-SH-FLOOD-LIST {
    description "OSPF Flood List";
    leaf flood-interface-name {
      type xr:Interface-name;
      description "Interface name";
    }
    leaf flood-pacing-timer {
      type uint32;
      description "Time until next LS update due (ms)";
    }
    leaf flood-lsa-count {
      type uint32;
      description "Number of LSAs currently being flooded";
    }

    list area-flood {
      description "Area scope floodlist";
      uses OSPF-SH-LSA-SUM;
    }

    list as-flood {
      description "AS scope floodlist";
      uses OSPF-SH-LSA-SUM;
    }
  }
}
