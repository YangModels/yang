module Cisco-IOS-XR-openconfig-optical-client-cfg {

  /*** NAMESPACE / PREFIX DEFINITION ***/

  namespace "http://cisco.com/ns/yang"+
    "/Cisco-IOS-XR-openconfig-optical-client-cfg";


  prefix "openconfig-optical-client-cfg";

  /*** LINKAGE (IMPORTS / INCLUDES) ***/

  import Cisco-IOS-XR-types { prefix "xr"; }

  import Cisco-IOS-XR-ifmgr-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR openconfig-optical-client package configuration.

     This YANG module augments the
       Cisco-IOS-XR-ifmgr-cfg
     module with configuration data.

     Copyright (c) 2013-2016 by Cisco Systems, Inc.
     All rights reserved.";

  revision "2015-11-09" {
    description
      "IOS XR 6.0 revision.";
  }


  augment "/a1:interface-configurations/a1:interface-configuration" {

    container client-port {
      description "Mxp optics for client ports";

      container logical-channel-assignments {
        description "Client port logical channel assignment";

        list logical-channel-assignment {
          key "assignment-index";
          description "Logical channel assignment id";
          leaf allocation {
            type int32;
            description
              "Configure Allocation for this assignment(10,
              40 or 100G)";
          }
          leaf logical-channel-id {
            type int32;
            description
              "Configure Logical channel for this assignment";
          }
          leaf description {
            type string {
              length "1..255";
            }
            description "Configure description for this assignment";
          }
          leaf assignment-index {
            type int32;
            description "Logical channel assignment id";
          }
        }
      }

      container channels {
        description "Client Port Lane";

        list channel {
          key "index";
          description "Lane";
          leaf channel-description {
            type string {
              length "1..255";
            }
            description "Configure description for this Lane";
          }
          leaf index {
            type int32;
            description "Channel Number";
          }
        }
      }
    }
    description
      "This augment extends the configuration data of
      'Cisco-IOS-XR-ifmgr-cfg'";
  }
}
