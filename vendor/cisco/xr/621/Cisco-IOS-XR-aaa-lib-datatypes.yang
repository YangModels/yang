module Cisco-IOS-XR-aaa-lib-datatypes {

  /*** NAMESPACE / PREFIX DEFINITION ***/

  namespace "http://cisco.com/ns"+
    "/yang/Cisco-IOS-XR-aaa-lib-datatypes";


  prefix "aaa-lib-datatypes";

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of generally useful
     derived YANG data types.

     Copyright (c) 2013-2016 by Cisco Systems, Inc.
     All rights reserved.";

  revision "2015-11-09" {
    description
      "IOS XR 6.0 revision.";
  }

  typedef Aaa-port-range {
    type uint32 {
      range "1..65535";
    }
    description "Aaa port range";
  }
  typedef Aaa-accounting {
    type enumeration {
      enum not-set {
        value 0;
        description "Not Set";
      }
      enum start-stop {
        value 1;
        description "Start Stop";
      }
      enum stop-only {
        value 2;
        description "Stop Only";
      }
    }
    description "Aaa accounting";
  }
  typedef Aaa-accounting-rp-failover {
    type enumeration {
      enum disable {
        value 0;
        description "Disable rpfailover";
      }
      enum enable {
        value 1;
        description "Enable rpfailover";
      }
    }
    description "Aaa accounting rp failover";
  }
  typedef Aaa-accounting-broadcast {
    type enumeration {
      enum disable {
        value 0;
        description "Disable Broadcast";
      }
      enum enable {
        value 1;
        description "Enable Broadcast";
      }
    }
    description "Aaa accounting broadcast";
  }
  typedef Aaa-method {
    type enumeration {
      enum not-set {
        value 0;
        description "Not Set";
      }
      enum none {
        value 1;
        description "None";
      }
      enum local {
        value 2;
        description "Local";
      }
      enum radius {
        value 3;
        description "Radius";
      }
      enum tacacs-plus {
        value 4;
        description "TACACS+";
      }
      enum dsmd {
        value 5;
        description "DSMD";
      }
      enum sgbp {
        value 6;
        description "SGBP";
      }
      enum acct-d {
        value 7;
        description "AcctD";
      }
      enum error {
        value 8;
        description "Error";
      }
      enum if-authenticated {
        value 9;
        description "If Authenticated";
      }
      enum server-group {
        value 10;
        description "Server Group";
      }
      enum server-group-not-defined {
        value 11;
        description "Server Group Not Defined";
      }
      enum line {
        value 12;
        description "Line";
      }
      enum enable {
        value 13;
        description "Enable";
      }
      enum kerberos {
        value 14;
        description "Kerberos";
      }
      enum diameter {
        value 15;
        description "Diameter";
      }
      enum last {
        value 16;
        description "Last";
      }
    }
    description "Aaa method";
  }
  typedef Aaa-accounting-update {
    type enumeration {
      enum none {
        value 0;
        description "Not Set";
      }
      enum newinfo {
        value 3;
        description
          "Update records for new accountable information
          only";
      }
      enum periodic {
        value 4;
        description "Update records at periodic intervals";
      }
    }
    description "Aaa accounting update";
  }
}
