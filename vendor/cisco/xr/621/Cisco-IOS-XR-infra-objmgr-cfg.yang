module Cisco-IOS-XR-infra-objmgr-cfg {

  /*** NAMESPACE / PREFIX DEFINITION ***/

  namespace "http://cisco.com/ns/yang/Cisco-IOS-XR-infra-objmgr-cfg";


  prefix "infra-objmgr-cfg";

  /*** LINKAGE (IMPORTS / INCLUDES) ***/

  import ietf-inet-types { prefix "inet"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR infra-objmgr package configuration.

     This module contains definitions
     for the following management objects:
       object-group: Object-group configuration

     Copyright (c) 2013-2016 by Cisco Systems, Inc.
     All rights reserved.";

  revision "2015-11-09" {
    description
      "IOS XR 6.0 revision.";
  }

  typedef Start-port {
    type union {
      type enumeration {
        enum echo {
          value 7;
          description "Echo (7)";
        }
        enum discard {
          value 9;
          description "Discard (9)";
        }
        enum daytime {
          value 13;
          description "Daytime (13)";
        }
        enum chargen {
          value 19;
          description "Character generator (19)";
        }
        enum ftp-data {
          value 20;
          description
            "FTP data connections (used infrequently, 20)";
        }
        enum ftp {
          value 21;
          description "File Transfer Protocol (21)";
        }
        enum ssh {
          value 22;
          description "Secure Shell (22)";
        }
        enum telnet {
          value 23;
          description "Telnet (23)";
        }
        enum smtp {
          value 25;
          description "Simple Mail Transport Protocol (25)";
        }
        enum time {
          value 37;
          description "Time (37)";
        }
        enum nicname {
          value 43;
          description "Nicname (43)";
        }
        enum tacacs {
          value 49;
          description "TAC Access Control System (49)";
        }
        enum domain {
          value 53;
          description "Domain Name Service (53)";
        }
        enum gopher {
          value 70;
          description "Gopher (70)";
        }
        enum finger {
          value 79;
          description "Finger (79)";
        }
        enum www {
          value 80;
          description "World Wide Web (HTTP, 80)";
        }
        enum host-name {
          value 101;
          description "NIC hostname server (101)";
        }
        enum pop2 {
          value 109;
          description "Post Office Protocol v2 (109)";
        }
        enum pop3 {
          value 110;
          description "Post Office Protocol v3 (110)";
        }
        enum sun-rpc {
          value 111;
          description "Sun Remote Procedure Call (111)";
        }
        enum ident {
          value 113;
          description "Ident Protocol (113)";
        }
        enum nntp {
          value 119;
          description "Network News Transport Protocol (119)";
        }
        enum bgp {
          value 179;
          description "Border Gateway Protocol (179)";
        }
        enum irc {
          value 194;
          description "Internet Relay Chat (194)";
        }
        enum pim-auto-rp {
          value 496;
          description "PIM Auto-RP (496)";
        }
        enum exec {
          value 512;
          description "Exec (rsh, 512)";
        }
        enum login {
          value 513;
          description "Login (rlogin, 513)";
        }
        enum cmd {
          value 514;
          description "Remote commands (rcmd, 514)";
        }
        enum lpd {
          value 515;
          description "Printer service (515)";
        }
        enum uucp {
          value 540;
          description "Unix-to-Unix Copy Program (540)";
        }
        enum klogin {
          value 543;
          description "Kerberos login (543)";
        }
        enum kshell {
          value 544;
          description "Kerberos shell (544)";
        }
        enum talk {
          value 517;
          description "Talk (517)";
        }
        enum ldp {
          value 646;
          description "LDP session connection attempts (MPLS, 646)";
        }
      }
      type uint32 {
        range "0..65535";
      }
    }
    description "Start port";
  }
  typedef Port-operator {
    type enumeration {
      enum equal {
        value 0;
        description
          "Match packets on ports equal to entered port
          number";
      }
      enum not-equal {
        value 1;
        description
          "Match packets on ports not equal to entered
          port number";
      }
      enum greater-than {
        value 2;
        description
          "Match packets on ports greater than entered
          port number";
      }
      enum less-than {
        value 3;
        description
          "Match packets on ports less than entered port
          number";
      }
    }
    description "Port operator";
  }
  typedef Port {
    type union {
      type enumeration {
        enum echo {
          value 7;
          description "Echo (7)";
        }
        enum discard {
          value 9;
          description "Discard (9)";
        }
        enum daytime {
          value 13;
          description "Daytime (13)";
        }
        enum chargen {
          value 19;
          description "Character generator (19)";
        }
        enum ftp-data {
          value 20;
          description
            "FTP data connections (used infrequently, 20)";
        }
        enum ftp {
          value 21;
          description "File Transfer Protocol (21)";
        }
        enum ssh {
          value 22;
          description "Secure Shell (22)";
        }
        enum telnet {
          value 23;
          description "Telnet (23)";
        }
        enum smtp {
          value 25;
          description "Simple Mail Transport Protocol (25)";
        }
        enum time {
          value 37;
          description "Time (37)";
        }
        enum nicname {
          value 43;
          description "Nicname (43)";
        }
        enum tacacs {
          value 49;
          description "TAC Access Control System (49)";
        }
        enum domain {
          value 53;
          description "Domain Name Service (53)";
        }
        enum gopher {
          value 70;
          description "Gopher (70)";
        }
        enum finger {
          value 79;
          description "Finger (79)";
        }
        enum www {
          value 80;
          description "World Wide Web (HTTP, 80)";
        }
        enum host-name {
          value 101;
          description "NIC hostname server (101)";
        }
        enum pop2 {
          value 109;
          description "Post Office Protocol v2 (109)";
        }
        enum pop3 {
          value 110;
          description "Post Office Protocol v3 (110)";
        }
        enum sun-rpc {
          value 111;
          description "Sun Remote Procedure Call (111)";
        }
        enum ident {
          value 113;
          description "Ident Protocol (113)";
        }
        enum nntp {
          value 119;
          description "Network News Transport Protocol (119)";
        }
        enum bgp {
          value 179;
          description "Border Gateway Protocol (179)";
        }
        enum irc {
          value 194;
          description "Internet Relay Chat (194)";
        }
        enum pim-auto-rp {
          value 496;
          description "PIM Auto-RP (496)";
        }
        enum exec {
          value 512;
          description "Exec (rsh, 512)";
        }
        enum login {
          value 513;
          description "Login (rlogin, 513)";
        }
        enum cmd {
          value 514;
          description "Remote commands (rcmd, 514)";
        }
        enum lpd {
          value 515;
          description "Printer service (515)";
        }
        enum uucp {
          value 540;
          description "Unix-to-Unix Copy Program (540)";
        }
        enum klogin {
          value 543;
          description "Kerberos login (543)";
        }
        enum kshell {
          value 544;
          description "Kerberos shell (544)";
        }
        enum talk {
          value 517;
          description "Talk (517)";
        }
        enum ldp {
          value 646;
          description "LDP session connection attempts (MPLS, 646)";
        }
      }
      type uint32 {
        range "0..65535";
      }
    }
    description "Port";
  }
  typedef End-port {
    type union {
      type enumeration {
        enum echo {
          value 7;
          description "Echo (7)";
        }
        enum discard {
          value 9;
          description "Discard (9)";
        }
        enum daytime {
          value 13;
          description "Daytime (13)";
        }
        enum chargen {
          value 19;
          description "Character generator (19)";
        }
        enum ftp-data {
          value 20;
          description
            "FTP data connections (used infrequently, 20)";
        }
        enum ftp {
          value 21;
          description "File Transfer Protocol (21)";
        }
        enum ssh {
          value 22;
          description "Secure Shell (22)";
        }
        enum telnet {
          value 23;
          description "Telnet (23)";
        }
        enum smtp {
          value 25;
          description "Simple Mail Transport Protocol (25)";
        }
        enum time {
          value 37;
          description "Time (37)";
        }
        enum nicname {
          value 43;
          description "Nicname (43)";
        }
        enum tacacs {
          value 49;
          description "TAC Access Control System (49)";
        }
        enum domain {
          value 53;
          description "Domain Name Service (53)";
        }
        enum gopher {
          value 70;
          description "Gopher (70)";
        }
        enum finger {
          value 79;
          description "Finger (79)";
        }
        enum www {
          value 80;
          description "World Wide Web (HTTP, 80)";
        }
        enum host-name {
          value 101;
          description "NIC hostname server (101)";
        }
        enum pop2 {
          value 109;
          description "Post Office Protocol v2 (109)";
        }
        enum pop3 {
          value 110;
          description "Post Office Protocol v3 (110)";
        }
        enum sun-rpc {
          value 111;
          description "Sun Remote Procedure Call (111)";
        }
        enum ident {
          value 113;
          description "Ident Protocol (113)";
        }
        enum nntp {
          value 119;
          description "Network News Transport Protocol (119)";
        }
        enum bgp {
          value 179;
          description "Border Gateway Protocol (179)";
        }
        enum irc {
          value 194;
          description "Internet Relay Chat (194)";
        }
        enum pim-auto-rp {
          value 496;
          description "PIM Auto-RP (496)";
        }
        enum exec {
          value 512;
          description "Exec (rsh, 512)";
        }
        enum login {
          value 513;
          description "Login (rlogin, 513)";
        }
        enum cmd {
          value 514;
          description "Remote commands (rcmd, 514)";
        }
        enum lpd {
          value 515;
          description "Printer service (515)";
        }
        enum uucp {
          value 540;
          description "Unix-to-Unix Copy Program (540)";
        }
        enum klogin {
          value 543;
          description "Kerberos login (543)";
        }
        enum kshell {
          value 544;
          description "Kerberos shell (544)";
        }
        enum talk {
          value 517;
          description "Talk (517)";
        }
        enum ldp {
          value 646;
          description "LDP session connection attempts (MPLS, 646)";
        }
      }
      type uint32 {
        range "0..65535";
      }
    }
    description "End port";
  }

  container object-group {
    description "Object-group configuration";

    container port {
      description "Port object group";

      container udf-objects {
        description "Table of port objects groups";

        list udf-object {
          key "object-name";
          description "Port object group";

          container operators {
            description "Table of port operators";

            list operator {
              key "operator-type port";
              description "op class";
              leaf operator-type {
                type Port-operator;
                description "operation for ports";
              }
              leaf port {
                type Port;
                description "Port number";
              }
            }
          }

          container nested-groups {
            description "Table of nested port object groups";

            list nested-group {
              key "nested-group-name";
              description "nested object group";
              leaf nested-group-name {
                type xr:Cisco-ios-xr-string {
                  length "1..64";
                }
                description "Name of a nested object group";
              }
            }
          }

          container port-ranges {
            description "Table of port range addresses";

            list port-range {
              key "start-port end-port";
              description
                "Match only packets on a given port range";
              leaf start-port {
                type Start-port;
                description "Port number";
              }
              leaf end-port {
                type End-port;
                description "Port number";
              }
            }
          }
          leaf description {
            type string {
              length "1..100";
            }
            description
              "Up to 100 characters describing this object";
          }
          leaf object-name {
            type xr:Cisco-ios-xr-string {
              length "1..64";
            }
            description
              "Port object group name - maximum 64
              characters";
          }
        }
      }
    }

    container network {
      description "Network object group";

      container ipv6 {
        description "IPv6 object group";

        container udf-objects {
          description "Table of ipv6 object groups";

          list udf-object {
            key "object-name";
            description "IPv6 object group";

            container nested-groups {
              description "Table of nested ipv6 object groups";

              list nested-group {
                key "nested-group-name";
                description "nested object group";
                leaf nested-group-name {
                  type xr:Cisco-ios-xr-string {
                    length "1..64";
                  }
                  description
                    "Enter the name of a nested object group";
                }
              }
            }

            container address-ranges {
              description "Table of ipv6 address ranges";

              list address-range {
                key "start-address end-address";
                description "Range of host addresses";
                leaf start-address {
                  type inet:ip-address-no-zone;
                  description "IPv6 address";
                }
                leaf end-address {
                  type inet:ip-address-no-zone;
                  description "IPv6 address";
                }
              }
            }

            container addresses {
              description "Table of ipv6 addresses";

              list address {
                key "prefix prefix-length";
                description "IPv6 address";
                leaf prefix {
                  type inet:ip-address-no-zone;
                  description "IPv6 prefix x:x::x/y";
                }
                leaf prefix-length {
                  type xr:Ipv6-prefix-length;
                  description "Prefix of the IP Address";
                }
              }
            }

            container hosts {
              description "Table of ipv6 host addresses";

              list host {
                key "host-address";
                description "A single host address";
                leaf host-address {
                  type inet:ip-address-no-zone;
                  description "host ipv6 address";
                }
              }
            }
            leaf description {
              type string {
                length "1..100";
              }
              description
                "Up to 100 characters describing this object";
            }
            leaf object-name {
              type xr:Cisco-ios-xr-string {
                length "1..64";
              }
              description
                "IPv6 object group name - maximum 64
                characters";
            }
          }
        }
      }

      container ipv4 {
        description "IPv4 object group";

        container udf-objects {
          description "Table of ipv4 object groups";

          list udf-object {
            key "object-name";
            description "IPv4 object group";

            container nested-groups {
              description "Table of nested ipv4 object groups";

              list nested-group {
                key "nested-group-name";
                description "Nested object group";
                leaf nested-group-name {
                  type xr:Cisco-ios-xr-string {
                    length "1..64";
                  }
                  description "Nested object group";
                }
              }
            }

            container address-ranges {
              description "Table of ipv4 host address ranges";

              list address-range {
                key "start-address end-address";
                description "Range of host addresses";
                leaf start-address {
                  type inet:ip-address-no-zone;
                  description "IPv4 address";
                }
                leaf end-address {
                  type inet:ip-address-no-zone;
                  description "IPv4 address";
                }
              }
            }

            container addresses {
              description "Table of addresses";

              list address {
                key "prefix prefix-length";
                description "IPv4 address";
                leaf prefix {
                  type inet:ip-address-no-zone;
                  description "IPv4 address/prefix";
                }
                leaf prefix-length {
                  type xr:Ipv4-prefix-length;
                  description "Prefix of the IP Address";
                }
              }
            }

            container hosts {
              description "Table of host addresses";

              list host {
                key "host-address";
                description "A single host address";
                leaf host-address {
                  type inet:ip-address-no-zone;
                  description "Host ipv4 address";
                }
              }
            }
            leaf description {
              type string {
                length "1..100";
              }
              description
                "Up to 100 characters describing this object";
            }
            leaf object-name {
              type xr:Cisco-ios-xr-string {
                length "1..64";
              }
              description
                "IPv4 object group name - maximum 64
                characters";
            }
          }
        }
      }
    }
  }
}
