module Cisco-IOS-XR-um-cont-port-mode-cfg {
  namespace "http://cisco.com/ns/yang/Cisco-IOS-XR-um-cont-port-mode-cfg";
  prefix um-cont-port-mode-cfg;

  import Cisco-IOS-XR-um-interface-cfg {
    prefix a1;
  }
  import tailf-common {
    prefix tailf;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR cont-port-mode package configuration.
     
     This YANG module augments the
     modules with configuration data.
     
     Copyright (c) 2020-2022 by Cisco Systems, Inc.
     All rights reserved.";

  revision 2022-06-28 {
    description
      "Removed none option from rate node under ethernet";
    semver:module-version "1.0.1M";
  }
  revision 2020-08-20 {
    description
      "Initial release";
    semver:module-version "1.0.0";
  }

  feature optics {
    description
      "optics";
  }

  grouping CONT-BODY {
    container port-mode {
      when "../a1:controller-name[starts-with(text(),'Optics')]" {
        tailf:dependency "../a1:controller-name";
      }
      if-feature "optics";
      description
        "Configure the port-mode";
      container ethernet {
        must "not(../fc or ../otn or ../sdh or ../sonet or ../cpri)";
        presence "Indicates a ethernet node is configured.";
        description
          "Ethernet portmode type";
        leaf framing {
          type enumeration {
            enum "opu0" {
              value 1;
              description
                "opu0 for framing";
            }
            enum "opu1e" {
              value 3;
              description
                "opu1e for framing";
            }
            enum "opu2" {
              value 5;
              description
                "opu2 for framing";
            }
            enum "opu2e" {
              value 6;
              description
                "opu2e for framing";
            }
            enum "opu3" {
              value 8;
              description
                "opu3 for framing";
            }
            enum "opu3e1" {
              value 9;
              description
                "opu3e1 for framing";
            }
            enum "opu3e2" {
              value 10;
              description
                "opu3e2 for framing";
            }
            enum "opu4" {
              value 11;
              description
                "opu4 for framing";
            }
            enum "opuflex" {
              value 12;
              description
                "opuflex for framing";
            }
            enum "packet" {
              value 15;
              description
                "packet for framing";
            }
          }
          mandatory true;
          description
            "framing for portmode";
        }
        leaf mapping {
          when "../framing != 'opu3e1' and ../framing != 'opu3e2' and ../framing != 'packet'";
          type enumeration {
            enum "bmp" {
              value 3;
              description
                "bmp for mapping";
            }
            enum "gmp" {
              value 4;
              description
                "gmp for mapping";
            }
            enum "GfpF" {
              value 1;
              description
                "gfp_f for mapping";
            }
            enum "GfpF-Ext" {
              value 6;
              description
                "gfp_f_ext for mapping";
            }
            enum "wis" {
              value 5;
              description
                "wis for mapping";
            }
          }
          description
            "mapping for portmode";
        }
        leaf rate {
          when "../mapping = 'wis' or ../framing = 'opuflex'";
          type enumeration {
            enum "OC192" {
              value 4;
              description
                "oc192 for rate";
            }
            enum "STM64" {
              value 9;
              description
                "STM64 for rate";
            }
            enum "100GE" {
              value 11;
              description
                "100GE for rate";
            }
            enum "10GE" {
              value 12;
              description
                "10GE for rate";
            }
            enum "40GE" {
              value 13;
              description
                "40GE for rate";
            }
            enum "1GE" {
              value 14;
              description
                "1GE for rate";
            }
            enum "25GE" {
              value 15;
              description
                "25GE for rate";
            }
          }
          description
            "Portmode rate";
        }
      }
      container sonet {
        must "not(../fc or ../otn or ../sdh or ../ethernet or ../cpri)";
        presence "Indicates a sonet node is configured.";
        description
          "Sonet portmode type";
        leaf framing {
          type enumeration {
            enum "opu0" {
              value 1;
              description
                "opu0 for framing";
            }
            enum "opu1" {
              value 2;
              description
                "opu1 for framing";
            }
            enum "opu2" {
              value 5;
              description
                "opu2 for framing";
            }
            enum "opu3" {
              value 8;
              description
                "opu3 for framing";
            }
            enum "WIS" {
              value 16;
              description
                "Wis for framing";
            }
          }
          mandatory true;
          description
            "framing for portmode";
        }
        leaf mapping {
          type enumeration {
            enum "amp" {
              value 2;
              description
                "amp for mapping";
            }
            enum "bmp" {
              value 3;
              description
                "bmp for mapping";
            }
            enum "gmp" {
              value 4;
              description
                "gmp for mapping";
            }
          }
          description
            "mapping for portmode";
        }
        leaf rate {
          when "../framing = 'opu0'";
          type enumeration {
            enum "none" {
              value 0;
              description
                "No rate";
            }
            enum "OC12" {
              value 2;
              description
                "OC12 for rate";
            }
            enum "OC3" {
              value 1;
              description
                "OC3 for rate";
            }
          }
          description
            "Portmode rate";
        }
      }
      container fc {
        must "not(../sonet or ../otn or ../sdh or ../ethernet or ../cpri)";
        presence "Indicates a fc node is configured.";
        description
          "FC portmode type";
        leaf framing {
          type enumeration {
            enum "opu1f" {
              value 4;
              description
                "opu1f for framing";
            }
            enum "opu2" {
              value 5;
              description
                "opu2 for framing";
            }
            enum "opu2e" {
              value 6;
              description
                "opu2e for framing";
            }
            enum "opu2f" {
              value 7;
              description
                "opu2f for framing";
            }
          }
          mandatory true;
          description
            "framing for portmode";
        }
      }
      container otn {
        must "not(../sonet or ../fc or ../sdh or ../ethernet or ../cpri)";
        presence "Indicates a otn node is configured.";
        description
          "Otn portmode type";
        leaf framing {
          type enumeration {
            enum "opu1" {
              value 2;
              description
                "opu1 for framing";
            }
            enum "opu1e" {
              value 3;
              description
                "opu1e for framing";
            }
            enum "opu1f" {
              value 4;
              description
                "opu1e for framing";
            }
            enum "opu2" {
              value 5;
              description
                "opu2 for framing";
            }
            enum "opu2e" {
              value 6;
              description
                "opu2e for framing";
            }
            enum "opu2f" {
              value 7;
              description
                "opu2e for framing";
            }
            enum "opu3" {
              value 8;
              description
                "opu3 for framing";
            }
            enum "opu3e1" {
              value 9;
              description
                "opu3e1 for framing";
            }
            enum "opu3e2" {
              value 10;
              description
                "opu3e2 for framing";
            }
            enum "opu4" {
              value 11;
              description
                "opu4 for framing";
            }
            enum "opuc2" {
              value 13;
              description
                "opuc2 for framing";
            }
            enum "opuc4" {
              value 14;
              description
                "opuc4 for framing";
            }
            enum "opuflex" {
              value 12;
              description
                "opuflex for framing";
            }
          }
          mandatory true;
          description
            "framing for portmode";
        }
      }
      container sdh {
        must "not(../sonet or ../fc or ../otn or ../ethernet or ../cpri)";
        presence "Indicates a sdh node is configured.";
        description
          "SDH portmode type";
        leaf framing {
          type enumeration {
            enum "opu0" {
              value 1;
              description
                "opu0 for framing";
            }
            enum "opu1" {
              value 2;
              description
                "opu1 for framing";
            }
            enum "opu2" {
              value 5;
              description
                "opu2 for framing";
            }
            enum "opu3" {
              value 8;
              description
                "opu3 for framing";
            }
            enum "WIS" {
              value 16;
              description
                "WIS for framing";
            }
          }
          mandatory true;
          description
            "framing for portmode";
        }
        leaf mapping {
          type enumeration {
            enum "none" {
              value 0;
              description
                "No mapping";
            }
            enum "amp" {
              value 2;
              description
                "amp for mapping";
            }
            enum "bmp" {
              value 3;
              description
                "bmp for mapping";
            }
            enum "gmp" {
              value 4;
              description
                "gmp for mapping";
            }
          }
          description
            "mapping for portmode";
        }
        leaf rate {
          when "../mapping = 'opu0'";
          type enumeration {
            enum "none" {
              value 0;
              description
                "No rate value";
            }
            enum "STM1" {
              value 6;
              description
                "STM1 for rate";
            }
            enum "STM4" {
              value 7;
              description
                "STM4 for rate";
            }
          }
          description
            "Portmode rate";
        }
      }
      container cpri {
        must "not(../sonet or ../fc or ../otn or ../ethernet or ../sdh)";
        must "role/primary or role/subordinate";
        presence "Indicates a cpri node is configured.";
        description
          "port-mode type cpri";
        container role {
          description
            "this cpri controller node's role";
          container primary {
            must "not(../subordinate)";
            presence "Indicates a primary node is configured.";
            description
              "CPRI port act as primary";
          }
          container subordinate {
            must "not(../primary)";
            presence "Indicates a subordinate node is configured.";
            description
              "CPRI port act as subordinate";
          }
          leaf-list datarate-list {
            type enumeration {
              enum "614" {
                value 1;
                description
                  "Rate of    614 MB";
              }
              enum "1228" {
                value 2;
                description
                  "Rate of  1.228 GB";
              }
              enum "2457" {
                value 3;
                description
                  "Rate of  2.457 GB";
              }
              enum "3072" {
                value 4;
                description
                  "Rate of  3.072 GB";
              }
              enum "4915" {
                value 5;
                description
                  "Rate of  4.915 GB";
              }
              enum "6144" {
                value 6;
                description
                  "Rate of  6.144 GB";
              }
              enum "9830" {
                value 7;
                description
                  "Rate of  9.830 GB";
              }
              enum "10137" {
                value 9;
                description
                  "Rate of 10.137 GB";
              }
            }
            min-elements 1;
            max-elements "4";
            description
              "rate list for cpri port";
          }
        }
      }
    }
    container breakout-modes {
      when "../a1:controller-name[starts-with(text(),'Optics')]" {
        tailf:dependency "../a1:controller-name";
      }
      if-feature "optics";
      description
        "Configure the breakout-mode";
      list breakout-mode {
        must "ethernet or fc or otn or sdh or sonet";
        key "lane-number";
        description
          "Configure the breakout-mode";
        leaf lane-number {
          type uint32 {
            range "1..10" {
              description
                "Lane number ";
            }
          }
          description
            "Configure the breakout-mode";
        }
        container ethernet {
          must "not(../fc or ../otn or ../sdh or ../sonet)";
          presence "Indicates a ethernet node is configured.";
          description
            "Ethernet portmode type";
          leaf framing {
            type enumeration {
              enum "opu0" {
                value 1;
                description
                  "opu0 for framing";
              }
              enum "opu1e" {
                value 3;
                description
                  "opu1e for framing";
              }
              enum "opu2" {
                value 5;
                description
                  "opu2 for framing";
              }
              enum "opu2e" {
                value 6;
                description
                  "opu2e for framing";
              }
              enum "opu3" {
                value 8;
                description
                  "opu3 for framing";
              }
              enum "opu3e1" {
                value 9;
                description
                  "opu3e1 for framing";
              }
              enum "opu3e2" {
                value 10;
                description
                  "opu3e2 for framing";
              }
              enum "opu4" {
                value 11;
                description
                  "opu4 for framing";
              }
              enum "opuflex" {
                value 12;
                description
                  "opuflex for framing";
              }
              enum "packet" {
                value 15;
                description
                  "packet for framing";
              }
            }
            mandatory true;
            description
              "framing for portmode";
          }
          leaf mapping {
            when "../framing != 'opu3e1' and ../framing != 'opu3e2' and ../framing != 'packet'";
            type enumeration {
              enum "bmp" {
                value 3;
                description
                  "bmp for mapping";
              }
              enum "gmp" {
                value 4;
                description
                  "gmp for mapping";
              }
              enum "GfpF" {
                value 1;
                description
                  "gfp_f for mapping";
              }
              enum "GfpF-Ext" {
                value 6;
                description
                  "gfp_f_ext for mapping";
              }
              enum "wis" {
                value 5;
                description
                  "wis for mapping";
              }
            }
            description
              "mapping for portmode";
          }
          leaf rate {
            when "../mapping = 'wis' or ../framing = 'opuflex'";
            type enumeration {
              enum "none" {
                value 0;
                description
                  "No rate";
              }
              enum "OC192" {
                value 4;
                description
                  "oc192 for rate";
              }
              enum "STM64" {
                value 9;
                description
                  "STM64 for rate";
              }
              enum "100GE" {
                value 11;
                description
                  "100GE for rate";
              }
              enum "10GE" {
                value 12;
                description
                  "10GE for rate";
              }
              enum "40GE" {
                value 13;
                description
                  "40GE for rate";
              }
              enum "1GE" {
                value 14;
                description
                  "1GE for rate";
              }
              enum "25GE" {
                value 15;
                description
                  "25GE for rate";
              }
            }
            description
              "Portmode rate";
          }
        }
        container sonet {
          must "not(../fc or ../otn or ../sdh or ../ethernet)";
          presence "Indicates a sonet node is configured.";
          description
            "Sonet portmode type";
          leaf framing {
            type enumeration {
              enum "opu0" {
                value 1;
                description
                  "opu0 for framing";
              }
              enum "opu1" {
                value 2;
                description
                  "opu1 for framing";
              }
              enum "opu2" {
                value 5;
                description
                  "opu2 for framing";
              }
              enum "opu3" {
                value 8;
                description
                  "opu3 for framing";
              }
              enum "WIS" {
                value 16;
                description
                  "Wis for framing";
              }
            }
            mandatory true;
            description
              "framing for portmode";
          }
          leaf mapping {
            type enumeration {
              enum "amp" {
                value 2;
                description
                  "amp for mapping";
              }
              enum "bmp" {
                value 3;
                description
                  "bmp for mapping";
              }
              enum "gmp" {
                value 4;
                description
                  "gmp for mapping";
              }
            }
            description
              "mapping for portmode";
          }
          leaf rate {
            when "../framing = 'opu0'";
            type enumeration {
              enum "none" {
                value 0;
                description
                  "No rate";
              }
              enum "OC12" {
                value 2;
                description
                  "OC12 for rate";
              }
              enum "OC3" {
                value 1;
                description
                  "OC3 for rate";
              }
            }
            description
              "Portmode rate";
          }
        }
        container fc {
          must "not(../sonet or ../otn or ../sdh or ../ethernet)";
          presence "Indicates a fc node is configured.";
          description
            "FC portmode type";
          leaf framing {
            type enumeration {
              enum "opu1f" {
                value 4;
                description
                  "opu1f for framing";
              }
              enum "opu2" {
                value 5;
                description
                  "opu2 for framing";
              }
              enum "opu2e" {
                value 6;
                description
                  "opu2e for framing";
              }
              enum "opu2f" {
                value 7;
                description
                  "opu2f for framing";
              }
            }
            mandatory true;
            description
              "framing for portmode";
          }
        }
        container otn {
          must "not(../sonet or ../fc or ../sdh or ../ethernet)";
          presence "Indicates a otn node is configured.";
          description
            "Otn portmode type";
          leaf framing {
            type enumeration {
              enum "opu1" {
                value 2;
                description
                  "opu1 for framing";
              }
              enum "opu1e" {
                value 3;
                description
                  "opu1e for framing";
              }
              enum "opu1f" {
                value 4;
                description
                  "opu1e for framing";
              }
              enum "opu2" {
                value 5;
                description
                  "opu2 for framing";
              }
              enum "opu2e" {
                value 6;
                description
                  "opu2e for framing";
              }
              enum "opu2f" {
                value 7;
                description
                  "opu2e for framing";
              }
              enum "opu3" {
                value 8;
                description
                  "opu3 for framing";
              }
              enum "opu3e1" {
                value 9;
                description
                  "opu3e1 for framing";
              }
              enum "opu3e2" {
                value 10;
                description
                  "opu3e2 for framing";
              }
              enum "opu4" {
                value 11;
                description
                  "opu4 for framing";
              }
              enum "opuc2" {
                value 13;
                description
                  "opuc2 for framing";
              }
              enum "opuc4" {
                value 14;
                description
                  "opuc4 for framing";
              }
              enum "opuflex" {
                value 12;
                description
                  "opuflex for framing";
              }
            }
            mandatory true;
            description
              "framing for portmode";
          }
        }
        container sdh {
          must "not(../sonet or ../fc or ../otn or ../ethernet)";
          presence "Indicates a sdh node is configured.";
          description
            "SDH portmode type";
          leaf framing {
            type enumeration {
              enum "opu0" {
                value 1;
                description
                  "opu0 for framing";
              }
              enum "opu1" {
                value 2;
                description
                  "opu1 for framing";
              }
              enum "opu2" {
                value 5;
                description
                  "opu2 for framing";
              }
              enum "opu3" {
                value 8;
                description
                  "opu3 for framing";
              }
            }
            mandatory true;
            description
              "framing for portmode";
          }
          leaf mapping {
            type enumeration {
              enum "amp" {
                value 2;
                description
                  "amp for mapping";
              }
              enum "bmp" {
                value 3;
                description
                  "bmp for mapping";
              }
              enum "gmp" {
                value 4;
                description
                  "gmp for mapping";
              }
            }
            description
              "mapping for portmode";
          }
          leaf rate {
            when "../mapping = 'opu0'";
            type enumeration {
              enum "none" {
                value 0;
                description
                  "STM1 for rate";
              }
              enum "STM1" {
                value 6;
                description
                  "STM1 for rate";
              }
              enum "STM4" {
                value 7;
                description
                  "STM4 for rate";
              }
            }
            description
              "Portmode rate";
          }
        }
      }
    }
  }

  augment "/a1:interfaces/a1:controller" {
    uses CONT-BODY;
  }
  augment "/a1:interfaces/a1:controller-preconfigure" {
    uses CONT-BODY;
  }
  container hw-module {
    description
      "Configure h/w module";
    container ains {
      description
        "Configure AINS Params";
      leaf set-default-time {
        type uint32 {
          range "0..2880" {
            description
              "ains timer in minutes";
          }
        }
        description
          "Set default ains time";
      }
    }
  }
}
