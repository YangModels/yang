module Cisco-IOS-XR-um-subscriber-ush-cfg {
  namespace "http://cisco.com/ns/yang/Cisco-IOS-XR-um-subscriber-ush-cfg";
  prefix um-subscriber-ush-cfg;

  import Cisco-IOS-XR-types {
    prefix xr;
  }
  import Cisco-IOS-XR-um-subscriber-cfg {
    prefix a1;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR subscriber-ush package configuration.
     
     This YANG module augments the
     modules with configuration data.
     
     Copyright (c) 2020-2021 by Cisco Systems, Inc.
     All rights reserved.";

  revision 2021-04-23 {
    description
      "Initial release";
    semver:module-version "1.0.0";
  }

  augment "/a1:subscriber" {
    container ush {
      description
        "Unified Session History";
      container enable {
        presence "Indicates a enable node is configured.";
        description
          "Enable Unified Session History";
      }
      container interfaces {
        description
          "enable for specific interfaces";
        list interface {
          key "interface-name";
          description
            "enable for specific interfaces";
          leaf interface-name {
            type xr:Interface-name;
            description
              "enable for specific interfaces";
          }
        }
      }
    }
  }
}
