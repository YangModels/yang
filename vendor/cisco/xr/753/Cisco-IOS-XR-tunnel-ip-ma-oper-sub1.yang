submodule Cisco-IOS-XR-tunnel-ip-ma-oper-sub1 {
  belongs-to Cisco-IOS-XR-tunnel-ip-ma-oper {
    prefix Cisco-IOS-XR-tunnel-ip-ma-oper;
  }

  import ietf-inet-types {
    prefix inet;
  }
  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR tunnel-ip-ma package operational data.
     
     Copyright (c) 2013-2022 by Cisco Systems, Inc.
     All rights reserved.";

  revision 2022-02-26 {
    description
      "Added a field in tunl_gre_ma_edm_idb structure for source direct address";
    semver:module-version "1.2.0";
  }
  revision 2021-02-25 {
    description
      "Added an entry for src addr db in bag";
    semver:module-version "1.1.0";
  }
  revision 2019-04-05 {
    description
      "Establish semantic version baseline.";
    semver:module-version "1.0.1";
  }
  revision 2018-10-09 {
    description
      "Modified hierarchy for endpoints, gspnode-db and application-db-stats";
  }
  revision 2015-11-09 {
    description
      "IOS XR 6.0 revision.";
  }

  typedef Tunl-gre-ka-states {
    type enumeration {
      enum "tunl-gre-ka-state-disabled" {
        description
          "tunl gre ka state disabled";
      }
      enum "tunl-gre-ka-state-enabled" {
        description
          "tunl gre ka state enabled";
      }
      enum "tunl-gre-ka-state-success" {
        description
          "tunl gre ka state success";
      }
      enum "tunl-gre-ka-state-check" {
        description
          "tunl gre ka state check";
      }
      enum "tunl-gre-ka-state-failed" {
        description
          "tunl gre ka state failed";
      }
      enum "tunl-gre-ka-state-max" {
        description
          "tunl gre ka state max";
      }
    }
    description
      "Tunl gre ka states";
  }

  typedef Tunl-ip-tunl-flag-bits {
    type enumeration {
      enum "tunl-ip-flag-bits-none" {
        value 0;
        description
          "tunl ip flag bits none";
      }
      enum "tunl-ip-flag-bfd-state-up" {
        value 1;
        description
          "tunl ip flag bfd state up";
      }
      enum "tunl-ip-flag-bfd-state-down" {
        value 2;
        description
          "tunl ip flag bfd state down";
      }
      enum "tunl-ip-flag-bfd-period" {
        value 4;
        description
          "tunl ip flag bfd period";
      }
      enum "tunl-ip-flag-bfd-retry" {
        value 8;
        description
          "tunl ip flag bfd retry";
      }
      enum "tunl-ip-flag-bfd-set" {
        value 16;
        description
          "tunl ip flag bfd set";
      }
      enum "tunl-ip-flag-bfd-running" {
        value 32;
        description
          "tunl ip flag bfd running";
      }
    }
    description
      "Tunl ip tunl flag bits";
  }

  typedef Tunl-ip-transport-proto {
    type enumeration {
      enum "tunl-ip-transport-ipv4" {
        value 0;
        description
          "tunl ip transport ipv4";
      }
      enum "tunl-ip-transport-ipv6" {
        value 1;
        description
          "tunl ip transport ipv6";
      }
      enum "tunl-ip-transport-max" {
        value 2;
        description
          "tunl ip transport max";
      }
    }
    description
      "Tunl ip transport proto";
  }

  typedef Tunl-ip-tunl-flag {
    type enumeration {
      enum "tunl-ip-flag-dest-connected" {
        value -2147483648;
        description
          "tunl ip flag dest connected";
      }
      enum "tunl-ip-flag-none" {
        value 0;
        description
          "tunl ip flag none";
      }
      enum "tunl-ip-flag-dfbit-disable" {
        value 1;
        description
          "tunl ip flag dfbit disable";
      }
      enum "tunl-ip-flag-ka" {
        value 2;
        description
          "tunl ip flag ka";
      }
      enum "tunl-ip-flag-tos" {
        value 4;
        description
          "tunl ip flag tos";
      }
      enum "tunl-ip-flag-gre-key" {
        value 8;
        description
          "tunl ip flag gre key";
      }
      enum "tunl-ip-flag-src-up" {
        value 16;
        description
          "tunl ip flag src up";
      }
      enum "tunl-ip-flag-dest-reach" {
        value 32;
        description
          "tunl ip flag dest reach";
      }
      enum "tunl-ip-flag-dest-reach-conv" {
        value 64;
        description
          "tunl ip flag dest reach conv";
      }
      enum "tunl-ip-flag-dest-local" {
        value 128;
        description
          "tunl ip flag dest local";
      }
      enum "tunl-ip-flag-dest-tunl" {
        value 256;
        description
          "tunl ip flag dest tunl";
      }
      enum "tunl-ip-flag-dest-db-added" {
        value 512;
        description
          "tunl ip flag dest db added";
      }
      enum "tunl-ip-flag-intf-state-up" {
        value 1024;
        description
          "tunl ip flag intf state up";
      }
      enum "tunl-ip-flag-intf-state-admin-down" {
        value 2048;
        description
          "tunl ip flag intf state admin down";
      }
      enum "tunl-ip-flag-bc-state-up" {
        value 4096;
        description
          "tunl ip flag bc state up";
      }
      enum "tunl-ip-flag-ipv4-caps" {
        value 8192;
        description
          "tunl ip flag ipv4 caps";
      }
      enum "tunl-ip-flag-ipv6-caps" {
        value 16384;
        description
          "tunl ip flag ipv6 caps";
      }
      enum "tunl-ip-flag-mpls-caps" {
        value 32768;
        description
          "tunl ip flag mpls caps";
      }
      enum "tunl-ip-flag-src-dst-inval" {
        value 65536;
        description
          "tunl ip flag src dst inval";
      }
      enum "tunl-ip-flag-trans-vrf" {
        value 131072;
        description
          "tunl ip flag trans vrf";
      }
      enum "tunl-ip-flag-gre-key-enable" {
        value 262144;
        description
          "tunl ip flag gre key enable";
      }
      enum "tunl-ip-flag-src-intf-ip-vrf-valid" {
        value 524288;
        description
          "tunl ip flag src intf ip vrf valid";
      }
      enum "tunl-ip-flag-decap" {
        value 1048576;
        description
          "tunl ip flag decap";
      }
      enum "tunl-ip-flag-line-state" {
        value 2097152;
        description
          "tunl ip flag line state";
      }
      enum "tunl-ip-flag-mark" {
        value 4194304;
        description
          "tunl ip flag mark";
      }
      enum "tunl-ip-flag-encap-in-sw" {
        value 8388608;
        description
          "tunl ip flag encap in sw";
      }
      enum "tunl-ip-flag-dfbit-copy" {
        value 16777216;
        description
          "tunl ip flag dfbit copy";
      }
      enum "tunl-ip-flag-mtu-cfg" {
        value 33554432;
        description
          "tunl ip flag mtu cfg";
      }
      enum "tunl-ip-flag-item-exists" {
        value 67108864;
        description
          "tunl ip flag item exists";
      }
      enum "tunl-ip-flag-create-if" {
        value 134217728;
        description
          "tunl ip flag create if";
      }
      enum "tunl-ip-flag-dest-acl" {
        value 268435456;
        description
          "tunl ip flag dest acl";
      }
      enum "tunl-ip-flag-ttl-cfg" {
        value 536870912;
        description
          "tunl ip flag ttl cfg";
      }
      enum "tunl-ip-flag-encap" {
        value 1073741824;
        description
          "tunl ip flag encap";
      }
    }
    description
      "Tunl ip tunl flag";
  }

  typedef Tunl-ip-mode-dir {
    type enumeration {
      enum "tunl-ip-mode-dir-none" {
        description
          "tunl ip mode dir none";
      }
      enum "tunl-ip-mode-dir-decap" {
        description
          "tunl ip mode dir decap";
      }
      enum "tunl-ip-mode-dir-encap" {
        description
          "tunl ip mode dir encap";
      }
      enum "tunl-ip-mode-dir-max" {
        description
          "tunl ip mode dir max";
      }
    }
    description
      "Tunl ip mode dir";
  }

  typedef Tunl-ip-mode {
    type enumeration {
      enum "tunl-ip-mode-none" {
        value 0;
        description
          "tunl ip mode none";
      }
      enum "tunl-ip-mode-gr-eo-ipv4" {
        value 1;
        description
          "tunl ip mode gr eo ipv4";
      }
      enum "tunl-ip-mode-gr-eo-ipv6" {
        value 2;
        description
          "tunl ip mode gr eo ipv6";
      }
      enum "tunl-ip-mode-mgr-eo-ipv4" {
        value 3;
        description
          "tunl ip mode mgr eo ipv4";
      }
      enum "tunl-ip-mode-mgr-eo-ipv6" {
        value 4;
        description
          "tunl ip mode mgr eo ipv6";
      }
      enum "tunl-ip-mode-ipv4" {
        value 5;
        description
          "tunl ip mode ipv4";
      }
      enum "tunl-ip-mode-ipv6" {
        value 6;
        description
          "tunl ip mode ipv6";
      }
      enum "tunl-ip-mode-max" {
        value 7;
        description
          "tunl ip mode max";
      }
    }
    description
      "Tunl ip mode";
  }

  typedef Tunl-in6-addr {
    type inet:ipv6-address;
    description
      "Tunl in6 addr";
  }

  typedef Tunl-in-addr {
    type inet:ipv4-address;
    description
      "Tunl in addr";
  }

  typedef Tunl-af-id {
    type enumeration {
      enum "tunl-af-id-none" {
        value 0;
        description
          "Unspecified AFI";
      }
      enum "tunl-af-id-ipv4" {
        value 2;
        description
          "IPv4 AFI";
      }
      enum "tunl-af-id-ipv6" {
        value 10;
        description
          "IPv6 AFI";
      }
    }
    description
      "Tunl af id";
  }

  grouping TUNL-P2MP-MA-EDM-OVERLAY {
    description
      "TUNL P2MP MA EDM OVERLAY";
    container overlay-address {
      description
        "Overlay Address";
      uses IP-ADDR-UNION;
    }
    leaf adjacency {
      type uint32;
      description
        "Adjacency";
    }
    leaf stale-flag {
      type boolean;
      description
        "Stale Flag";
    }
  }

  grouping TUNL-P2MP-MA-EDM-TED-DB {
    description
      "TUNL P2MP MA EDM TED DB";
    container transport-address {
      description
        "Transport Address";
      uses IP-ADDR-UNION;
    }
    list overlay-array {
      description
        "Overlay Address";
      uses TUNL-P2MP-MA-EDM-OVERLAY;
    }
  }

  grouping TUNL-P2MP-MA-EDM-TED-DB-ARRAY {
    description
      "Array of TED DB entries BAG";
    leaf tunnel-id-xr {
      type uint32;
      description
        "Tunnel id";
    }
    leaf tunnel-mode {
      type Tunl-ip-mode;
      description
        "Mode of Tunnel";
    }
    leaf endpt-count {
      type uint32;
      description
        "Endpoint count";
    }
    list ted-db-array {
      description
        "Array of MA TED DB";
      uses TUNL-P2MP-MA-EDM-TED-DB;
    }
  }

  grouping TUNL-P2MP-MA-EDM-APP-PROD {
    description
      "app_prod BAG";
    leaf is-valid {
      type boolean;
      description
        "Is valid flag";
    }
    leaf reg-status {
      type boolean;
      description
        "Register status";
    }
    leaf eod-recvd {
      type boolean;
      description
        "EOD received";
    }
    leaf endpt-prod {
      type boolean;
      description
        "Is endpt producer";
    }
    leaf is-tmr-run {
      type boolean;
      description
        "Is timer running";
    }
    leaf endpt-count {
      type uint32;
      description
        "Endpt count";
    }
  }

  grouping TUNL-P2MP-MA-EDM-APP-PROD-ARRAY {
    description
      "Array of APP PROD entries BAG";
    list app-prod-array {
      description
        "APP_PROD array";
      uses TUNL-P2MP-MA-EDM-APP-PROD;
    }
  }

  grouping TUNL-IP-MA-EDM-CHKPT {
    description
      "TUNL IP MA EDM CHKPT";
    container source-address {
      description
        "Tunnel Source Interface Address";
      uses IP-ADDR-UNION;
    }
    leaf tunnel-id {
      type uint32;
      description
        "Tunnel ID";
    }
    leaf flags {
      type uint32;
      description
        "Interface State and Basecap State flags";
    }
    leaf platform-tunnel-id {
      type uint16;
      description
        "Platform Tunnel ID";
    }
    leaf object-id {
      type uint64;
      description
        "chkpt object ID";
    }
    leaf tunnel-app-id {
      type uint32;
      description
        "Tunnel App ID";
    }
    leaf ep-app-id {
      type uint32;
      description
        "EP App ID";
    }
  }

  grouping TUNL-IP-MA-SUM {
    description
      "TUNL IP MA SUM";
    leaf gre-cap-platform-supported {
      type boolean;
      description
        "Is Platform Supported";
    }
    leaf gre-cap-max-tunnels-supported {
      type uint32;
      description
        "Max Tunnel Supported";
    }
    leaf gre-cap-max-mtu-supported {
      type uint32;
      description
        "Max MTU Supported";
    }
    leaf gre-cap-multi-encap-supported {
      type boolean;
      description
        "Multi Encap Supported";
    }
    leaf gre-cap-key-supported {
      type boolean;
      description
        "Is Key Supported";
    }
    leaf gre-cap-ipv4-transport-supported {
      type boolean;
      description
        "Is GRE IPV4 Supported";
    }
    leaf gre-cap-ipv6-transport-supported {
      type boolean;
      description
        "Is GRE IPV6 Supported";
    }
    leaf gre-cap-mgre-ipv4-transport-supported {
      type boolean;
      description
        "Is GRE IPV4 Supported";
    }
    leaf gre-cap-mgre-ipv6-transport-supported {
      type boolean;
      description
        "Is GRE IPV4 Supported";
    }
    leaf cap-ipv4-transport-supported {
      type boolean;
      description
        "Is IPV4 Supported";
    }
    leaf cap-ipv6-transport-supported {
      type boolean;
      description
        "Is IPV6 Supported";
    }
    leaf gre-cap-checksum-supported {
      type boolean;
      description
        "Is Checksum Supported";
    }
    leaf gre-cap-seq-num-supported {
      type boolean;
      description
        "Is Sequence Number Supported";
    }
    leaf gre-cap-shm-reset-supported {
      type boolean;
      description
        "Is Shmem reset Supported";
    }
    leaf gre-tid-db-count {
      type uint32;
      description
        "Number of Tunnels in Tunnel ID DB";
    }
    leaf gre-ifh-db-count {
      type uint32;
      description
        "Number of Tunnels in Ifhandle DB";
    }
    leaf gre-dst-db-count {
      type uint32;
      description
        "Number of Tunnels in Destination DB";
    }
    leaf gre-src-db-count {
      type uint32;
      description
        "Number of Tunnels in Source DB";
    }
    leaf gre-trans-vrf-db-count {
      type uint32;
      description
        "Number of Tunnels in Transport VRF DB";
    }
    leaf gre-chkpt-db-count {
      type uint32;
      description
        "Number of Tunnels in Checkpoint DB";
    }
    leaf gre-ka-db-count {
      type uint32;
      description
        "Number of Tunnels in Keepalive DB";
    }
    leaf gre-im-dpc-bulk-count {
      type uint32;
      description
        "Number of bulk DPC messages";
    }
    leaf gre-im-dpc-total-count {
      type uint32;
      description
        "Number of Total DPC messages";
    }
    leaf gre-im-dpc-error-count {
      type uint32;
      description
        "Number of DPC error messages";
    }
    leaf gre-intf-state-up-up {
      type uint32;
      description
        "Number of interfaces in UP/UP state";
    }
    leaf gre-intf-state-up-down {
      type uint32;
      description
        "Number of interfaces in UP/DOWN state";
    }
    leaf gre-intf-state-down-down {
      type uint32;
      description
        "Number of interfaces in DOWN/DOWN state";
    }
    leaf gre-src-addr-db-count {
      type uint32;
      description
        "Number of Tunnels in Source addr DB";
    }
  }

  grouping TUNL-IP-MA-EDM-RIB-CONV {
    description
      "TUNL IP MA EDM RIB CONV";
    leaf tunnel-vrf-table-id {
      type uint32;
      description
        "Tunnel VRF table ID";
    }
    leaf afi {
      type uint32;
      description
        "Transport VRF AFI";
    }
    leaf vrf-name {
      type string;
      description
        "Transport VRF Name";
    }
    leaf convergence-state {
      type boolean;
      description
        "IS Table Convergence State";
    }
  }

  grouping TUNL-IP-MA-EDM-KA {
    description
      "TUNL IP MA EDM KA";
    container source-address {
      description
        "Source Address";
      uses IP-ADDR-UNION;
    }
    container destination-address {
      description
        "Destination Address";
      uses IP-ADDR-UNION;
    }
    leaf tunnel-id-xr {
      type uint32;
      description
        "Tunnel id";
    }
    leaf interface-type {
      type xr:Interface-name;
      description
        "Interface Type";
    }
    leaf gre-key {
      type uint32;
      description
        "GRE key";
    }
    leaf tunnel-vrfid {
      type uint32;
      description
        "Tunnel VRF ID";
    }
    leaf tunnel-vrf-table-id {
      type uint32;
      description
        "Tunnel VRF table ID";
    }
    leaf flags {
      type Tunl-ip-tunl-flag;
      description
        "Flags for interface/line protocol state";
    }
    leaf keepalive-period {
      type uint16;
      description
        "Keepalive Period";
    }
    leaf keepalive-maximum-retries {
      type uint8;
      description
        "Keepalive Maximum Retries";
    }
    leaf keepalive-fail {
      type uint8;
      description
        "Keepalive Fail Count";
    }
    leaf ttl {
      type uint8;
      description
        "Tunnel TTL";
    }
    leaf keepalive-state {
      type Tunl-gre-ka-states;
      description
        "keepalive State";
    }
    leaf ka-sent-packets {
      type uint32;
      description
        "Number of keepalive packets sent";
    }
    leaf ka-received-packets {
      type uint32;
      description
        "Number of keepalive packets received";
    }
    leaf ka-sent-time {
      type uint32;
      description
        "Timestamp of Keepalive packets sent";
    }
    leaf ka-received-time {
      type uint32;
      description
        "Timestamp of Keepalive packets received";
    }
  }

  grouping IP-ADDR-UNION {
    description
      "IP ADDR UNION";
    leaf afi {
      type Tunl-af-id;
      description
        "AFI";
    }
    leaf ipv4 {
      when "../afi = 'tunl-af-id-ipv4'" {
        description
          "../AFI = 'TUNL_AF_ID_IPV4'";
      }
      type Tunl-in-addr;
      description
        "IPv4 address type";
    }
    leaf ipv6 {
      when "../afi = 'tunl-af-id-ipv6'" {
        description
          "../AFI = 'TUNL_AF_ID_IPV6'";
      }
      type Tunl-in6-addr;
      description
        "IPv6 address type";
    }
  }

  grouping TUNL-GRE-MA-EDM-IDB {
    description
      "TUNL GRE MA EDM IDB";
    container source-address {
      description
        "Source Address";
      uses IP-ADDR-UNION;
    }
    container destination-address {
      description
        "Destination Address";
      uses IP-ADDR-UNION;
    }
    leaf tunnel-id {
      type uint32;
      description
        "Tunnel ID";
    }
    leaf interface-type {
      type xr:Interface-name;
      description
        "Interface Type";
    }
    leaf source-interface-name {
      type string;
      description
        "Source Interface Name";
    }
    leaf tunnel-src-vrf-table-id {
      type uint32;
      description
        "Tunnel Source VRF table ID";
    }
    leaf destination-address-length {
      type uint8;
      description
        "Destination Address Length";
    }
    leaf destination-prefix-list {
      type string;
      description
        "Destination Prefix List";
    }
    leaf tunnel-vrf-table-id {
      type uint32;
      description
        "Tunnel VRF table ID";
    }
    leaf tunnel-vrfid {
      type uint32;
      description
        "Tunnel VRF ID";
    }
    leaf vrf-name {
      type string;
      description
        "Interface Name";
    }
    leaf tunnel-mode {
      type Tunl-ip-mode;
      description
        "Mode of Tunnel";
    }
    leaf tunnel-mode-direction {
      type Tunl-ip-mode-dir;
      description
        "Mode direction";
    }
    leaf flags {
      type Tunl-ip-tunl-flag;
      description
        "Flags for don't fragment, TOS reflection";
    }
    leaf mtu {
      type uint16;
      description
        "Max Transferable Unit";
    }
    leaf tos {
      type uint8;
      description
        "Type Of Service";
    }
    leaf ttl {
      type uint8;
      description
        "Time To Live";
    }
    leaf interface-name {
      type string;
      description
        "Interface Name";
    }
    leaf keepalive-maximum-retries {
      type uint8;
      description
        "Keepalive Retries";
    }
    leaf keepalive-period {
      type uint16;
      description
        "Keepalive Period";
    }
    leaf platform-tunnel-id {
      type uint16;
      description
        "Platform Tunnel ID";
    }
    leaf bandwidth {
      type uint32;
      description
        "Bandwidth";
    }
    leaf flags-other {
      type uint32;
      description
        "Other Flags";
    }
    leaf key {
      type uint32;
      description
        "Key Value for GRE Packet";
    }
    leaf key-entropy-length {
      type uint8;
      description
        "Key Entropy Length for GRE Packet";
    }
    leaf transport-proto {
      type Tunl-ip-transport-proto;
      description
        "Tunnel Transport Protocol";
    }
    leaf op-ifhandle {
      type xr:Interface-name;
      description
        "Output Interface handle";
    }
    leaf flag-bits {
      type Tunl-ip-tunl-flag-bits;
      description
        "Flags for BFD";
    }
    leaf interface-state {
      type string;
      description
        "Tunnel Interface State";
    }
    leaf base-caps-state {
      type string;
      description
        "Base Caps State";
    }
    leaf bfd-session-state {
      type string;
      description
        "BFD Session State";
    }
    leaf source-direct {
      type uint8;
      description
        "Source direct";
    }
  }

  grouping TUNL-IP-MA-EDM-IDB-ARRAY {
    description
      "Array of IDB entries BAG";
    list idb-array {
      description
        "Array of MA IDB";
      uses TUNL-GRE-MA-EDM-IDB;
    }
  }

  grouping TUNL-P2MP-MA-EDM-GSPDB {
    description
      "gspdb BAG";
    leaf node-state {
      type uint16;
      description
        "Node state";
    }
    leaf nodeid {
      type uint32;
      description
        "Node id";
    }
    leaf leaf-timer-flag {
      type boolean;
      description
        "leaf timer flag";
    }
  }

  grouping TUNL-P2MP-MA-EDM-GSPDB-ARRAY {
    description
      "Array of GSP DB entries BAG";
    list gspdb-array {
      description
        "GSP_DB array";
      uses TUNL-P2MP-MA-EDM-GSPDB;
    }
  }
}
