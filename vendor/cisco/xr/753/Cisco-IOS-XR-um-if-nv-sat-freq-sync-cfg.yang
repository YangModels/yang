module Cisco-IOS-XR-um-if-nv-sat-freq-sync-cfg {
  namespace "http://cisco.com/ns/yang/Cisco-IOS-XR-um-if-nv-sat-freq-sync-cfg";
  prefix um-if-nv-sat-freq-sync-cfg;

  import Cisco-IOS-XR-um-interface-cfg {
    prefix a1;
  }
  import Cisco-IOS-XR-um-nv-satellite-cfg {
    prefix a2;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR if-nv-sat-freq-sync package configuration.
     
     This YANG module augments the
     modules with configuration data.
     
     Copyright (c) 2020-2021 by Cisco Systems, Inc.
     All rights reserved.";

  revision 2021-01-06 {
    description
      "Initial release";
    semver:module-version "1.0.0";
  }

  grouping IF-NV-BODY {
    container frequency {
      description
        "Enable Frequency Synchronization";
      container synchronization {
        presence "Indicates a synchronization node is configured.";
        description
          "Enable Frequency Synchronization";
      }
    }
  }

  augment "/a1:interfaces/a1:interface/a2:nv/a2:satellite-fabric-link/a2:satellite" {
    uses IF-NV-BODY;
  }
  augment "/a1:interfaces/a1:interface-preconfigure/a2:nv/a2:satellite-fabric-link/a2:satellite" {
    uses IF-NV-BODY;
  }
}
