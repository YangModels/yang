module Cisco-IOS-XR-infra-script-mgmt-cfg {
  namespace "http://cisco.com/ns/yang/Cisco-IOS-XR-infra-script-mgmt-cfg";
  prefix infra-script-mgmt-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR infra-script-mgmt package configuration.
     
     This module contains definitions
     for the following management objects:
       scripts: Script-mgmt configuration data
     
     Copyright (c) 2013-2022 by Cisco Systems, Inc.
     All rights reserved.";

  revision 2022-08-02 {
    description
      "Fixed SNMP checksum configuration
       2021-12-13
         Added snmp as a new script type supported by script management.";
    semver:module-version "2.0.1m";
  }
  revision 2021-08-31 {
    description
      "Define range for update interval in yang
       2021-08-25
          Encrypt password in auto-update config
       2021-08-14
          Extend schema to support auto-update feature
       2021-07-20
          revert checksum type to Enum";
    semver:module-version "2.0.0";
  }
  revision 2019-04-05 {
    description
      "Establish semantic version baseline.";
    semver:module-version "1.0.0";
  }
  revision 2015-11-09 {
    description
      "IOS XR 6.0 revision.";
  }

  typedef Config-checksum {
    type enumeration {
      enum "sha256" {
        value 1;
        description
          "SHA256";
      }
    }
    description
      "Config checksum";
  }

  typedef On-failure {
    type enumeration {
      enum "do-not-run" {
        value 0;
        description
          "do not run";
      }
      enum "run-local" {
        value 1;
        description
          "run local";
      }
    }
    description
      "On failure";
  }

  grouping SCHEDULED-UPDATE-TABLE {
    description
      "Common node of process-script, eem-script,
       exec-script, config-script, snmp-script";
    container scheduled-updates {
      description
        "Name of script";
      list scheduled-update {
        key "script-name";
        description
          "Config Script activation item";
        container condition-schedule {
          description
            "auto-update condition";
          leaf url {
            type string;
            default "none";
            description
              "URL location";
          }
          leaf update-interval {
            type uint32 {
              range "60..262800";
            }
            default "262800";
            description
              "update interval";
          }
          leaf username {
            type string;
            default "none";
            description
              "Username";
          }
          leaf password {
            type xr:Proprietary-password;
            default "none";
            description
              "Password";
          }
          leaf vrf {
            type string;
            default "default";
            description
              "VRF name";
          }
        }
        leaf script-name {
          type xr:Cisco-ios-xr-string;
          description
            "Script name";
        }
      }
    }
  }

  grouping MANUAL-UPDATE-TABLE {
    description
      "Common node of process-script, eem-script,
       exec-script, config-script, snmp-script";
    container manual-updates {
      description
        "Name of script";
      list manual-update {
        key "script-name";
        description
          "Config Script activation item";
        container condition-manual {
          description
            "auto-update condition";
          leaf url {
            type string;
            default "none";
            description
              "URL location";
          }
          leaf username {
            type string;
            default "none";
            description
              "Username";
          }
          leaf password {
            type xr:Proprietary-password;
            default "none";
            description
              "Password";
          }
          leaf vrf {
            type string;
            default "default";
            description
              "VRF name";
          }
        }
        leaf script-name {
          type xr:Cisco-ios-xr-string;
          description
            "Script name";
        }
      }
    }
  }

  grouping SCRIPT-TABLE {
    description
      "Common node of exec-script, process-script,
       snmp-script";
    container scripts {
      description
        "Name of script";
      list script {
        key "script-name";
        description
          "Config Script activation item";
        container checksum {
          presence "Indicates a checksum node is configured.";
          description
            "Checksum of script";
          leaf checksum-type {
            type Config-checksum;
            mandatory true;
            description
              "Checksum type";
          }
          leaf checksum {
            type string {
              length "64";
            }
            mandatory true;
            description
              "Checksum value";
          }
        }
        leaf script-name {
          type xr:Cisco-ios-xr-string;
          description
            "Script name";
        }
      }
    }
  }

  container scripts {
    description
      "Script-mgmt configuration data";
    container exec-script {
      description
        "Exec script";
      container runtime-updates {
        description
          "Name of script";
        list runtime-update {
          key "script-name";
          description
            "Config Script activation item";
          container condition-runtime {
            description
              "auto-update condition";
            leaf url {
              type string;
              default "none";
              description
                "URL location";
            }
            leaf failure {
              type On-failure;
              default "do-not-run";
              description
                "run local/do not run";
            }
            leaf username {
              type string;
              default "none";
              description
                "Username";
            }
            leaf password {
              type xr:Proprietary-password;
              default "none";
              description
                "Password";
            }
            leaf vrf {
              type string;
              default "default";
              description
                "VRF name";
            }
          }
          leaf script-name {
            type xr:Cisco-ios-xr-string;
            description
              "Script name";
          }
        }
      }
      uses SCHEDULED-UPDATE-TABLE;
      uses MANUAL-UPDATE-TABLE;
      uses SCRIPT-TABLE;
    }
    container snmp-script {
      description
        "Snmp script";
      uses SCHEDULED-UPDATE-TABLE;
      uses MANUAL-UPDATE-TABLE;
      uses SCRIPT-TABLE;
    }
    container config-script {
      description
        "Config scripts";
      uses SCHEDULED-UPDATE-TABLE;
      uses MANUAL-UPDATE-TABLE;
    }
    container eem-script {
      description
        "Eem script";
      uses SCHEDULED-UPDATE-TABLE;
      uses MANUAL-UPDATE-TABLE;
    }
    container process-script {
      description
        "Process script";
      uses SCHEDULED-UPDATE-TABLE;
      uses MANUAL-UPDATE-TABLE;
      uses SCRIPT-TABLE;
    }
  }
}
