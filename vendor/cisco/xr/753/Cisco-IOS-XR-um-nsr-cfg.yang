module Cisco-IOS-XR-um-nsr-cfg {
  namespace "http://cisco.com/ns/yang/Cisco-IOS-XR-um-nsr-cfg";
  prefix um-nsr-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR nsr package configuration.
     
     This YANG module augments the
     modules with configuration data.
     
     Copyright (c) 2020 by Cisco Systems, Inc.
     All rights reserved.";

  revision 2020-03-23 {
    description
      "Initial release";
    semver:module-version "1.0.0";
  }

  container nsr {
    description
      "Global NSR configuration commands";
    container process-failures {
      description
        "Recovery action for Process failures on active RP/DRP";
      container switchover {
        presence "Indicates a switchover node is configured.";
        description
          "Switch over to standby RP/DRP to maintain NSR";
      }
    }
  }
}
