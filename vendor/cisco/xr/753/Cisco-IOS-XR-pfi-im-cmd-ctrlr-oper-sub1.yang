submodule Cisco-IOS-XR-pfi-im-cmd-ctrlr-oper-sub1 {
  belongs-to Cisco-IOS-XR-pfi-im-cmd-ctrlr-oper {
    prefix Cisco-IOS-XR-pfi-im-cmd-ctrlr-oper;
  }

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR pfi-im-cmd-ctrlr package operational data.
     
     Copyright (c) 2013-2019 by Cisco Systems, Inc.
     All rights reserved.";

  revision 2019-04-05 {
    description
      "Establish semantic version baseline.";
    semver:module-version "1.0.1";
  }
  revision 2015-11-09 {
    description
      "IOS XR 6.0 revision.";
  }

  typedef Im-state-enum {
    type enumeration {
      enum "im-state-not-ready" {
        description
          "im state not ready";
      }
      enum "im-state-admin-down" {
        description
          "im state admin down";
      }
      enum "im-state-down" {
        description
          "im state down";
      }
      enum "im-state-up" {
        description
          "im state up";
      }
      enum "im-state-shutdown" {
        description
          "im state shutdown";
      }
      enum "im-state-err-disable" {
        description
          "im state err disable";
      }
      enum "im-state-down-immediate" {
        description
          "im state down immediate";
      }
      enum "im-state-down-immediate-admin" {
        description
          "im state down immediate admin";
      }
      enum "im-state-down-graceful" {
        description
          "im state down graceful";
      }
      enum "im-state-begin-shutdown" {
        description
          "im state begin shutdown";
      }
      enum "im-state-end-shutdown" {
        description
          "im state end shutdown";
      }
      enum "im-state-begin-error-disable" {
        description
          "im state begin error disable";
      }
      enum "im-state-end-error-disable" {
        description
          "im state end error disable";
      }
      enum "im-state-begin-down-graceful" {
        description
          "im state begin down graceful";
      }
      enum "im-state-reset" {
        description
          "im state reset";
      }
      enum "im-state-operational" {
        description
          "im state operational";
      }
      enum "im-state-not-operational" {
        description
          "im state not operational";
      }
      enum "im-state-unknown" {
        description
          "im state unknown";
      }
      enum "im-state-last" {
        description
          "im state last";
      }
    }
    description
      "Im state enum";
  }

  grouping IM-CTRLR-DESC-INFO {
    description
      "Controller description information";
    leaf controller {
      type xr:Interface-name;
      description
        "Interface handle of Controller";
    }
    leaf state {
      type Im-state-enum;
      description
        "Operational state with no translation of error
         disable or shutdown";
    }
    leaf description {
      type string;
      description
        "Controller description string";
    }
  }
}
