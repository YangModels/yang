module Cisco-IOS-XR-um-asr9k-hw-module-bfd-hw-offload-cfg {
  namespace "http://cisco.com/ns/yang/Cisco-IOS-XR-um-asr9k-hw-module-bfd-hw-offload-cfg";
  prefix um-asr9k-hw-module-bfd-hw-offload-cfg;

  import Cisco-IOS-XR-types {
    prefix xr;
  }
  import Cisco-IOS-XR-um-location-cfg {
    prefix location;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR asr9k-hw-module-bfd-hw-offload package configuration.
     
     This YANG module augments the
     modules with configuration data.
     
     Copyright (c) 2021 by Cisco Systems, Inc.
     All rights reserved.";

  revision 2021-09-15 {
    description
      "Initial release";
    semver:module-version "1.0.0";
  }

  grouping LOCATION-BODY {
    container bfd-hw-offload {
      description
        "Configure BFD hw offload parameters";
      container enable {
        description
          "Enable BFD hw offload mode";
        list node {
          key "node-name";
          description
            "Node id to filter out trient card";
          leaf node-name {
            type xr:Node-id;
            description
              "Node Name";
          }
        }
      }
    }
  }

  augment "/location:locations/location:location" {
    uses LOCATION-BODY;
  }
  augment "/location:locations/location:preconfigured-location" {
    uses LOCATION-BODY;
  }
}
