module Cisco-IOS-XR-um-asr9k-hw-module-fia-cfg {
  namespace "http://cisco.com/ns/yang/Cisco-IOS-XR-um-asr9k-hw-module-fia-cfg";
  prefix um-asr9k-hw-module-fia-cfg;

  import Cisco-IOS-XR-um-location-cfg {
    prefix location;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR asr9k-hw-module-fia package configuration.
     
     This YANG module augments the
     modules with configuration data.
     
     Copyright (c) 2020 by Cisco Systems, Inc.
     All rights reserved.";

  revision 2020-09-15 {
    description
      "Initial release";
    semver:module-version "1.0.0";
  }

  grouping LOCATION-BODY {
    container fia-vqi-shaper {
      description
        "Enhance VQI shaper limit for Skytrain";
      container enhance {
        presence "Indicates a enhance node is configured.";
        description
          "Operate on a higher VQI shaper limit";
      }
    }
    container fia-buffer-profile {
      description
        "FIA interface buffer profile selection";
      container extra-large {
        presence "Indicates a extra-large node is configured.";
        description
          "Setup an extra-large FIA buffer profile";
      }
    }
    container port-queue-remap {
      description
        "Remap front panel port to fabric queue";
      container ports {
        description
          "Front panel port number";
        list port {
          key "port-number";
          description
            "Front panel port number";
          leaf port-number {
            type uint32 {
              range "10|11|22|23|34|35|46|47" {
                description
                  "port number <10,11,22,23 34,35,46,47>";
              }
            }
            description
              "Front panel port number";
          }
          leaf queue {
            type uint32 {
              range "0..19" {
                description
                  "queue number <0-19>";
              }
            }
            description
              "Fabric queue number";
          }
        }
      }
    }
  }

  augment "/location:locations/location:location" {
    uses LOCATION-BODY;
  }
  augment "/location:locations/location:preconfigured-location" {
    uses LOCATION-BODY;
  }
  container hw-module {
    description
      "Configure h/w module";
    container fia-intf-policer {
      description
        "FIA interface rate-limiter on 7-Fabric LC";
      container disable {
        presence "Indicates a disable node is configured.";
        description
          "disable FIA interface policer ";
      }
    }
  }
}
