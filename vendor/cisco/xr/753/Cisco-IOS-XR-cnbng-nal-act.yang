module Cisco-IOS-XR-cnbng-nal-act {
  namespace "http://cisco.com/ns/yang/Cisco-IOS-XR-cnbng-nal-act";
  prefix cnbng-nal-act;

  import cisco-semver {
    prefix semver;
  }
  import Cisco-IOS-XR-types {
    prefix csc;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR action package configuration.
     
     Copyright (c) 2018-2021 by Cisco Systems, Inc.
     All rights reserved.";

  revision 2021-08-29 {
    description
      "IOS XR 7.6.1 revision removing cnbng-nal task";
    semver:module-version "1.1.0";
  }
  revision 2021-02-11 {
    description
      "IOS XR 7.4.1 revision removing unused imports.";
    semver:module-version "1.0.0";
  }
  revision 2020-09-10 {
    description
      "IOS XR 7.3.1 revision.";
    semver:module-version "1.0.0";
  }

  rpc clear-cnbng-nal-cp-association {
    description
      "Clear cnBNG NAL CP server association";
    csc:cli-command "clear cnbng-nal cp-association";
  }
  rpc clear-cnbng-nal-cp-association-location {
    description
      "Clear cnBNG NAL CP server association for given node";
    input {
      leaf node-location {
        type string;
        mandatory true;
        description
          "Node location";
        csc:cli-name "*";
      }
    }
    csc:cli-command "clear cnbng-nal cp-association location <node-location>";
  }
  rpc clear-cnbng-nal-dynamic-routes-afi {
    description
      "Execute clear cnBNG NAL Dynamic-routes AFI-type";
    input {
      leaf afi-type {
        type string;
        mandatory true;
        description
          "Address-family";
        csc:cli-name "*";
      }
    }
    csc:cli-command "clear cnbng-nal dynamic-routes afi <afi-type>";
  }
  rpc clear-cnbng-nal-dynamic-routes-afi-location {
    description
      "Execute clear cnBNG NAL Dynamic-routes AFI for the given node";
    input {
      leaf afi-type {
        type string;
        mandatory true;
        description
          "Address-family";
        csc:cli-name "*";
      }
      leaf node-location {
        type string;
        mandatory true;
        description
          "Node location";
        csc:cli-name "*";
      }
    }
    csc:cli-command "clear cnbng-nal dynamic-routes afi <afi-type> location <node-location>";
  }
  rpc clear-cnbng-nal-dynamic-routes-history {
    description
      "Clear cnBNG NAL Dynamic-routes history";
    csc:cli-command "clear cnbng-nal dynamic-routes history";
  }
  rpc clear-cnbng-nal-dynamic-routes-history-location {
    description
      "Clear cnBNG NAL Dynamic-routes history for given node";
    input {
      leaf node-location {
        type string;
        mandatory true;
        description
          "Node location";
        csc:cli-name "*";
      }
    }
    csc:cli-command "clear cnbng-nal dynamic-routes history location <node-location>";
  }
  rpc clear-cnbng-nal-subscriber-disconnect-history {
    description
      "Clear cnBNG NAL subscriber disconnect-history entries";
    csc:cli-command "clear cnbng-nal subscriber disconnect-history";
  }
  rpc clear-cnbng-nal-subscriber-disconnect-history-location {
    description
      "Clear cnBNG NAL subscriber disconnect-history entries for given node";
    input {
      leaf node-location {
        type string;
        mandatory true;
        description
          "Node location";
        csc:cli-name "*";
      }
    }
    csc:cli-command "clear cnbng-nal subscriber disconnect-history location <node-location>";
  }
}
