module Cisco-IOS-XR-test-ocni-isis-oper {
  namespace "http://cisco.com/ns/yang/Cisco-IOS-XR-test-ocni-isis-oper";
  prefix test-ocni-isis-oper;

  import cisco-semver {
    prefix semver;
  }
  include Cisco-IOS-XR-test-ocni-isis-oper-sub1 {
    revision-date 2019-04-05;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR test-ocni-isis package operational data.
     
     This module contains definitions
     for the following management objects:
       ocni-isis: An OpenConfig description of a network-instance
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  typedef Oc-netinstisis-integer64 {
    type string;
    description
      "Oc netinstisis integer64";
  }

  container ocni-isis {
    config false;
    description
      "An OpenConfig description of a network-instance";
    container network-instances {
      description
        "Network instances configured on the local system";
      list network-instance {
        key "name";
        description
          "Network instances configured on the local
           system";
        container interfaces {
          description
            "An interface associated with the network
             instance";
          list interface {
            key "id";
            description
              "An interface associated with the network
               instance";
            leaf id {
              type string;
              description
                "A reference to an identifier for this
                 interface which acts as a key for this list";
            }
            uses OVERLAY-OCNI-ISIS-INTERFACE;
          }
        }
        container protocols {
          description
            "A process (instance) of a routing protocol";
          list protocol {
            key "identifier name";
            description
              "A process (instance) of a routing protocol";
            container protocols-state {
              description
                "State parameters relating to the routing
                 protocol instance";
              uses OVERLAY-OCNI-ISIS-PROTOCOL-STATE;
            }
            container isis {
              description
                "This container defines top-level ISIS
                 configuration and state information";
              container isis-interfaces {
                description
                  "This list contains ISIS interfaces";
                list isis-interface {
                  key "interface-id";
                  description
                    "This list contains ISIS interfaces";
                  container interfaces-afi-safis {
                    description
                      "Address-family/Subsequent Address-family
                       list";
                    list interfaces-afi-safi {
                      key "afi-name safi-name";
                      description
                        "Address-family/Subsequent Address-family
                         list";
                      leaf afi-name {
                        type string;
                        description
                          "Reference to address-family type";
                      }
                      leaf safi-name {
                        type string;
                        description
                          "Reference to subsequent address-family
                           type";
                      }
                      uses OVERLAY-OCNI-ISIS-AFI-SAFI-AF;
                    }
                  }
                  container interfaces-state {
                    description
                      "This container defines state information
                       for ISIS interfaces";
                    uses OVERLAY-OCNI-ISIS-INTERFACE-STATE;
                  }
                  container interfaces-levels {
                    description
                      "Configuration and operational state
                       parameters related to a particular level
                       on an IS-IS enabled interface";
                    list interfaces-level {
                      key "level-number";
                      description
                        "Configuration and operational state
                         parameters related to a particular level
                         on an IS-IS enabled interface";
                      container hello-authentication {
                        description
                          "This container defines ISIS
                           authentication";
                        uses OVERLAY-OCNI-ISIS-HELLO-AUTHENTICATION;
                      }
                      container interfaces-levels-state {
                        description
                          "This container defines interface ISIS
                           level state information";
                        uses OVERLAY-OCNI-ISIS-LEVELS-LEVEL-STATE;
                      }
                      container packet-counters {
                        description
                          "This container defines ISIS interface
                           packet counters";
                        uses OVERLAY-OCNI-ISIS-PACKET-COUNTERS;
                      }
                      container adjacencies {
                        description
                          "List of the local system's IS-IS
                           adjacencies";
                        list adjacency {
                          key "system-id";
                          description
                            "List of the local system's IS-IS
                             adjacencies";
                          leaf system-id {
                            type string;
                            description
                              "Reference to the IS neighbor";
                          }
                          uses OVERLAY-OCNI-ISIS-ADJACENCY;
                        }
                      }
                      container levels-timers {
                        description
                          "This container defines ISIS timers";
                        uses OVERLAY-OCNI-ISIS-LEVEL-TIMERS;
                      }
                      container levels-afi-safis {
                        description
                          "Address-family/Subsequent
                           Address-family list";
                        list levels-afi-safi {
                          key "afi-name safi-name";
                          description
                            "Address-family/Subsequent
                             Address-family list";
                          container afi-safi-state {
                            description
                              "This container defines AFI-SAFI State
                               information";
                            uses OVERLAY-OCNI-ISIS-AF-STATE;
                          }
                          container afi-safi-segment-routing {
                            description
                              "Configuration and operatioanl state
                               parameters relating to segment
                               routing for an interface within the
                               IGP";
                            container segment-routing-prefix-sids {
                              description
                                "An IGP prefix that should have a
                                 segment routing IGP-Prefix SID
                                 allocated to it";
                              list segment-routing-prefix-sid {
                                key "prefix";
                                description
                                  "An IGP prefix that should have a
                                   segment routing IGP-Prefix SID
                                   allocated to it";
                                leaf prefix {
                                  type string;
                                  description
                                    "Reference to the prefix for which
                                     the IGP-Prefix SID is to be
                                     advertised";
                                }
                                uses OVERLAY-OCNI-ISIS-SEGMENT-ROUTING-PREFIX-SIDS-PREFIX-SID;
                              }
                            }
                          }
                          leaf afi-name {
                            type string;
                            description
                              "Reference to address-family type";
                          }
                          leaf safi-name {
                            type string;
                            description
                              "Reference to subsequent
                               address-family type";
                          }
                        }
                      }
                      leaf level-number {
                        type uint32;
                        description
                          "Reference to ISIS level-number";
                      }
                    }
                  }
                  container circuit-counters {
                    description
                      "This container defines state information
                       for ISIS circuit counters";
                    uses OVERLAY-OCNI-ISIS-CIRCUIT-COUNTERS;
                  }
                  container bfd {
                    description
                      "This container defines BFD";
                    uses OVERLAY-OCNI-ISIS-BFD;
                  }
                  container interfaces-authentication {
                    description
                      "This container defines ISIS
                       authentication";
                    uses OVERLAY-OCNI-ISIS-INTERFACE-AUTHENTICATION;
                  }
                  container interfaces-timers {
                    description
                      "This container describes ISIS interface
                       timers configuration";
                    uses OVERLAY-OCNI-ISIS-INTERFACE-TIMERS;
                  }
                  leaf interface-id {
                    type string;
                    description
                      "Reference to interface-id";
                  }
                }
              }
              container global {
                description
                  "This container defines global ISIS
                   configuration and state information";
                container segment-routing {
                  description
                    "Configuration and operational state
                     relating to segment routing";
                  uses OVERLAY-OCNI-ISIS-SEGMENT-ROUTING;
                }
                container lsp-bit {
                  description
                    "This container defines ISIS LSP
                     Operational Bits";
                  container overload-bit {
                    description
                      "This container defines Overload Bit
                       configuration";
                    container overload-bit-state {
                      description
                        "This container defines state for ISIS
                         Overload Bit";
                      uses OVERLAY-OCNI-ISIS-OVERLOAD-BIT-STATE;
                    }
                    container reset-triggers {
                      description
                        "This list describes ISIS Overload reset
                         trigger reasons";
                      list reset-trigger {
                        key "reset-trigger";
                        description
                          "This list describes ISIS Overload reset
                           trigger reasons";
                        leaf reset-trigger {
                          type string;
                          description
                            "Reference to the reset trigger reason";
                        }
                        uses OVERLAY-OCNI-ISIS-RESET-TRIGGER;
                      }
                    }
                  }
                  container attached-bit {
                    description
                      "This container defines Attached Bit";
                    uses OVERLAY-OCNI-ISIS-ATTACHED-BIT;
                  }
                }
                container nsr {
                  description
                    "This container defines ISIS Non-Stop
                     Routing";
                  uses OVERLAY-OCNI-ISIS-NSR;
                }
                container graceful-restart {
                  description
                    "This container defines ISIS Graceful
                     Restart";
                  uses OVERLAY-OCNI-ISIS-GRACEFUL-RESTART;
                }
                container global-state {
                  description
                    "This container defines state for ISIS
                     global router";
                  uses OVERLAY-OCNI-ISIS-GLOBAL-STATE;
                }
                container inter-level-propagation-policies {
                  description
                    "Policies to propagate prefixes between
                     IS-IS levels";
                  uses OVERLAY-OCNI-ISIS-INTER-LEVEL-PROPAGATION-POLICIES;
                }
                container afi-safis {
                  description
                    "Address-family/Subsequent Address-family
                     list";
                  list afi-safi {
                    key "afi-name safi-name";
                    description
                      "Address-family/Subsequent Address-family
                       list";
                    leaf afi-name {
                      type string;
                      description
                        "Reference to address-family type";
                    }
                    leaf safi-name {
                      type string;
                      description
                        "Reference to subsequent address-family
                         type";
                    }
                    uses OVERLAY-OCNI-ISIS-AF;
                  }
                }
                container timers {
                  description
                    "This container defines ISIS timers";
                  uses OVERLAY-OCNI-ISIS-TIMERS;
                }
                container transport {
                  description
                    "This container defines ISIS transport";
                  uses OVERLAY-OCNI-ISIS-TRANSPORT;
                }
              }
              container levels {
                description
                  "Configuration and operational state
                   parameters related to a particular level
                   within the IS-IS protocol instance";
                list level {
                  key "level-number";
                  description
                    "Configuration and operational state
                     parameters related to a particular level
                     within the IS-IS protocol instance";
                  container route-preference {
                    description
                      "This container defines Administrative
                       Distance (or preference) assigned to ISIS
                       routes (level1 internal, level2 internal,
                       level1 external, level2 external)";
                    uses OVERLAY-OCNI-ISIS-ROUTE-PREFERENCE;
                  }
                  container levels-state {
                    description
                      "This container defines ISIS level state
                       information";
                    uses OVERLAY-OCNI-ISIS-LEVEL-STATE;
                  }
                  container traffic-engineering {
                    description
                      "This container defines ISIS TE";
                    uses OVERLAY-OCNI-ISIS-TRAFFIC-ENGINEERING;
                  }
                  container levels-authentication {
                    description
                      "This container defines ISIS
                       authentication";
                    uses OVERLAY-OCNI-ISIS-LEVEL-AUTHENTICATION;
                  }
                  container system-level-counters {
                    description
                      "This container defines ISIS system level
                       counters";
                    uses OVERLAY-OCNI-ISIS-SYSTEM-LEVEL-COUNTERS;
                  }
                  container link-state-databases {
                    description
                      "This list describes LSPs in the LSDB";
                    list link-state-database {
                      key "lsp-id";
                      description
                        "This list describes LSPs in the LSDB";
                      container undefined-tlvs {
                        description
                          "List of TLVs that are not defined
                           within the model, or are not recognised
                           by the system";
                        list undefined-tlv {
                          key "type";
                          description
                            "List of TLVs that are not defined
                             within the model, or are not
                             recognised by the system";
                          leaf type {
                            type uint32;
                            description
                              "Reference to the undefined TLV's type";
                          }
                          uses OVERLAY-OCNI-ISIS-UNDEFINED-TLV;
                        }
                      }
                      container link-state-database-state {
                        description
                          "State parameters of Link State PDU";
                        uses OVERLAY-OCNI-ISIS-LSP-STATE;
                      }
                      container tlvses {
                        description
                          "List of TLV types in the LSDB for the
                           specified LSP";
                        list tlvs {
                          key "type";
                          description
                            "List of TLV types in the LSDB for the
                             specified LSP";
                          container area-address {
                            description
                              "This container defines TLV 1";
                            uses OVERLAY-OCNI-ISIS-AREA-ADDRESS;
                          }
                          container authentication {
                            description
                              "This container defines authentication
                               information of the node";
                            uses OVERLAY-OCNI-ISIS-AUTHENTICATION;
                          }
                          container ipv4-interface-addresses {
                            description
                              "This container defines TLV 132";
                            uses OVERLAY-OCNI-ISIS-IPV4-INTERFACE-ADDRESSES;
                          }
                          container router-capabilities {
                            description
                              "This list describes IS Router
                               capabilities";
                            list router-capability {
                              key "instance-number";
                              description
                                "This list describes IS Router
                                 capabilities";
                              container router-capabilities-state {
                                description
                                  "State parameters of TLV 242";
                                uses OVERLAY-OCNI-ISIS-CAPABILITY-STATE;
                              }
                              container undefined-subtlvs {
                                description
                                  "Sub-TLVs that are not defined in
                                   the model or not recognised by
                                   system";
                                list undefined-subtlv {
                                  key "type";
                                  description
                                    "Sub-TLVs that are not defined in
                                     the model or not recognised by
                                     system";
                                  leaf type {
                                    type uint32;
                                    description
                                      "Reference to the type of the
                                       undefined sub-TLV";
                                  }
                                  uses OVERLAY-OCNI-ISIS-UNDEFINED-SUBTLV;
                                }
                              }
                              container subtlvs {
                                description
                                  "List of subTLV types in the LSDB
                                   for the specified TLV";
                                list subtlv {
                                  key "type";
                                  description
                                    "List of subTLV types in the LSDB
                                     for the specified TLV";
                                  container subtlvs-state {
                                    description
                                      "State parameters of IS Router
                                       Capabilities";
                                    uses OVERLAY-OCNI-ISIS-SUBTLV-STATE;
                                  }
                                  container segment-routing-algorithms {
                                    description
                                      "This container defines SR
                                       algorithm sub-TLV 19";
                                    uses OVERLAY-OCNI-ISIS-SEGMENT-ROUTING-ALGORITHMS;
                                  }
                                  container segment-routing-capability {
                                    description
                                      "This container defines SR
                                       Capability sub-TLV 2";
                                    container segment-routing-capability-state {
                                      description
                                        "State parameters of IS SR Router
                                         Capability";
                                      uses OVERLAY-OCNI-ISIS-SEGMENT-ROUTING-CAPABILITY-STATE;
                                    }
                                    container srgb-descriptors {
                                      description
                                        "Descriptor entry within the SR
                                         capabilty sub-TLV";
                                      list srgb-descriptor {
                                        key "range";
                                        description
                                          "Descriptor entry within the SR
                                           capabilty sub-TLV";
                                        leaf range {
                                          type uint32;
                                          description
                                            "Reference to unique SRGB
                                             Descriptor";
                                        }
                                        uses OVERLAY-OCNI-ISIS-SRGB-DESCRIPTOR;
                                      }
                                    }
                                  }
                                  leaf type {
                                    type string;
                                    description
                                      "Reference to the sub-TLV type";
                                  }
                                }
                              }
                              leaf instance-number {
                                type uint32;
                                description
                                  "Reference to the instance number of
                                   the router capability TLV";
                              }
                            }
                          }
                          container mt-ipv4-reachability {
                            description
                              "This container defines list of IPv4
                               reachability Information in
                               multi-topology environment";
                            container mt-ipv4-reachability-prefixes {
                              description
                                "IPv4 prefixes that are contained
                                 within MT reachability TLV";
                              list mt-ipv4-reachability-prefixe {
                                key "mt-id prefix";
                                description
                                  "IPv4 prefixes that are contained
                                   within MT reachability TLV";
                                container mt-ipv4-reachability-prefixes-state {
                                  description
                                    "State parameters of an IPv4
                                     extended prefix";
                                  uses OVERLAY-OCNI-ISIS-MT-IPV4-REACHABILITY-PREFIXES-PREFIX-STATE;
                                }
                                container mt-ipv4-reachability-prefixes-undefined-subtlvs {
                                  description
                                    "Sub-TLVs that are not defined in
                                     the model or not recognised by
                                     system";
                                  list mt-ipv4-reachability-prefixes-undefined-subtlv {
                                    key "type";
                                    description
                                      "Sub-TLVs that are not defined in
                                       the model or not recognised by
                                       system";
                                    leaf type {
                                      type uint32;
                                      description
                                        "Reference to the type of the
                                         undefined sub-TLV";
                                    }
                                    uses OVERLAY-OCNI-ISIS-MT-IPV4-REACHABILITY-PREFIXES-PREFIX-UNDEFINED-SUBTLVS-UNDEFINED-SUBTLV;
                                  }
                                }
                                container mt-ipv4-reachability-prefixes-subtlvs {
                                  description
                                    "List of subTLV types in the LSDB
                                     for the specified TLV";
                                  list mt-ipv4-reachability-prefixes-subtlv {
                                    key "type";
                                    description
                                      "List of subTLV types in the LSDB
                                       for the specified TLV";
                                    container prefixes-subtlvs-tag64 {
                                      description
                                        "This container defines sub-TLV 2";
                                      uses OVERLAY-OCNI-ISIS-SUBTLVS-SUBTLV-TAG64;
                                    }
                                    container prefixes-subtlvs-tag {
                                      description
                                        "This container defines sub-TLV 1";
                                      uses OVERLAY-OCNI-ISIS-SUBTLVS-SUBTLV-TAG;
                                    }
                                    container mt-ipv4-reachability-prefixes-subtlvs-state {
                                      description
                                        "State parameters for a prefix";
                                      uses OVERLAY-OCNI-ISIS-MT-IPV4-REACHABILITY-PREFIXES-PREFIX-SUBTLVS-SUBTLV-STATE;
                                    }
                                    container prefixes-subtlvs-ipv4-source-router-id {
                                      description
                                        "This container defines sub-TLV
                                         11";
                                      uses OVERLAY-OCNI-ISIS-SUBTLVS-SUBTLV-IPV4-SOURCE-ROUTER-ID;
                                    }
                                    container prefixes-subtlvs-ipv6-source-router-id {
                                      description
                                        "This container defines sub-TLV
                                         12";
                                      uses OVERLAY-OCNI-ISIS-SUBTLVS-SUBTLV-IPV6-SOURCE-ROUTER-ID;
                                    }
                                    container prefixes-subtlvs-prefix-sids {
                                      description
                                        "Prefix Segment-ID list";
                                      list prefixes-subtlvs-prefix-sid {
                                        key "value";
                                        description
                                          "Prefix Segment-ID list";
                                        leaf value {
                                          type uint32;
                                          description
                                            "Reference to the value of the
                                             prefix SID";
                                        }
                                        uses OVERLAY-OCNI-ISIS-SUBTLV-PREFIX-SIDS-PREFIX-SID;
                                      }
                                    }
                                    container prefixes-subtlvs-flags {
                                      description
                                        "This container defines sub-TLV 4";
                                      uses OVERLAY-OCNI-ISIS-SUBTLVS-SUBTLV-FLAGS;
                                    }
                                    leaf type {
                                      type string;
                                      description
                                        "Reference to the sub-TLV type";
                                    }
                                  }
                                }
                                leaf mt-id {
                                  type uint32;
                                  description
                                    "Reference to the topology ID of
                                     the topology that the prefix is
                                     within";
                                }
                                leaf prefix {
                                  type string;
                                  description
                                    "Reference to the prefix to which
                                     reachability is being advertised";
                                }
                              }
                            }
                          }
                          container mt-isn {
                            description
                              "This container defines list of ISIS
                               multi-topology neighbors";
                            container mt-isn-neighbors {
                              description
                                "This container describes IS
                                 neighbors";
                              list mt-isn-neighbor {
                                key "mt-id system-id";
                                description
                                  "This container describes IS
                                   neighbors";
                                container neighbors-instances {
                                  description
                                    "Instance of TLV-222 between the
                                     originating and remote IS";
                                  list neighbors-instance {
                                    key "id";
                                    description
                                      "Instance of TLV-222 between the
                                       originating and remote IS";
                                    container neighbors-instances-state {
                                      description
                                        "State parameters of MT neighbor";
                                      uses OVERLAY-OCNI-ISIS-INSTANCES-INSTANCE-STATE;
                                    }
                                    container neighbors-instances-undefined-subtlvs {
                                      description
                                        "Sub-TLVs that are not defined in
                                         the model or not recognised by
                                         system";
                                      list neighbors-instances-undefined-subtlv {
                                        key "type";
                                        description
                                          "Sub-TLVs that are not defined
                                           in the model or not recognised
                                           by system";
                                        leaf type {
                                          type uint32;
                                          description
                                            "Reference to the type of the
                                             undefined sub-TLV";
                                        }
                                        uses OVERLAY-OCNI-ISIS-INSTANCE-UNDEFINED-SUBTLVS-UNDEFINED-SUBTLV;
                                      }
                                    }
                                    container neighbors-instances-subtlvs {
                                      description
                                        "List of subTLV types in the LSDB
                                         for the specified TLV";
                                      list neighbors-instances-subtlv {
                                        key "type";
                                        description
                                          "List of subTLV types in the
                                           LSDB for the specified TLV";
                                        container subtlvs-ipv6-neighbor-address {
                                          description
                                            "This container defines sub-TLV
                                             13";
                                          uses OVERLAY-OCNI-ISIS-SUBTLV-IPV6-NEIGHBOR-ADDRESS;
                                        }
                                        container subtlvs-link-id {
                                          description
                                            "This container defines sub-TLV
                                             4";
                                          uses OVERLAY-OCNI-ISIS-SUBTLV-LINK-ID;
                                        }
                                        container subtlvs-ipv4-interface-address {
                                          description
                                            "This container defines sub-TLV
                                             6";
                                          uses OVERLAY-OCNI-ISIS-SUBTLV-IPV4-INTERFACE-ADDRESS;
                                        }
                                        container subtlvs-max-reservable-link-bandwidth {
                                          description
                                            "This container defines sub-TLV
                                             10";
                                          uses OVERLAY-OCNI-ISIS-SUBTLV-MAX-RESERVABLE-LINK-BANDWIDTH;
                                        }
                                        container subtlvs-max-link-bandwidth {
                                          description
                                            "This container defines sub-TLV
                                             9";
                                          uses OVERLAY-OCNI-ISIS-SUBTLV-MAX-LINK-BANDWIDTH;
                                        }
                                        container subtlvs-adjacency-sids {
                                          description
                                            "Adjacency Segment-IDs List";
                                          list subtlvs-adjacency-sid {
                                            key "value";
                                            description
                                              "Adjacency Segment-IDs List";
                                            leaf value {
                                              type uint32;
                                              description
                                                "Reference to the value of
                                                 the Adjacency-SID";
                                            }
                                            uses OVERLAY-OCNI-ISIS-ADJACENCY-SIDS-ADJACENCY-SID;
                                          }
                                        }
                                        container subtlvs-link-loss {
                                          description
                                            "This container defines
                                             unidirectional link loss delay";
                                          uses OVERLAY-OCNI-ISIS-SUBTLV-LINK-LOSS;
                                        }
                                        container subtlvs-min-max-link-delay {
                                          description
                                            "This container defines min/max
                                             link delay";
                                          uses OVERLAY-OCNI-ISIS-SUBTLV-MIN-MAX-LINK-DELAY;
                                        }
                                        container subtlvs-bandwidth-constraints {
                                          description
                                            "List of the Bandwidth
                                             Constraints sub-TLV instances
                                             present in the TLV";
                                          list subtlvs-bandwidth-constraint {
                                            key "model-id";
                                            description
                                              "List of the Bandwidth
                                               Constraints sub-TLV instances
                                               present in the TLV";
                                            container bandwidth-constraints-constraints {
                                              description
                                                "List of the constraints
                                                 within the Bandwidth
                                                 Constraints sub-TLV";
                                              list bandwidth-constraints-constraint {
                                                key "constraint-id";
                                                description
                                                  "List of the constraints
                                                   within the Bandwidth
                                                   Constraints sub-TLV";
                                                leaf constraint-id {
                                                  type uint32;
                                                  description
                                                    "Reference to the unique ID
                                                     for the BCN level";
                                                }
                                                uses OVERLAY-OCNI-ISIS-CONSTRAINTS-CONSTRAINT;
                                              }
                                            }
                                            container subtlvs-bandwidth-constraints-state {
                                              description
                                                "State parameters of IS
                                                 Extended Reachability
                                                 sub-TLV 22";
                                              uses OVERLAY-OCNI-ISIS-BANDWIDTH-CONSTRAINTS-BANDWIDTH-CONSTRAINT-STATE;
                                            }
                                            leaf model-id {
                                              type uint32;
                                              description
                                                "Reference to the model ID
                                                 associated with the instance
                                                 of the Bandwidth Constraints
                                                 sub-TLV";
                                            }
                                          }
                                        }
                                        container subtlvs-unreserved-bandwidths {
                                          description
                                            "Setup priority (0 through 7)
                                             for unreserved bandwidth";
                                          list subtlvs-unreserved-bandwidth {
                                            key "priority";
                                            description
                                              "Setup priority (0 through 7)
                                               for unreserved bandwidth";
                                            leaf priority {
                                              type uint32;
                                              description
                                                "Reference to the setup
                                                 priority to which the
                                                 unreserved bandwidth
                                                 corresponds";
                                            }
                                            uses OVERLAY-OCNI-ISIS-UNRESERVED-BANDWIDTH-SETUP-PRIORITY;
                                          }
                                        }
                                        container subtlvs-ipv4-neighbor-address {
                                          description
                                            "This container defines sub-TLV
                                             8";
                                          uses OVERLAY-OCNI-ISIS-SUBTLV-IPV4-NEIGHBOR-ADDRESS;
                                        }
                                        container subtlvs-te-default-metric {
                                          description
                                            "This container defines sub-TLV
                                             18";
                                          uses OVERLAY-OCNI-ISIS-SUBTLV-TE-DEFAULT-METRIC;
                                        }
                                        container subtlvs-ipv6-interface-address {
                                          description
                                            "This container defines sub-TLV
                                             12";
                                          uses OVERLAY-OCNI-ISIS-SUBTLV-IPV6-INTERFACE-ADDRESS;
                                        }
                                        container subtlvs-available-bandwidth {
                                          description
                                            "This container defines
                                             unidirectional lavailable
                                             bandwidth";
                                          uses OVERLAY-OCNI-ISIS-SUBTLV-AVAILABLE-BANDWIDTH;
                                        }
                                        container subtlvs-admin-group {
                                          description
                                            "This container defines sub-TLV
                                             3";
                                          uses OVERLAY-OCNI-ISIS-SUBTLV-ADMIN-GROUP;
                                        }
                                        container neighbors-instances-subtlvs-state {
                                          description
                                            "State parameters of IS
                                             neighbor state";
                                          uses OVERLAY-OCNI-ISIS-INSTANCE-SUBTLVS-SUBTLV-STATE;
                                        }
                                        container subtlvs-utilized-bandwidth {
                                          description
                                            "This container defines
                                             unidirectional utilized
                                             bandwidth";
                                          uses OVERLAY-OCNI-ISIS-SUBTLV-UTILIZED-BANDWIDTH;
                                        }
                                        container subtlvs-link-delay-variation {
                                          description
                                            "This container defines
                                             unidirectional link delay
                                             variation";
                                          uses OVERLAY-OCNI-ISIS-SUBTLV-LINK-DELAY-VARIATION;
                                        }
                                        container subtlvs-lan-adjacency-sids {
                                          description
                                            "Adjacency Segment-IDs List";
                                          list subtlvs-lan-adjacency-sid {
                                            key "value";
                                            description
                                              "Adjacency Segment-IDs List";
                                            leaf value {
                                              type uint32;
                                              description
                                                "Reference to the value of
                                                 the LAN Adjacency-SID";
                                            }
                                            uses OVERLAY-OCNI-ISIS-LAN-ADJACENCY-SIDS-LAN-ADJACENCY-SID;
                                          }
                                        }
                                        container subtlvs-extended-admin-group {
                                          description
                                            "This container defines sub-TLV
                                             14";
                                          uses OVERLAY-OCNI-ISIS-SUBTLV-EXTENDED-ADMIN-GROUP;
                                        }
                                        container subtlvs-residual-bandwidth {
                                          description
                                            "This container defines
                                             unidirectional residual
                                             bandwidth";
                                          uses OVERLAY-OCNI-ISIS-SUBTLV-RESIDUAL-BANDWIDTH;
                                        }
                                        container subtlvs-link-delay {
                                          description
                                            "This container defines
                                             unidirectional link delay";
                                          uses OVERLAY-OCNI-ISIS-SUBTLV-LINK-DELAY;
                                        }
                                        leaf type {
                                          type string;
                                          description
                                            "Reference to the sub-TLV type";
                                        }
                                      }
                                    }
                                    leaf id {
                                      type Oc-netinstisis-integer64;
                                      description
                                        "Reference to the unique
                                         identifier for the instance of
                                         the multi-topology IS neighbor
                                         TLV instance";
                                    }
                                  }
                                }
                                container mt-isn-neighbors-state {
                                  description
                                    "Operational state parameters
                                     related to the MT ISN TLV";
                                  uses OVERLAY-OCNI-ISIS-NEIGHBORS-NEIGHBOR-STATE;
                                }
                                leaf mt-id {
                                  type uint32;
                                  description
                                    "Reference to the topology that the
                                     neighbor is within";
                                }
                                leaf system-id {
                                  type string;
                                  description
                                    "Reference to the System ID of the
                                     neighbor";
                                }
                              }
                            }
                          }
                          container ipv6-srlgs {
                            description
                              "Instance of the IPv6 SRLG TLV";
                            list ipv6-srlg {
                              key "instance-number";
                              description
                                "Instance of the IPv6 SRLG TLV";
                              leaf instance-number {
                                type uint32;
                                description
                                  "Reference to the instance number of
                                   the IPv6 Shared Risk Link Group
                                   (SRLG) TLV";
                              }
                              uses OVERLAY-OCNI-ISIS-IPV6-SRLG;
                            }
                          }
                          container tlvs-state {
                            description
                              "Operational state parameters relating
                               to the specified LSP";
                            uses OVERLAY-OCNI-ISIS-TLV-STATE;
                          }
                          container purge-oi {
                            description
                              "This container defines ISIS purge TLV";
                            uses OVERLAY-OCNI-ISIS-PURGE-OI;
                          }
                          container host-name {
                            description
                              "This container defines TLV 137";
                            uses OVERLAY-OCNI-ISIS-HOSTNAME;
                          }
                          container ipv6-reachability {
                            description
                              "This container defines list of IPv6
                               reachability information";
                            container ipv6-reachability-prefixes {
                              description
                                "This list defines IPv6 extended
                                 prefix attributes";
                              list ipv6-reachability-prefixe {
                                key "prefix";
                                description
                                  "This list defines IPv6 extended
                                   prefix attributes";
                                container ipv6-reachability-prefixes-state {
                                  description
                                    "State parameters of IPv6 prefix
                                     attributes";
                                  uses OVERLAY-OCNI-ISIS-PREFIXES-PREFIX-STATE;
                                }
                                container ipv6-reachability-prefixes-subtlvs {
                                  description
                                    "List of subTLV types in the LSDB
                                     for the specified TLV";
                                  list ipv6-reachability-prefixes-subtlv {
                                    key "type";
                                    description
                                      "List of subTLV types in the LSDB
                                       for the specified TLV";
                                    container subtlvs-tag {
                                      description
                                        "This container defines sub-TLV 1";
                                      uses OVERLAY-OCNI-ISIS-SUBTLV-TAG;
                                    }
                                    container subtlvs-tag64 {
                                      description
                                        "This container defines sub-TLV 2";
                                      uses OVERLAY-OCNI-ISIS-SUBTLV-TAG64;
                                    }
                                    container subtlvs-prefix-sids {
                                      description
                                        "Prefix Segment-ID list";
                                      list subtlvs-prefix-sid {
                                        key "value";
                                        description
                                          "Prefix Segment-ID list";
                                        leaf value {
                                          type uint32;
                                          description
                                            "Reference to the value of the
                                             prefix SID";
                                        }
                                        uses OVERLAY-OCNI-ISIS-PREFIX-SIDS-PREFIX-SID;
                                      }
                                    }
                                    container subtlvs-ipv4-source-router-id {
                                      description
                                        "This container defines sub-TLV
                                         11";
                                      uses OVERLAY-OCNI-ISIS-SUBTLV-IPV4-SOURCE-ROUTER-ID;
                                    }
                                    container ipv6-reachability-prefixes-subtlvs-state {
                                      description
                                        "State parameters for a prefix";
                                      uses OVERLAY-OCNI-ISIS-PREFIXES-PREFIX-SUBTLVS-SUBTLV-STATE;
                                    }
                                    container subtlvs-ipv6-source-router-id {
                                      description
                                        "This container defines sub-TLV
                                         12";
                                      uses OVERLAY-OCNI-ISIS-SUBTLV-IPV6-SOURCE-ROUTER-ID;
                                    }
                                    container subtlvs-flags {
                                      description
                                        "This container defines sub-TLV 4";
                                      uses OVERLAY-OCNI-ISIS-SUBTLV-FLAGS;
                                    }
                                    leaf type {
                                      type string;
                                      description
                                        "Reference to the sub-TLV type";
                                    }
                                  }
                                }
                                container ipv6-reachability-prefixes-undefined-subtlvs {
                                  description
                                    "Sub-TLVs that are not defined in
                                     the model or not recognised by
                                     system";
                                  list ipv6-reachability-prefixes-undefined-subtlv {
                                    key "type";
                                    description
                                      "Sub-TLVs that are not defined in
                                       the model or not recognised by
                                       system";
                                    leaf type {
                                      type uint32;
                                      description
                                        "Reference to the type of the
                                         undefined sub-TLV";
                                    }
                                    uses OVERLAY-OCNI-ISIS-PREFIXES-PREFIX-UNDEFINED-SUBTLVS-UNDEFINED-SUBTLV;
                                  }
                                }
                                leaf prefix {
                                  type string;
                                  description
                                    "Reference to the IPv6 prefix that
                                     the TLV corresponds to";
                                }
                              }
                            }
                          }
                          container ipv6-te-router-id {
                            description
                              "This container defines TLV 140";
                            uses OVERLAY-OCNI-ISIS-IPV6-TE-ROUTER-ID;
                          }
                          container ipv4-internal-reachability {
                            description
                              "This container defines list of IPv4
                               internal reachability information";
                            container prefixes {
                              description
                                "IPv4 prefixes and internal
                                 reachability attributes";
                              list prefixe {
                                key "prefix";
                                description
                                  "IPv4 prefixes and internal
                                   reachability attributes";
                                leaf prefix {
                                  type string;
                                  description
                                    "Reference to the IPv4 prefix";
                                }
                                uses OVERLAY-OCNI-ISIS-PREFIX;
                              }
                            }
                          }
                          container ipv6-interface-addresses {
                            description
                              "This container defines TLV 232";
                            uses OVERLAY-OCNI-ISIS-IPV6-INTERFACE-ADDRESSES;
                          }
                          container extended-is-reachability {
                            description
                              "This container defines list of ISIS
                               extended reachability neighbors";
                            container extended-is-reachability-neighbors {
                              description
                                "This list describes ISIS extended
                                 neighbors and reachability
                                 attributes";
                              list extended-is-reachability-neighbor {
                                key "system-id";
                                description
                                  "This list describes ISIS extended
                                   neighbors and reachability
                                   attributes";
                                container instances {
                                  description
                                    "Instance of the TLV to the remote
                                     IS neighbor";
                                  list instance {
                                    key "id";
                                    description
                                      "Instance of the TLV to the remote
                                       IS neighbor";
                                    container instances-subtlvs {
                                      description
                                        "List of subTLV types in the LSDB
                                         for the specified TLV";
                                      list instances-subtlv {
                                        key "type";
                                        description
                                          "List of subTLV types in the
                                           LSDB for the specified TLV";
                                        container min-max-link-delay {
                                          description
                                            "This container defines min/max
                                             link delay";
                                          uses OVERLAY-OCNI-ISIS-MIN-MAX-LINK-DELAY;
                                        }
                                        container max-link-bandwidth {
                                          description
                                            "This container defines sub-TLV
                                             9";
                                          uses OVERLAY-OCNI-ISIS-MAX-LINK-BANDWIDTH;
                                        }
                                        container ipv6-neighbor-address {
                                          description
                                            "This container defines sub-TLV
                                             13";
                                          uses OVERLAY-OCNI-ISIS-IPV6-NEIGHBOR-ADDRESS;
                                        }
                                        container ipv6-interface-address {
                                          description
                                            "This container defines sub-TLV
                                             12";
                                          uses OVERLAY-OCNI-ISIS-IPV6-INTERFACE-ADDRESS;
                                        }
                                        container lan-adjacency-sids {
                                          description
                                            "Adjacency Segment-IDs List";
                                          list lan-adjacency-sid {
                                            key "value";
                                            description
                                              "Adjacency Segment-IDs List";
                                            leaf value {
                                              type uint32;
                                              description
                                                "Reference to the value of
                                                 the LAN Adjacency-SID";
                                            }
                                            uses OVERLAY-OCNI-ISIS-LAN-ADJACENCY-SID;
                                          }
                                        }
                                        container available-bandwidth {
                                          description
                                            "This container defines
                                             unidirectional lavailable
                                             bandwidth";
                                          uses OVERLAY-OCNI-ISIS-AVAILABLE-BANDWIDTH;
                                        }
                                        container adjacency-sids {
                                          description
                                            "Adjacency Segment-IDs List";
                                          list adjacency-sid {
                                            key "value";
                                            description
                                              "Adjacency Segment-IDs List";
                                            leaf value {
                                              type uint32;
                                              description
                                                "Reference to the value of
                                                 the Adjacency-SID";
                                            }
                                            uses OVERLAY-OCNI-ISIS-ADJACENCY-SID;
                                          }
                                        }
                                        container te-default-metric {
                                          description
                                            "This container defines sub-TLV
                                             18";
                                          uses OVERLAY-OCNI-ISIS-TE-DEFAULT-METRIC;
                                        }
                                        container admin-group {
                                          description
                                            "This container defines sub-TLV
                                             3";
                                          uses OVERLAY-OCNI-ISIS-ADMIN-GROUP;
                                        }
                                        container link-delay-variation {
                                          description
                                            "This container defines
                                             unidirectional link delay
                                             variation";
                                          uses OVERLAY-OCNI-ISIS-LINK-DELAY-VARIATION;
                                        }
                                        container max-reservable-link-bandwidth {
                                          description
                                            "This container defines sub-TLV
                                             10";
                                          uses OVERLAY-OCNI-ISIS-MAX-RESERVABLE-LINK-BANDWIDTH;
                                        }
                                        container link-id {
                                          description
                                            "This container defines sub-TLV
                                             4";
                                          uses OVERLAY-OCNI-ISIS-LINK-ID;
                                        }
                                        container extended-admin-group {
                                          description
                                            "This container defines sub-TLV
                                             14";
                                          uses OVERLAY-OCNI-ISIS-EXTENDED-ADMIN-GROUP;
                                        }
                                        container unreserved-bandwidths {
                                          description
                                            "Setup priority (0 through 7)
                                             for unreserved bandwidth";
                                          list unreserved-bandwidth {
                                            key "priority";
                                            description
                                              "Setup priority (0 through 7)
                                               for unreserved bandwidth";
                                            leaf priority {
                                              type uint32;
                                              description
                                                "Reference to the setup
                                                 priority to which the
                                                 unreserved bandwidth
                                                 corresponds";
                                            }
                                            uses OVERLAY-OCNI-ISIS-SETUP-PRIORITY;
                                          }
                                        }
                                        container link-loss {
                                          description
                                            "This container defines
                                             unidirectional link loss delay";
                                          uses OVERLAY-OCNI-ISIS-LINK-LOSS;
                                        }
                                        container utilized-bandwidth {
                                          description
                                            "This container defines
                                             unidirectional utilized
                                             bandwidth";
                                          uses OVERLAY-OCNI-ISIS-UTILIZED-BANDWIDTH;
                                        }
                                        container ipv4-interface-address {
                                          description
                                            "This container defines sub-TLV
                                             6";
                                          uses OVERLAY-OCNI-ISIS-IPV4-INTERFACE-ADDRESS;
                                        }
                                        container ipv4-neighbor-address {
                                          description
                                            "This container defines sub-TLV
                                             8";
                                          uses OVERLAY-OCNI-ISIS-IPV4-NEIGHBOR-ADDRESS;
                                        }
                                        container residual-bandwidth {
                                          description
                                            "This container defines
                                             unidirectional residual
                                             bandwidth";
                                          uses OVERLAY-OCNI-ISIS-RESIDUAL-BANDWIDTH;
                                        }
                                        container bandwidth-constraints {
                                          description
                                            "List of the Bandwidth
                                             Constraints sub-TLV instances
                                             present in the TLV";
                                          list bandwidth-constraint {
                                            key "model-id";
                                            description
                                              "List of the Bandwidth
                                               Constraints sub-TLV instances
                                               present in the TLV";
                                            container constraints {
                                              description
                                                "List of the constraints
                                                 within the Bandwidth
                                                 Constraints sub-TLV";
                                              list constraint {
                                                key "constraint-id";
                                                description
                                                  "List of the constraints
                                                   within the Bandwidth
                                                   Constraints sub-TLV";
                                                leaf constraint-id {
                                                  type uint32;
                                                  description
                                                    "Reference to the unique ID
                                                     for the BCN level";
                                                }
                                                uses OVERLAY-OCNI-ISIS-CONSTRAINT;
                                              }
                                            }
                                            container bandwidth-constraints-state {
                                              description
                                                "State parameters of IS
                                                 Extended Reachability
                                                 sub-TLV 22";
                                              uses OVERLAY-OCNI-ISIS-BANDWIDTH-CONSTRAINT-STATE;
                                            }
                                            leaf model-id {
                                              type uint32;
                                              description
                                                "Reference to the model ID
                                                 associated with the instance
                                                 of the Bandwidth Constraints
                                                 sub-TLV";
                                            }
                                          }
                                        }
                                        container instances-subtlvs-state {
                                          description
                                            "State parameters of IS
                                             neighbor state";
                                          uses OVERLAY-OCNI-ISIS-SUBTLVS-SUBTLV-STATE;
                                        }
                                        container link-delay {
                                          description
                                            "This container defines
                                             unidirectional link delay";
                                          uses OVERLAY-OCNI-ISIS-LINK-DELAY;
                                        }
                                        leaf type {
                                          type string;
                                          description
                                            "Reference to the sub-TLV type";
                                        }
                                      }
                                    }
                                    container instances-state {
                                      description
                                        "State parameters of extended
                                         neighbor";
                                      uses OVERLAY-OCNI-ISIS-INSTANCE-STATE;
                                    }
                                    container instances-undefined-subtlvs {
                                      description
                                        "Sub-TLVs that are not defined in
                                         the model or not recognised by
                                         system";
                                      list instances-undefined-subtlv {
                                        key "type";
                                        description
                                          "Sub-TLVs that are not defined
                                           in the model or not recognised
                                           by system";
                                        leaf type {
                                          type uint32;
                                          description
                                            "Reference to the type of the
                                             undefined sub-TLV";
                                        }
                                        uses OVERLAY-OCNI-ISIS-UNDEFINED-SUBTLVS-UNDEFINED-SUBTLV;
                                      }
                                    }
                                    leaf id {
                                      type Oc-netinstisis-integer64;
                                      description
                                        "Reference to the unique
                                         identifier for the instance of
                                         the extended IS reachability
                                         sub-TLV";
                                    }
                                  }
                                }
                                container neighbors-state {
                                  description
                                    "State parameters corresponding to
                                     the extended neighbour";
                                  uses OVERLAY-OCNI-ISIS-NEIGHBOR-STATE;
                                }
                                leaf system-id {
                                  type string;
                                  description
                                    "Reference to the neighboring
                                     system's system ID";
                                }
                              }
                            }
                          }
                          container instance-ids {
                            description
                              "A list of instance IDs received
                               within TLV 7 within an IS-IS LSP";
                            list instance-id {
                              key "instance-id";
                              description
                                "A list of instance IDs received
                                 within TLV 7 within an IS-IS LSP";
                              leaf instance-id {
                                type uint32;
                                description
                                  "Reference to the unique instance ID";
                              }
                              uses OVERLAY-OCNI-ISIS-INSTANCE-ID;
                            }
                          }
                          container ipv4-srlgs {
                            description
                              "Instance of the IPv4 SRLG TLV";
                            list ipv4-srlg {
                              key "instance-number";
                              description
                                "Instance of the IPv4 SRLG TLV";
                              leaf instance-number {
                                type uint32;
                                description
                                  "Reference to the instance number of
                                   TLV 138";
                              }
                              uses OVERLAY-OCNI-ISIS-IPV4-SRLG;
                            }
                          }
                          container is-reachability {
                            description
                              "This container describes list of ISIS
                               neighbors and attributes";
                            container neighbors {
                              description
                                "IS reachability neighbor attributes";
                              list neighbor {
                                key "system-id";
                                description
                                  "IS reachability neighbor attributes";
                                leaf system-id {
                                  type string;
                                  description
                                    "Reference to the system ID of the
                                     neighbor";
                                }
                                uses OVERLAY-OCNI-ISIS-NEIGHBOR;
                              }
                            }
                          }
                          container ipv4-te-router-id {
                            description
                              "This container defines TLV 134";
                            uses OVERLAY-OCNI-ISIS-IPV4-TE-ROUTER-ID;
                          }
                          container nlpid {
                            description
                              "This container defines TLV 129";
                            uses OVERLAY-OCNI-ISIS-NLPID;
                          }
                          container extended-ipv4-reachability {
                            description
                              "This container defines list of IPv4
                               extended reachability information";
                            container extended-ipv4-reachability-prefixes {
                              description
                                "This list describes IPv4 extended
                                 prefixes and attributes";
                              list extended-ipv4-reachability-prefixe {
                                key "prefix";
                                description
                                  "This list describes IPv4 extended
                                   prefixes and attributes";
                                container prefixes-state {
                                  description
                                    "State parameters of an IPv4
                                     extended prefix";
                                  uses OVERLAY-OCNI-ISIS-PREFIX-STATE;
                                }
                                container prefixes-subtlvs {
                                  description
                                    "List of subTLV types in the LSDB
                                     for the specified TLV";
                                  list prefixes-subtlv {
                                    key "type";
                                    description
                                      "List of subTLV types in the LSDB
                                       for the specified TLV";
                                    container tag {
                                      description
                                        "This container defines sub-TLV 1";
                                      uses OVERLAY-OCNI-ISIS-TAG;
                                    }
                                    container ipv4-source-router-id {
                                      description
                                        "This container defines sub-TLV
                                         11";
                                      uses OVERLAY-OCNI-ISIS-IPV4-SOURCE-ROUTER-ID;
                                    }
                                    container ipv6-source-router-id {
                                      description
                                        "This container defines sub-TLV
                                         12";
                                      uses OVERLAY-OCNI-ISIS-IPV6-SOURCE-ROUTER-ID;
                                    }
                                    container prefixes-subtlvs-state {
                                      description
                                        "State parameters for a prefix";
                                      uses OVERLAY-OCNI-ISIS-PREFIX-SUBTLVS-SUBTLV-STATE;
                                    }
                                    container flags {
                                      description
                                        "This container defines sub-TLV 4";
                                      uses OVERLAY-OCNI-ISIS-FLAGS;
                                    }
                                    container tag64 {
                                      description
                                        "This container defines sub-TLV 2";
                                      uses OVERLAY-OCNI-ISIS-TAG64;
                                    }
                                    container prefix-sids {
                                      description
                                        "Prefix Segment-ID list";
                                      list prefix-sid {
                                        key "value";
                                        description
                                          "Prefix Segment-ID list";
                                        leaf value {
                                          type uint32;
                                          description
                                            "Reference to the value of the
                                             prefix SID";
                                        }
                                        uses OVERLAY-OCNI-ISIS-PREFIX-SID;
                                      }
                                    }
                                    leaf type {
                                      type string;
                                      description
                                        "Reference to the sub-TLV type";
                                    }
                                  }
                                }
                                container prefixes-undefined-subtlvs {
                                  description
                                    "Sub-TLVs that are not defined in
                                     the model or not recognised by
                                     system";
                                  list prefixes-undefined-subtlv {
                                    key "type";
                                    description
                                      "Sub-TLVs that are not defined in
                                       the model or not recognised by
                                       system";
                                    leaf type {
                                      type uint32;
                                      description
                                        "Reference to the type of the
                                         undefined sub-TLV";
                                    }
                                    uses OVERLAY-OCNI-ISIS-PREFIX-UNDEFINED-SUBTLVS-UNDEFINED-SUBTLV;
                                  }
                                }
                                leaf prefix {
                                  type string;
                                  description
                                    "Reference to the IPv4 prefix that
                                     the TLV describes the attributes
                                     of";
                                }
                              }
                            }
                          }
                          container multi-topology {
                            description
                              "This container defines the topology
                               supported";
                            container topologies {
                              description
                                "This list describes a topology";
                              list topology {
                                key "mt-id";
                                description
                                  "This list describes a topology";
                                leaf mt-id {
                                  type uint32;
                                  description
                                    "Reference to the multi-topology ID
                                     being described by the list entry";
                                }
                                uses OVERLAY-OCNI-ISIS-TOPOLOGY;
                              }
                            }
                          }
                          container ipv4-external-reachability {
                            description
                              "This container defines list of IPv4
                               external reachability information";
                            container ipv4-external-reachability-prefixes {
                              description
                                "IPv4 external prefixes and
                                 reachability attributes";
                              list ipv4-external-reachability-prefixe {
                                key "prefix";
                                description
                                  "IPv4 external prefixes and
                                   reachability attributes";
                                leaf prefix {
                                  type string;
                                  description
                                    "Reference to the IPv4 prefix";
                                }
                                uses OVERLAY-OCNI-ISIS-PREFIXES-PREFIX;
                              }
                            }
                          }
                          container mt-ipv6-reachability {
                            description
                              "This container defines list of IPv6
                               reachability information in multi -
                               topology environment";
                            container mt-ipv6-reachability-prefixes {
                              description
                                "List of IPv6 prefixes contained
                                 within MT reachability TLV";
                              list mt-ipv6-reachability-prefixe {
                                key "prefix mt-id";
                                description
                                  "List of IPv6 prefixes contained
                                   within MT reachability TLV";
                                container mt-ipv6-reachability-prefixes-state {
                                  description
                                    "State parameters relating an IPv6
                                     prefix attribute";
                                  uses OVERLAY-OCNI-ISIS-MT-IPV6-REACHABILITY-PREFIXES-PREFIX-STATE;
                                }
                                container mt-ipv6-reachability-prefixes-subtlvs {
                                  description
                                    "List of subTLV types in the LSDB
                                     for the specified TLV";
                                  list mt-ipv6-reachability-prefixes-subtlv {
                                    key "type";
                                    description
                                      "List of subTLV types in the LSDB
                                       for the specified TLV";
                                    container mt-ipv6-reachability-prefixes-subtlvs-prefix-sids {
                                      description
                                        "Prefix Segment-ID list";
                                      list mt-ipv6-reachability-prefixes-subtlvs-prefix-sid {
                                        key "value";
                                        description
                                          "Prefix Segment-ID list";
                                        leaf value {
                                          type uint32;
                                          description
                                            "Reference to the value of the
                                             prefix SID";
                                        }
                                        uses OVERLAY-OCNI-ISIS-SUBTLVS-SUBTLV-PREFIX-SIDS-PREFIX-SID;
                                      }
                                    }
                                    container mt-ipv6-reachability-prefixes-subtlvs-flags {
                                      description
                                        "This container defines sub-TLV 4";
                                      uses OVERLAY-OCNI-ISIS-PREFIX-SUBTLVS-SUBTLV-FLAGS;
                                    }
                                    container mt-ipv6-reachability-prefixes-subtlvs-ipv4-source-router-id {
                                      description
                                        "This container defines sub-TLV
                                         11";
                                      uses OVERLAY-OCNI-ISIS-PREFIX-SUBTLVS-SUBTLV-IPV4-SOURCE-ROUTER-ID;
                                    }
                                    container mt-ipv6-reachability-prefixes-subtlvs-tag64 {
                                      description
                                        "This container defines sub-TLV 2";
                                      uses OVERLAY-OCNI-ISIS-PREFIX-SUBTLVS-SUBTLV-TAG64;
                                    }
                                    container mt-ipv6-reachability-prefixes-subtlvs-ipv6-source-router-id {
                                      description
                                        "This container defines sub-TLV
                                         12";
                                      uses OVERLAY-OCNI-ISIS-PREFIX-SUBTLVS-SUBTLV-IPV6-SOURCE-ROUTER-ID;
                                    }
                                    container mt-ipv6-reachability-prefixes-subtlvs-tag {
                                      description
                                        "This container defines sub-TLV 1";
                                      uses OVERLAY-OCNI-ISIS-PREFIX-SUBTLVS-SUBTLV-TAG;
                                    }
                                    container mt-ipv6-reachability-prefixes-subtlvs-state {
                                      description
                                        "State parameters for a prefix";
                                      uses OVERLAY-OCNI-ISIS-MT-IPV6-REACHABILITY-PREFIXES-PREFIX-SUBTLVS-SUBTLV-STATE;
                                    }
                                    leaf type {
                                      type string;
                                      description
                                        "Reference to the sub-TLV type";
                                    }
                                  }
                                }
                                container mt-ipv6-reachability-prefixes-undefined-subtlvs {
                                  description
                                    "Sub-TLVs that are not defined in
                                     the model or not recognised by
                                     system";
                                  list mt-ipv6-reachability-prefixes-undefined-subtlv {
                                    key "type";
                                    description
                                      "Sub-TLVs that are not defined in
                                       the model or not recognised by
                                       system";
                                    leaf type {
                                      type uint32;
                                      description
                                        "Reference to the type of the
                                         undefined sub-TLV";
                                    }
                                    uses OVERLAY-OCNI-ISIS-MT-IPV6-REACHABILITY-PREFIXES-PREFIX-UNDEFINED-SUBTLVS-UNDEFINED-SUBTLV;
                                  }
                                }
                                leaf prefix {
                                  type string;
                                  description
                                    "Reference to the IPv6 prefix
                                     described by the TLV";
                                }
                                leaf mt-id {
                                  type uint32;
                                  description
                                    "Reference to the multi-topology ID";
                                }
                              }
                            }
                          }
                          leaf type {
                            type string;
                            description
                              "Reference to the TLV's type";
                          }
                        }
                      }
                      leaf lsp-id {
                        type string;
                        description
                          "A reference to the Link State PDU ID";
                      }
                    }
                  }
                  leaf level-number {
                    type uint32;
                    description
                      "Reference to ISIS level-number";
                  }
                }
              }
            }
            leaf identifier {
              type string;
              description
                "The protocol name for the routing or
                 forwarding protocol to be instantiated";
            }
            leaf name {
              type string;
              description
                "An operator-assigned identifier for the
                 routing or forwarding protocol";
            }
          }
        }
        container state {
          description
            "Operational state parameters relating to a
             network instance";
          uses OVERLAY-OCNI-ISIS-STATE;
        }
        leaf name {
          type string;
          description
            "A unique name identifying the network instance";
        }
      }
    }
  }
}
