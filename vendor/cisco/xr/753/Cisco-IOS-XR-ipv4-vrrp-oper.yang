module Cisco-IOS-XR-ipv4-vrrp-oper {
  namespace "http://cisco.com/ns/yang/Cisco-IOS-XR-ipv4-vrrp-oper";
  prefix ipv4-vrrp-oper;

  import Cisco-IOS-XR-types {
    prefix xr;
  }
  import cisco-semver {
    prefix semver;
  }
  include Cisco-IOS-XR-ipv4-vrrp-oper-sub1 {
    revision-date 2022-03-24;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ipv4-vrrp package operational data.
     
     This module contains definitions
     for the following management objects:
       vrrp: VRRP operational data
     
     Copyright (c) 2013-2022 by Cisco Systems, Inc.
     All rights reserved.";

  revision 2022-03-24 {
    description
      "Increase in interface name length";
    semver:module-version "1.0.1m";
  }
  revision 2019-04-05 {
    description
      "Establish semantic version baseline.";
    semver:module-version "1.0.0";
  }
  revision 2018-12-12 {
    description
      "Moved router id to a range type.";
  }
  revision 2017-09-07 {
    description
      "Fixed type translation error.";
  }
  revision 2017-05-01 {
    description
      "Fixing backward compatibility error in module.";
  }
  revision 2016-12-16 {
    description
      "IOS XR 6.2.1 revision.";
  }
  revision 2015-11-09 {
    description
      "IOS XR 6.0 revision.";
  }

  typedef Virtual-router-id {
    type uint32 {
      range "1..255";
    }
    description
      "Virtual router id";
  }

  container vrrp {
    config false;
    description
      "VRRP operational data";
    container summary {
      description
        "VRRP summary statistics";
      uses VRRP-SUMMARY-INFO;
    }
    container ipv6 {
      description
        "IPv6 VRRP configuration";
      container track-items {
        description
          "The VRRP tracked item table";
        list track-item {
          key "interface-name virtual-router-id tracked-interface-name";
          description
            "A configured VRRP IP address entry";
          leaf interface-name {
            type xr:Interface-name;
            description
              "The interface name to track";
          }
          leaf virtual-router-id {
            type Virtual-router-id;
            description
              "The VRRP virtual router id";
          }
          leaf tracked-interface-name {
            type xr:Interface-name;
            description
              "The name of the tracked interface";
          }
          uses VRRP-TRACKITEM-INFO;
        }
      }
      container virtual-routers {
        description
          "The VRRP virtual router table";
        list virtual-router {
          key "interface-name virtual-router-id";
          description
            "A VRRP virtual router";
          leaf interface-name {
            type xr:Interface-name;
            description
              "The name of the interface";
          }
          leaf virtual-router-id {
            type Virtual-router-id;
            description
              "The VRRP virtual router id";
          }
          uses VRRP-VROUTER-INFO;
        }
      }
      container interfaces {
        description
          "The VRRP interface table";
        list interface {
          key "interface-name";
          description
            "A VRRP interface entry";
          leaf interface-name {
            type xr:Interface-name;
            description
              "The name of the interface";
          }
          uses VRRP-INTERFACE-INFO;
        }
      }
    }
    container ipv4 {
      description
        "IPv4 VRRP configuration";
      container interfaces {
        description
          "The VRRP interface table";
        list interface {
          key "interface-name";
          description
            "A VRRP interface entry";
          leaf interface-name {
            type xr:Interface-name;
            description
              "The name of the interface";
          }
          uses VRRP-INTERFACE-INFO;
        }
      }
      container track-items {
        description
          "The VRRP tracked item table";
        list track-item {
          key "interface-name virtual-router-id tracked-interface-name";
          description
            "A configured VRRP IP address entry";
          leaf interface-name {
            type xr:Interface-name;
            description
              "The interface name to track";
          }
          leaf virtual-router-id {
            type Virtual-router-id;
            description
              "The VRRP virtual router id";
          }
          leaf tracked-interface-name {
            type xr:Interface-name;
            description
              "The name of the tracked interface";
          }
          uses VRRP-TRACKITEM-INFO;
        }
      }
      container virtual-routers {
        description
          "The VRRP virtual router table";
        list virtual-router {
          key "interface-name virtual-router-id";
          description
            "A VRRP virtual router";
          leaf interface-name {
            type xr:Interface-name;
            description
              "The name of the interface";
          }
          leaf virtual-router-id {
            type Virtual-router-id;
            description
              "The VRRP virtual router id";
          }
          uses VRRP-VROUTER-INFO;
        }
      }
    }
    container mgo-sessions {
      description
        "VRRP MGO Session information";
      list mgo-session {
        key "session-name";
        description
          "A VRRP MGO Session";
        leaf session-name {
          type xr:Cisco-ios-xr-string;
          description
            "The name of the session";
        }
        uses VRRP-MGO-INFO;
      }
    }
  }
}
