//*************  DO-NOT EDIT  **************
//*********** Auto-generated file ********** 

 module cisco-xr-openconfig-if-tunnel-deviations {

  namespace "http://cisco.com/ns/yang/cisco-xr-openconfig-if-tunnel-deviations";
  prefix  "oc-tundevs";

  import openconfig-if-tunnel { prefix oc-tun; }
  import openconfig-interfaces { prefix oc-if; }

  organization "Cisco Systems, Inc.";

  contact
    "Cisco Systems, Inc.
     Customer Service

     Postal: 170 West Tasman Drive
     San Jose, CA 95134

     Tel: +1 800 553-NETS

     E-mail: cs-yang@cisco.com";

  description
    "This module contains a set of deviations for 
 
     openconfig-if-tunnel.yang@2018-11-21 

     on Cisco IOS-XR devices.

     Copyright (c) 2017, 2022 by Cisco Systems, Inc.
     All rights reserved.";

  revision "2022-04-22" {
    description
      "Removed duplicate entries";
  }
  
  revision "2022-03-08" {
    description
      "Disabled unsupported nodes";
  }

  revision "2020-03-20" {
    description
      "Initial revision applicable to IOS-XR 6.4.1";
  }


  deviation /oc-if:interfaces/oc-if:interface/oc-tun:tunnel/oc-tun:ipv4/oc-tun:addresses/oc-tun:address {
    deviate not-supported;
  }

  deviation /oc-if:interfaces/oc-if:interface/oc-tun:tunnel/oc-tun:ipv4/oc-tun:proxy-arp/oc-tun:config/oc-tun:mode {
    deviate not-supported;
  }

  deviation /oc-if:interfaces/oc-if:interface/oc-tun:tunnel/oc-tun:ipv4/oc-tun:proxy-arp/oc-tun:state/oc-tun:mode {
    deviate not-supported;
  }

  deviation /oc-if:interfaces/oc-if:interface/oc-tun:tunnel/oc-tun:ipv4/oc-tun:neighbors/oc-tun:neighbor {
    deviate not-supported;
  }

  deviation /oc-if:interfaces/oc-if:interface/oc-tun:tunnel/oc-tun:ipv4/oc-tun:unnumbered/oc-tun:config/oc-tun:enabled {
    deviate not-supported;
  }

  deviation /oc-if:interfaces/oc-if:interface/oc-tun:tunnel/oc-tun:ipv4/oc-tun:unnumbered/oc-tun:state/oc-tun:enabled {
    deviate not-supported;
  }

  deviation /oc-if:interfaces/oc-if:interface/oc-tun:tunnel/oc-tun:ipv4/oc-tun:unnumbered/oc-tun:interface-ref/oc-tun:config/oc-tun:interface {
    deviate not-supported;
  }

  deviation /oc-if:interfaces/oc-if:interface/oc-tun:tunnel/oc-tun:ipv4/oc-tun:unnumbered/oc-tun:interface-ref/oc-tun:config/oc-tun:subinterface {
    deviate not-supported;
  }

  deviation /oc-if:interfaces/oc-if:interface/oc-tun:tunnel/oc-tun:ipv4/oc-tun:unnumbered/oc-tun:interface-ref/oc-tun:state/oc-tun:interface {
    deviate not-supported;
  }

  deviation /oc-if:interfaces/oc-if:interface/oc-tun:tunnel/oc-tun:ipv4/oc-tun:unnumbered/oc-tun:interface-ref/oc-tun:state/oc-tun:subinterface {
    deviate not-supported;
  }

  deviation /oc-if:interfaces/oc-if:interface/oc-tun:tunnel/oc-tun:ipv4/oc-tun:config/oc-tun:enabled {
    deviate not-supported;
  }

  deviation /oc-if:interfaces/oc-if:interface/oc-tun:tunnel/oc-tun:ipv4/oc-tun:config/oc-tun:mtu {
    deviate not-supported;
  }

  deviation /oc-if:interfaces/oc-if:interface/oc-tun:tunnel/oc-tun:ipv4/oc-tun:config/oc-tun:dhcp-client {
    deviate not-supported;
  }

  deviation /oc-if:interfaces/oc-if:interface/oc-tun:tunnel/oc-tun:ipv4/oc-tun:state/oc-tun:enabled {
    deviate not-supported;
  }

  deviation /oc-if:interfaces/oc-if:interface/oc-tun:tunnel/oc-tun:ipv4/oc-tun:state/oc-tun:mtu {
    deviate not-supported;
  }

  deviation /oc-if:interfaces/oc-if:interface/oc-tun:tunnel/oc-tun:ipv4/oc-tun:state/oc-tun:dhcp-client {
    deviate not-supported;
  }

  deviation /oc-if:interfaces/oc-if:interface/oc-tun:tunnel/oc-tun:ipv4/oc-tun:state/oc-tun:counters/oc-tun:in-pkts {
    deviate not-supported;
  }

  deviation /oc-if:interfaces/oc-if:interface/oc-tun:tunnel/oc-tun:ipv4/oc-tun:state/oc-tun:counters/oc-tun:in-octets {
    deviate not-supported;
  }

  deviation /oc-if:interfaces/oc-if:interface/oc-tun:tunnel/oc-tun:ipv4/oc-tun:state/oc-tun:counters/oc-tun:in-error-pkts {
    deviate not-supported;
  }

  deviation /oc-if:interfaces/oc-if:interface/oc-tun:tunnel/oc-tun:ipv4/oc-tun:state/oc-tun:counters/oc-tun:in-forwarded-pkts {
    deviate not-supported;
  }

  deviation /oc-if:interfaces/oc-if:interface/oc-tun:tunnel/oc-tun:ipv4/oc-tun:state/oc-tun:counters/oc-tun:in-forwarded-octets {
    deviate not-supported;
  }

  deviation /oc-if:interfaces/oc-if:interface/oc-tun:tunnel/oc-tun:ipv4/oc-tun:state/oc-tun:counters/oc-tun:in-discarded-pkts {
    deviate not-supported;
  }

  deviation /oc-if:interfaces/oc-if:interface/oc-tun:tunnel/oc-tun:ipv4/oc-tun:state/oc-tun:counters/oc-tun:out-pkts {
    deviate not-supported;
  }

  deviation /oc-if:interfaces/oc-if:interface/oc-tun:tunnel/oc-tun:ipv4/oc-tun:state/oc-tun:counters/oc-tun:out-octets {
    deviate not-supported;
  }

  deviation /oc-if:interfaces/oc-if:interface/oc-tun:tunnel/oc-tun:ipv4/oc-tun:state/oc-tun:counters/oc-tun:out-error-pkts {
    deviate not-supported;
  }

  deviation /oc-if:interfaces/oc-if:interface/oc-tun:tunnel/oc-tun:ipv4/oc-tun:state/oc-tun:counters/oc-tun:out-forwarded-pkts {
    deviate not-supported;
  }

  deviation /oc-if:interfaces/oc-if:interface/oc-tun:tunnel/oc-tun:ipv4/oc-tun:state/oc-tun:counters/oc-tun:out-forwarded-octets {
    deviate not-supported;
  }

  deviation /oc-if:interfaces/oc-if:interface/oc-tun:tunnel/oc-tun:ipv4/oc-tun:state/oc-tun:counters/oc-tun:out-discarded-pkts {
    deviate not-supported;
  }

  deviation /oc-if:interfaces/oc-if:interface/oc-tun:tunnel/oc-tun:ipv6/oc-tun:addresses/oc-tun:address/oc-tun:state/oc-tun:origin {
    deviate not-supported;
  }

  deviation /oc-if:interfaces/oc-if:interface/oc-tun:tunnel/oc-tun:ipv6/oc-tun:router-advertisement/oc-tun:config/oc-tun:interval {
    deviate not-supported;
  }

  deviation /oc-if:interfaces/oc-if:interface/oc-tun:tunnel/oc-tun:ipv6/oc-tun:router-advertisement/oc-tun:config/oc-tun:lifetime {
    deviate not-supported;
  }

  deviation /oc-if:interfaces/oc-if:interface/oc-tun:tunnel/oc-tun:ipv6/oc-tun:router-advertisement/oc-tun:config/oc-tun:suppress {
    deviate not-supported;
  }

  deviation /oc-if:interfaces/oc-if:interface/oc-tun:tunnel/oc-tun:ipv6/oc-tun:router-advertisement/oc-tun:state/oc-tun:interval {
    deviate not-supported;
  }

  deviation /oc-if:interfaces/oc-if:interface/oc-tun:tunnel/oc-tun:ipv6/oc-tun:router-advertisement/oc-tun:state/oc-tun:lifetime {
    deviate not-supported;
  }

  deviation /oc-if:interfaces/oc-if:interface/oc-tun:tunnel/oc-tun:ipv6/oc-tun:router-advertisement/oc-tun:state/oc-tun:suppress {
    deviate not-supported;
  }

  deviation /oc-if:interfaces/oc-if:interface/oc-tun:tunnel/oc-tun:ipv6/oc-tun:neighbors/oc-tun:neighbor {
    deviate not-supported;
  }

  deviation /oc-if:interfaces/oc-if:interface/oc-tun:tunnel/oc-tun:ipv6/oc-tun:unnumbered/oc-tun:config/oc-tun:enabled {
    deviate not-supported;
  }

  deviation /oc-if:interfaces/oc-if:interface/oc-tun:tunnel/oc-tun:ipv6/oc-tun:unnumbered/oc-tun:state/oc-tun:enabled {
    deviate not-supported;
  }

  deviation /oc-if:interfaces/oc-if:interface/oc-tun:tunnel/oc-tun:ipv6/oc-tun:unnumbered/oc-tun:interface-ref/oc-tun:config/oc-tun:interface {
    deviate not-supported;
  }

  deviation /oc-if:interfaces/oc-if:interface/oc-tun:tunnel/oc-tun:ipv6/oc-tun:unnumbered/oc-tun:interface-ref/oc-tun:config/oc-tun:subinterface {
    deviate not-supported;
  }

  deviation /oc-if:interfaces/oc-if:interface/oc-tun:tunnel/oc-tun:ipv6/oc-tun:unnumbered/oc-tun:interface-ref/oc-tun:state/oc-tun:interface {
    deviate not-supported;
  }

  deviation /oc-if:interfaces/oc-if:interface/oc-tun:tunnel/oc-tun:ipv6/oc-tun:unnumbered/oc-tun:interface-ref/oc-tun:state/oc-tun:subinterface {
    deviate not-supported;
  }

  deviation /oc-if:interfaces/oc-if:interface/oc-tun:tunnel/oc-tun:ipv6/oc-tun:config/oc-tun:dup-addr-detect-transmits {
    deviate not-supported;
  }

  deviation /oc-if:interfaces/oc-if:interface/oc-tun:tunnel/oc-tun:ipv6/oc-tun:config/oc-tun:dhcp-client {
    deviate not-supported;
  }

  deviation /oc-if:interfaces/oc-if:interface/oc-tun:tunnel/oc-tun:ipv6/oc-tun:state/oc-tun:dup-addr-detect-transmits {
    deviate not-supported;
  }

  deviation /oc-if:interfaces/oc-if:interface/oc-tun:tunnel/oc-tun:ipv6/oc-tun:state/oc-tun:dhcp-client {
    deviate not-supported;
  }

  deviation /oc-if:interfaces/oc-if:interface/oc-tun:tunnel/oc-tun:ipv6/oc-tun:state/oc-tun:counters/oc-tun:in-pkts {
    deviate not-supported;
  }

  deviation /oc-if:interfaces/oc-if:interface/oc-tun:tunnel/oc-tun:ipv6/oc-tun:state/oc-tun:counters/oc-tun:in-octets {
    deviate not-supported;
  }

  deviation /oc-if:interfaces/oc-if:interface/oc-tun:tunnel/oc-tun:ipv6/oc-tun:state/oc-tun:counters/oc-tun:in-forwarded-pkts {
    deviate not-supported;
  }

  deviation /oc-if:interfaces/oc-if:interface/oc-tun:tunnel/oc-tun:ipv6/oc-tun:state/oc-tun:counters/oc-tun:in-forwarded-octets {
    deviate not-supported;
  }

  deviation /oc-if:interfaces/oc-if:interface/oc-tun:tunnel/oc-tun:ipv6/oc-tun:state/oc-tun:counters/oc-tun:in-discarded-pkts {
    deviate not-supported;
  }

  deviation /oc-if:interfaces/oc-if:interface/oc-tun:tunnel/oc-tun:ipv6/oc-tun:state/oc-tun:counters/oc-tun:out-pkts {
    deviate not-supported;
  }

  deviation /oc-if:interfaces/oc-if:interface/oc-tun:tunnel/oc-tun:ipv6/oc-tun:state/oc-tun:counters/oc-tun:out-octets {
    deviate not-supported;
  }

  deviation /oc-if:interfaces/oc-if:interface/oc-tun:tunnel/oc-tun:ipv6/oc-tun:state/oc-tun:counters/oc-tun:out-error-pkts {
    deviate not-supported;
  }

  deviation /oc-if:interfaces/oc-if:interface/oc-tun:tunnel/oc-tun:ipv6/oc-tun:state/oc-tun:counters/oc-tun:out-forwarded-pkts {
    deviate not-supported;
  }

  deviation /oc-if:interfaces/oc-if:interface/oc-tun:tunnel/oc-tun:ipv6/oc-tun:state/oc-tun:counters/oc-tun:out-forwarded-octets {
    deviate not-supported;
  }

  deviation /oc-if:interfaces/oc-if:interface/oc-tun:tunnel/oc-tun:ipv6/oc-tun:state/oc-tun:counters/oc-tun:out-discarded-pkts {
    deviate not-supported;
  }

  deviation /oc-if:interfaces/oc-if:interface/oc-tun:tunnel/oc-tun:ipv6/oc-tun:state/oc-tun:counters/oc-tun:in-error-pkts {
    deviate not-supported;
  }

  deviation /oc-if:interfaces/oc-if:interface/oc-tun:tunnel/oc-tun:ipv6/oc-tun:addresses/oc-tun:address/oc-tun:state/oc-tun:status {
    deviate not-supported;
  }

  deviation /oc-if:interfaces/oc-if:interface/oc-tun:tunnel/oc-tun:ipv6/oc-tun:config/oc-tun:enabled {
    deviate not-supported;
  }

  deviation /oc-if:interfaces/oc-if:interface/oc-tun:tunnel/oc-tun:ipv6/oc-tun:state/oc-tun:enabled {
    deviate not-supported;
  }

  deviation /oc-if:interfaces/oc-if:interface/oc-tun:tunnel/oc-tun:ipv6/oc-tun:state/oc-tun:mtu {
    deviate not-supported;
  }


}
//total deviations:57
