module Cisco-IOS-XR-sandbox-cfg {
  namespace "http://cisco.com/ns/yang/Cisco-IOS-XR-sandbox-cfg";
  prefix sandbox-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR sandbox package configuration.
     
     This module contains definitions
     for the following management objects:
       sandbox: System Health Check operational data space
     
     Copyright (c) 2013-2022 by Cisco Systems, Inc.
     All rights reserved.";

  revision 2022-07-08 {
    description
      "sandbox configuration added";
    semver:module-version "1.0.0";
  }
  revision 2019-04-05 {
    description
      "Establish semantic version baseline.";
  }
  revision 2015-11-09 {
    description
      "IOS XR 6.0 revision.";
  }

  container sandbox {
    description
      "System Health Check operational data space";
    container ordz {
      description
        "SandBoxMgr config";
      leaf enable {
        type empty;
        description
          "Enable or disable container";
      }
    }
  }
}
