module Cisco-IOS-XR-ip-daps-mib-cfg {
  namespace "http://cisco.com/ns/yang/Cisco-IOS-XR-ip-daps-mib-cfg";
  prefix ip-daps-mib-cfg;

  import Cisco-IOS-XR-snmp-agent-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ip-daps-mib package configuration.
     
     This YANG module augments the
       Cisco-IOS-XR-snmp-agent-cfg
     module with configuration data.
     
     Copyright (c) 2013-2017 by Cisco Systems, Inc.
     All rights reserved.";

  revision 2015-11-09 {
    description
      "IOS XR 6.0 revision.";
  }

  augment "/a1:snmp/a1:notification" {
    description
      "This augment extends the configuration data of
       'Cisco-IOS-XR-snmp-agent-cfg'";
    container addresspool-mib {
      description
        "Enable SNMP daps traps";
      leaf high {
        type boolean;
        description
          "Enable SNMP Address Pool High Threshold trap";
      }
      leaf low {
        type boolean;
        description
          "Enable SNMP Address Pool Low Threshold trap";
      }
    }
  }
}
