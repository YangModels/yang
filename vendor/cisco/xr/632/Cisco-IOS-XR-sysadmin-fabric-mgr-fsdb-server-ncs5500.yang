module Cisco-IOS-XR-sysadmin-fabric-mgr-fsdb-server-ncs5500 {
  namespace "http://www.cisco.com/ns/yang/Cisco-IOS-XR-sysadmin-fabric-mgr-fsdb-server";
  prefix fabric_fsdb;

  import tailf-common {
    prefix tailf;
  }
  import Cisco-IOS-XR-sysadmin-fabric-types {
    prefix fabric-types;
  }
  import Cisco-IOS-XR-sysadmin-show-trace {
    prefix show-trace;
  }

  revision 2017-05-01 {
    description
      "Namespace change to comply with Cisco guidelines on namespace";
  }

  grouping link_port_show {
    list data_idx {
      key "port_data_idx";
      max-elements "1024";
      tailf:cli-show-template
        "$(.legend_shown != true ?
         Description\\\\:
         Ch - Channel,    Sx - Slice/bus #,    Px - Port # within slice/bus
         DN - Down,       LI - Lane into CDR,  LO - Lane out of CDR
         
         $(.path ~= fia ?Fia Port       Admin  Near-end     Other End
         R/S/A/P        /Oper    CDR        R/S/A/P  
         $(.path ~= rx ?               state  LO-Sx-Px-LI           :               state  LI-Sx-Px-LO           )
         ------------------------------------------------------:SFE port       Admin  Near-end     Near    Far     Far-end      Other End
         R/S/A/P        /Oper    CDR        -end    -end      CDR        R/S/A/P  
         $(.path ~= rx ?               state  LO-Sx-Px-LI  PHY/Ln  PHY/Ln  LO-Sx-Px-LI           :               state  LI-Sx-Px-LO  PHY/Ln  PHY/Ln  LI-Sx-Px-LO           )
         ------------------------------------------------------------------------------)
         )$(sfe_port|ljust:14) $(admin-state|rjust:2)/$(oper_state|ljust:2)  $(near_end_cdr_ln|ljust:11)  $(.path ~= fia ?:$(near_end_cxp_ch|ljust:6)  $(far_end_cxp_ch|ljust:6)  $(far_end_cdr_ln|ljust:11)  )$(neighbor_link|ljust:14)$(.path ~= detail ?
         +-----------------------------------------------------------------------+
         | Timestamp                            Event\\\\(s\\\\)                         |
         +-----------------------------------------------------------------------+$(history|show)
         )
        ";
      tailf:cli-show-template-enter "";
      tailf:cli-suppress-table;
      tailf:cli-show-template-legend
        "
         Description\\\\:
         Ch - Channel,    Sx - Slice/bus #,    Px - Port # within slice/bus
         DN - Down,       LI - Lane into CDR,  LO - Lane out of CDR
         
         $(.path ~= fia ?Fia Port       Admin  Near-end     Other End
         R/S/A/P        /Oper    CDR        R/S/A/P  
         $(.path ~= rx ?               state  LO-Sx-Px-LI           :               state  LI-Sx-Px-LO           )
         ------------------------------------------------------:SFE port       Admin  Near-end     Near    Far     Far-end      Other End
         R/S/A/P        /Oper    CDR        -end    -end      CDR        R/S/A/P  
         $(.path ~= rx ?               state  LO-Sx-Px-LI  PHY/Ln  PHY/Ln  LO-Sx-Px-LI           :               state  LI-Sx-Px-LO  PHY/Ln  PHY/Ln  LI-Sx-Px-LO           )
         ------------------------------------------------------------------------------)
        ";
      leaf port_data_idx {
        type int64;
      }
      leaf sfe_port {
        type string;
        tailf:hidden "internal";
      }
      leaf admin-state {
        type string;
        tailf:hidden "internal";
      }
      leaf oper_state {
        type string;
        tailf:hidden "internal";
      }
      leaf near_end_cdr_ln {
        type string;
        tailf:hidden "internal";
      }
      leaf near_end_cxp_ch {
        type string;
        tailf:hidden "internal";
      }
      leaf far_end_cxp_ch {
        type string;
        tailf:hidden "internal";
      }
      leaf far_end_cdr_ln {
        type string;
        tailf:hidden "internal";
      }
      leaf neighbor_link {
        type string;
        tailf:hidden "internal";
      }
      list history {
        key "history_idx";
        tailf:cli-show-template
          "
           $(time_stamp|ljust:30) $(admin-state|ljust:10) $(oper_state|ljust:10) $(error_state)";
        tailf:cli-suppress-table;
        tailf:cli-show-template-enter "";
        leaf history_idx {
          type int32;
        }
        leaf time_stamp {
          type string;
          tailf:hidden "internal";
        }
        leaf admin-state {
          type string;
          tailf:hidden "internal";
        }
        leaf oper_state {
          type string;
          tailf:hidden "internal";
        }
        leaf error_state {
          type string;
          tailf:hidden "internal";
        }
      }
    }
  }

  grouping link_port_stats_show {
    list data_idx {
      key "port_data_idx";
      max-elements "1024";
      tailf:cli-suppress-table;
      tailf:cli-show-template-enter "";
      tailf:cli-show-template-legend
        "$(.path ~= brief ? 
         SFE Port             In Data      Out Data        CE       UCE      CRC
         R/S/A/P                Cells         Cells     Cells     Cells    Errors
         ------------------------------------------------------------------------
         )";
      tailf:cli-show-template
        "$(.legend_shown != true ?$(.path ~= brief ? 
         SFE Port             In Data      Out Data        CE       UCE       CRC
         R/S/A/P                Cells         Cells     Cells     Cells    Errors
         ------------------------------------------------------------------------
         ))$(.path ~= brief ?$(sfe_port|ljust:14) $(RX_Data_cell_counter|rjust:13) $(TX_Data_cell_counter|rjust:13) $(RX_LFEC_FEC_correctable_error|rjust:9) $(RX_LFEC_FEC_uncorrectable_errors|rjust:9) $(RX_CRC_errors_counter|rjust:9):The fabric link port\\\\: $(sfe_port)
           Total TX control cells           \\\\: $(TX_Control_cells_counter)
           Total TX data cells              \\\\: $(TX_Data_cell_counter)
           Total TX data bytes              \\\\: $(TX_Data_byte_counter)
           Total RX CRC errors              \\\\: $(RX_CRC_errors_counter)
           Total RX correctable errror      \\\\: $(RX_LFEC_FEC_correctable_error)
           Total RX 8b_10b disparity errror \\\\: $(RX_8b_10b_disparity_errors)
           Total RX control cells           \\\\: $(RX_Control_cells_counter)
           Total RX data cells              \\\\: $(RX_Data_cell_counter)
           Total RX data bytes              \\\\: $(RX_Data_byte_counter)
           Total RX dropped re-xmit control \\\\: $(RX_dropped_retransmitted_control)
           Total TX Asyn fifo rate          \\\\: $(TX_Asyn_fifo_rate)
           Total RX Asyn fifo rate          \\\\: $(RX_Asyn_fifo_rate)
           Total RX uncorrectable errror    \\\\: $(RX_LFEC_FEC_uncorrectable_errors)
           Total RX 8b_10b code error       \\\\: $(RX_8b_10b_code_errors)
         $(is_link_error != false ?
         
         Link $(sfe_port) has errors\\\\:
         CRC Error              \\\\: $(link_crc_error)
         Size Error             \\\\: $(link_size_error)
         Miss_align Error       \\\\: $(link_mis_align_error)
         Code_group Error       \\\\: $(link_code_group_error)
         No_sig_lock Error      \\\\: $(link_no_sig_lock_error)
         No_sig_accept Error    \\\\: $(link_no_sig_accept_error)
         Tokens Error           \\\\: $(link_tokens_error)
         Error token count      \\\\: $(error_token_count)
         ))
        ";
      leaf port_data_idx {
        type int64;
      }
      leaf rack_num {
        type string;
        tailf:hidden "internal";
      }
      leaf sfe_port {
        type string;
        tailf:hidden "internal";
      }
      leaf TX_Control_cells_counter {
        type uint64;
        tailf:hidden "internal";
      }
      leaf TX_Data_cell_counter {
        type uint64;
        tailf:hidden "internal";
      }
      leaf TX_Data_byte_counter {
        type uint64;
        tailf:hidden "internal";
      }
      leaf RX_CRC_errors_counter {
        type uint64;
        tailf:hidden "internal";
      }
      leaf RX_LFEC_FEC_correctable_error {
        type uint64;
        tailf:hidden "internal";
      }
      leaf RX_8b_10b_disparity_errors {
        type uint64;
        tailf:hidden "internal";
      }
      leaf RX_Control_cells_counter {
        type uint64;
        tailf:hidden "internal";
      }
      leaf RX_Data_cell_counter {
        type uint64;
        tailf:hidden "internal";
      }
      leaf RX_Data_byte_counter {
        type uint64;
        tailf:hidden "internal";
      }
      leaf RX_dropped_retransmitted_control {
        type uint64;
        tailf:hidden "internal";
      }
      leaf TX_Asyn_fifo_rate {
        type uint64;
        tailf:hidden "internal";
      }
      leaf RX_Asyn_fifo_rate {
        type uint64;
        tailf:hidden "internal";
      }
      leaf RX_LFEC_FEC_uncorrectable_errors {
        type uint64;
        tailf:hidden "internal";
      }
      leaf RX_8b_10b_code_errors {
        type uint64;
        tailf:hidden "internal";
      }
      leaf is_link_error {
        type boolean;
        default "false";
        tailf:hidden "internal";
      }
      leaf link_crc_error {
        type uint32;
        tailf:hidden "internal";
      }
      leaf link_size_error {
        type uint32;
        tailf:hidden "internal";
      }
      leaf link_mis_align_error {
        type uint32;
        tailf:hidden "internal";
      }
      leaf link_code_group_error {
        type uint32;
        tailf:hidden "internal";
      }
      leaf link_no_sig_lock_error {
        type uint32;
        tailf:hidden "internal";
      }
      leaf link_no_sig_accept_error {
        type uint32;
        tailf:hidden "internal";
      }
      leaf link_tokens_error {
        type uint32;
        tailf:hidden "internal";
      }
      leaf error_token_count {
        type uint32;
        tailf:hidden "internal";
      }
    }
  }

  grouping fabric_link_port_show_with_option {
    uses link_port_show;
    container brief {
      tailf:info "brief information";
      uses link_port_show;
    }
    container detail {
      tailf:info "detail information";
      uses link_port_show;
    }
  }

  grouping fabric_link_port_states {
    container state {
      tailf:info "State of the link";
      tailf:cli-incomplete-show-path;
      container up {
        tailf:info "link oper state up";
        uses fabric_link_port_show_with_option;
      }
      container down {
        tailf:info "link oper state down";
        uses fabric_link_port_show_with_option;
      }
      container mismatch {
        tailf:info "link oper/admin state mismatch";
        uses fabric_link_port_show_with_option;
      }
    }
  }

  grouping asic_status_show {
    list asic_list {
      key "asic_idx";
      tailf:cli-suppress-table;
      tailf:cli-show-template-enter "";
      tailf:cli-show-template-legend
        "
            Sfe         Admin    Oper
           R/S/A        State    State
         -----------------------------
        ";
      tailf:cli-show-template
        "$(asic_loc_str|ljust:14) $(admin-state|ljust:8) $(oper_state|ljust:7)$(.path ~= detail ?
         +-----------------------------------------------------------------------+
         | Timestamp                            Event\\\\(s\\\\)                         |
         +-----------------------------------------------------------------------+$(history|show)
         )
        ";
      leaf asic_idx {
        type int64;
      }
      leaf asic_loc_str {
        type string;
        tailf:hidden "internal";
      }
      leaf admin-state {
        type string;
        tailf:hidden "internal";
      }
      leaf oper_state {
        type string;
        tailf:hidden "internal";
      }
      leaf down_flags {
        type string;
        tailf:hidden "internal";
      }
      leaf fab_group {
        type string;
        tailf:hidden "internal";
      }
      list history {
        key "history_idx";
        tailf:cli-show-template
          "
           $(time_stamp|ljust:30) $(admin-state|ljust:10) $(oper_state|ljust:10) $(error_state)";
        tailf:cli-suppress-table;
        tailf:cli-show-template-enter "";
        leaf history_idx {
          type int32;
        }
        leaf time_stamp {
          type string;
          tailf:hidden "internal";
        }
        leaf admin-state {
          type string;
          tailf:hidden "internal";
        }
        leaf oper_state {
          type string;
          tailf:hidden "internal";
        }
        leaf error_state {
          type string;
          tailf:hidden "internal";
        }
      }
    }
  }

  grouping fsdb_svr_trace {
    container fsdb_srvr {
      description
        "FSDB Server information";
      tailf:hidden "internal-command";
      tailf:info "FSDB Server information";
      tailf:cli-incomplete-show-path;
      container fsdb_server {
        tailf:cli-incomplete-show-path;
        tailf:cli-drop-node-name;
        uses show-trace:traceable;
      }
    }
  }

  grouping fsdb_pla_reachability_show {
    list planes {
      key "plane_idx";
      tailf:cli-show-template-enter "";
      tailf:cli-suppress-table;
      tailf:cli-show-template
        "$(show_fabid == true ?Fab id\\\\: $(fabid_name)
         ========================
         )plane id\\\\:$(plane_num), Stage\\\\: $(asic_stage)
         ---------------------------------------------------------------------------
         Asic     mask type                mask                                Links
         ---------------------------------------------------------------------------
         $(cards|show)
        ";
      leaf plane_idx {
        type int32;
      }
      leaf plane_num {
        type int32;
        tailf:hidden "internal";
      }
      leaf fabid_name {
        type string;
        tailf:hidden "internal";
      }
      leaf show_fabid {
        type boolean;
        tailf:hidden "internal";
      }
      leaf asic_stage {
        type string;
        tailf:hidden "internal";
      }
      list cards {
        key "card_idx";
        tailf:cli-show-template-enter "";
        tailf:cli-suppress-table;
        tailf:cli-show-template "$(asics|show)";
        leaf card_idx {
          type int32;
        }
        list asics {
          key "asic_idx";
          tailf:cli-show-template-enter "";
          tailf:cli-suppress-table;
          tailf:cli-show-template "$(asic_idx|ljust:8) Reachability  \\\\: 0x$(reachability_mask|ljust:40) $(total_links|rjust:6)\n";
          leaf asic_idx {
            type int32;
          }
          leaf asic_RSA {
            type string;
            tailf:hidden "internal";
          }
          leaf reachability_mask {
            type string;
            tailf:hidden "internal";
          }
          leaf linkup_mask {
            type string;
            tailf:hidden "internal";
          }
          leaf all_reach_mask {
            type string;
            tailf:hidden "internal";
          }
          leaf total_links {
            type int32;
            tailf:hidden "internal";
          }
          leaf total_up_links {
            type int32;
            tailf:hidden "internal";
          }
          leaf total_all_reach_links {
            type int32;
            tailf:hidden "internal";
          }
          leaf asic_stage_name {
            type fabric-types:sfe_stage_type;
          }
        }
      }
    }
  }

  grouping fabric_link_state_and_statistics_show_w_loc {
    uses fabric_link_port_show_with_option;
    uses fabric_link_port_states;
    container statistics {
      tailf:display-when "../../../portname != 'fia'";
      tailf:info "link statistics";
      uses link_port_stats_show;
      container brief {
        tailf:info "brief statistics";
        uses link_port_stats_show;
      }
      container detail {
        tailf:info "detail statistics";
        uses link_port_stats_show;
      }
    }
  }

  grouping fabric_link_state_and_statistics_show {
    uses fabric_link_port_show_with_option;
    uses fabric_link_port_states;
    container statistics {
      tailf:display-when "../../portname != 'fia'";
      tailf:info "link statistics";
      uses link_port_stats_show;
      container brief {
        tailf:info "brief statistics";
        uses link_port_stats_show;
      }
      container detail {
        tailf:info "detail statistics";
        uses link_port_stats_show;
      }
    }
  }

  grouping fabric_link_port_state_and_stats {
    list port {
      key "portname";
      tailf:cli-no-key-completion;
      tailf:cli-no-match-completion;
      tailf:info "Fabric Link port";
      tailf:cli-show-template-enter "";
      tailf:cli-suppress-table;
      leaf portname {
        type fabric-types:link_port_type;
      }
      leaf description {
        type string;
        default "port.";
      }
      list location {
        key "loc_str";
        tailf:cli-no-key-completion;
        tailf:cli-no-match-completion;
        tailf:cli-show-template-enter "";
        tailf:cli-suppress-table;
        tailf:info "Link port location";
        leaf loc_str {
          type fabric-types:link_port_location_type;
        }
        container rx {
          description
            "Rx link option";
          tailf:info "Rx link option";
          uses fabric_link_state_and_statistics_show_w_loc;
        }
        container tx {
          description
            "Tx link option";
          tailf:info "Tx link option";
          uses fabric_link_state_and_statistics_show_w_loc;
        }
      }
      container rx {
        description
          "Rx link option";
        tailf:info "Rx link option";
        uses fabric_link_state_and_statistics_show;
      }
      container tx {
        description
          "Tx link option";
        tailf:info "Tx link option";
        uses fabric_link_state_and_statistics_show;
      }
    }
  }

  grouping fsdb_svr {
    container link {
      description
        "Fabric link option";
      tailf:hidden "internal-command";
      tailf:cli-incomplete-show-path;
      tailf:info "Fabric link option";
      list rack {
        key "rack_number";
        tailf:callpoint "fabric_fsdb_link";
        tailf:cli-show-template-enter "";
        tailf:cli-suppress-table;
        leaf rack_number {
          type int32;
        }
        uses fabric_link_port_state_and_stats;
      }
      list node_location {
        key "node_str";
        tailf:callpoint "fabric_sfe_link_port_stats_cp";
        tailf:cli-show-template-enter "";
        tailf:cli-suppress-table;
        leaf node_str {
          type string;
        }
        uses fabric_link_port_state_and_stats;
      }
    }
    container sfe {
      description
        "Switch Fabric Element option";
      tailf:hidden "internal-command";
      tailf:callpoint "fabric_fsdb_sfe";
      tailf:cli-incomplete-show-path;
      tailf:info "Switch Fabric Element option";
      list rack {
        key "rack_number";
        tailf:cli-show-template-enter "";
        tailf:cli-suppress-table;
        leaf rack_number {
          type int32;
        }
        list asic_stages {
          key "asic_stage_name";
          tailf:cli-no-key-completion;
          tailf:cli-no-match-completion;
          tailf:cli-incomplete-show-path;
          tailf:cli-drop-node-name;
          tailf:cli-show-template-enter "";
          tailf:cli-suppress-table;
          leaf asic_stage_name {
            type fabric-types:asic_stage_type;
          }
          list location {
            key "loc_str";
            tailf:cli-no-key-completion;
            tailf:cli-no-match-completion;
            tailf:cli-incomplete-show-path;
            tailf:cli-show-template-enter "";
            tailf:cli-suppress-table;
            leaf loc_str {
              type fabric-types:asic_location_type;
            }
            uses asic_status_show;
            container brief {
              tailf:info "Brief information";
              uses asic_status_show;
            }
            container detail {
              tailf:info "Detail information";
              uses asic_status_show;
            }
          }
          uses asic_status_show;
          container brief {
            tailf:info "Brief information";
            uses asic_status_show;
          }
          container detail {
            tailf:info "Detail information";
            uses asic_status_show;
          }
        }
      }
    }
    container fsdb_pla {
      description
        "plane availability status option";
      tailf:hidden "internal-command";
      tailf:callpoint "fabric_fsdb_pla";
      tailf:cli-incomplete-show-path;
      tailf:info "plane availability status option";
      list rack {
        key "rack_number";
        description
          "Rack";
        tailf:info "Rack";
        tailf:cli-show-template-enter "";
        tailf:cli-suppress-table;
        leaf rack_number {
          type int32;
        }
        list asic_stages {
          key "asic_stage_idx";
          tailf:cli-drop-node-name;
          tailf:cli-show-template-enter "";
          tailf:cli-suppress-table;
          tailf:cli-show-template-legend
            "Description: 
                planes       \\\\: p0-p(3|5)
                plane mask   : Asic # 0-5
                Asic value  1: destination reachable via asic
                            .: destination unreachable via asic
            ";
          tailf:cli-show-template
            "$(.legend_shown != true ?Description\\\\: 
             $(plane_number == 4 ?   planes       \\\\: p0-p3
             )$(plane_number == 6 ?   planes       \\\\: p0-p5
             )   plane mask   \\\\: Asic # 0-5
                Asic value  1\\\\: destination reachable via asic
                            .\\\\: destination unreachable via asic
             )Rack\\\\: $(rack_number), Stage\\\\: $(asic_stage_name)
             =============================
             $(plane_number == 6 ?Destination     p0     p1     p2     p3     p4     p5     Reach-mask Oper Up
             Address         mask   mask   mask   mask   mask   mask   links/asic links/asic
             Fabid(R/S/A\\\\)    012345 012345 012345 012345 012345 012345 Mn/x Total Mn/x Total
             --------------------------------------------------------------------------------
             $(fabids|show)$(down_fabids|show)
             )$(plane_number == 4 ?Destination   p0     p1     p2     p3     Reach-mask   Oper Up
             Address       mask   mask   mask   mask   links/asic   links/asic
             Fabid(R/S/A\\\\)  012345 012345 012345 012345 Mn/Mx Total  Mn/Mx  Total
             -------------------------------------------------------------------
             $(fabids|show)$(down_fabids|show)
             )";
          leaf asic_stage_idx {
            type fabric-types:sfe_stage_type;
          }
          leaf asic_stage_name {
            type fabric-types:sfe_stage_type;
            tailf:hidden "internal";
          }
          leaf rack_number {
            type string;
            tailf:hidden "internal";
          }
          leaf plane_number {
            type int32;
            tailf:hidden "internal";
          }
          list fabids {
            key "idx";
            tailf:cli-drop-node-name;
            tailf:cli-suppress-table;
            tailf:cli-show-template-enter "";
            tailf:cli-show-template "$(fabid_address|ljust:16)$(plane_num == 4 ?$(plane_0_mask|ljust:6) $(plane_1_mask|ljust:6) $(plane_2_mask|ljust:6) $(plane_3_mask|ljust:6) )$(plane_num == 6 ?$(plane_0_mask|ljust:6) $(plane_1_mask|ljust:6) $(plane_2_mask|ljust:6) $(plane_3_mask|ljust:6) $(plane_4_mask|ljust:6) $(plane_5_mask|ljust:6) )$(min_links_per_asic|rjust:2)/$(max_links_per_asic|ljust:2) $(total_links|rjust:3) $(min_up_links_per_asic|rjust:3)/$(max_up_links_per_asic|ljust:3) $(total_up_links|rjust:4) \n";
            leaf idx {
              type int32;
              tailf:cli-drop-node-name;
            }
            leaf fabid_address {
              type string;
              tailf:hidden "internal";
            }
            leaf plane_num {
              type int32;
              tailf:hidden "internal";
            }
            leaf plane_0_mask {
              type string;
              tailf:hidden "internal";
            }
            leaf plane_1_mask {
              type string;
              tailf:hidden "internal";
            }
            leaf plane_2_mask {
              type string;
              tailf:hidden "internal";
            }
            leaf plane_3_mask {
              type string;
              tailf:hidden "internal";
            }
            leaf plane_4_mask {
              type string;
              tailf:hidden "internal";
            }
            leaf plane_5_mask {
              type string;
              tailf:hidden "internal";
            }
            leaf min_links_per_asic {
              type int32;
              tailf:hidden "internal";
            }
            leaf max_links_per_asic {
              type int32;
              tailf:hidden "internal";
            }
            leaf total_links {
              type int32;
              tailf:hidden "internal";
            }
            leaf min_up_links_per_asic {
              type int32;
              tailf:hidden "internal";
            }
            leaf max_up_links_per_asic {
              type int32;
              tailf:hidden "internal";
            }
            leaf total_up_links {
              type int32;
              tailf:hidden "internal";
            }
          }
          list down_fabids {
            key "idx";
            tailf:cli-drop-node-name;
            tailf:cli-suppress-table;
            tailf:cli-show-template-enter "";
            tailf:cli-show-template "$(fabid_address|ljust:16)$(fabid_status|ljust)\n";
            leaf idx {
              type int32;
              tailf:cli-drop-node-name;
            }
            leaf fabid_address {
              type string;
              tailf:hidden "internal";
            }
            leaf fabid_status {
              type string;
              tailf:hidden "internal";
            }
          }
          list destination {
            key "amba_id";
            tailf:cli-show-template-enter "";
            tailf:cli-suppress-table;
            tailf:cli-no-key-completion;
            tailf:cli-no-match-completion;
            leaf amba_id {
              type fabric-types:fabric_fabid_type;
            }
            uses fsdb_pla_reachability_show;
          }
        }
      }
    }
    uses fsdb_svr_trace;
  }
  tailf:id "http://www.cisco.com/panini/calvados/fabric/fsdb";
}
