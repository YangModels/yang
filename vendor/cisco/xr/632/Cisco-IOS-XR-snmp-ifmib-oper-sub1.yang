submodule Cisco-IOS-XR-snmp-ifmib-oper-sub1 {
  belongs-to Cisco-IOS-XR-snmp-ifmib-oper {
    prefix Cisco-IOS-XR-snmp-ifmib-oper;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR snmp-ifmib package operational data.
     
     Copyright (c) 2013-2017 by Cisco Systems, Inc.
     All rights reserved.";

  revision 2015-01-07 {
    description
      "IOS XR 5.3.1 revision.";
  }

  typedef Link-up-down-status {
    type enumeration {
      enum "enabled" {
        value 1;
        description
          "LinkUpDown notification is enabled";
      }
      enum "disabled" {
        value 2;
        description
          "LinkUpDown notification is disabled";
      }
    }
    description
      "Link up down status";
  }

  grouping IFMIB-IFSTACKSTATUS-ENTRY {
    description
      "IF-MIB ifStackStatus entry";
    leaf if-stack-higher-layer {
      type string;
      description
        "Higher Layer Index";
    }
    leaf if-stack-lower-layer {
      type string;
      description
        "Lowyer Layer Index";
    }
    leaf if-stack-status {
      type string;
      description
        "Interface ifStackStaus info";
    }
  }

  grouping IFMIB-NOTIF-STATUS-ENTRY {
    description
      "IF-MIB ifname ifindex entry";
    leaf link-up-down-notif-status {
      type Link-up-down-status;
      description
        "LinkUpDown notification status";
    }
  }

  grouping IFMIB-IFALIAS-ENTRY {
    description
      "IF-MIB ifalias entry";
    leaf if-alias {
      type string;
      description
        "Interface ifAlias";
    }
  }

  grouping IFMIB-IFCONNECTORPRESENT-ENTRY {
    description
      "IF-MIB ifConnectorPresent entry";
    leaf if-connector-present {
      type string;
      description
        "Interface ifConnector";
    }
  }

  grouping IFMIB-IFNAME-IFINDEX-ENTRY {
    description
      "IF-MIB ifname ifindex entry";
    leaf if-index {
      type uint32;
      description
        "Interface Index";
    }
  }
}
