submodule openconfig-mpls-static {
  yang-version 1;
  belongs-to openconfig-mpls {
    prefix mpls;
  }

  import openconfig-mpls-types {
    prefix mplst;
  }
  import ietf-inet-types {
    prefix inet;
  }
  import openconfig-extensions {
    prefix oc-ext;
  }

  organization
    "OpenConfig working group";
  contact
    "OpenConfig working group
     netopenconfig@googlegroups.com";
  description
    "Defines static LSP configuration";

  revision 2015-11-05 {
    description
      "Initial public release of MPLS models";
    reference "0.2.1";
  }
  revision 2015-10-14 {
    description
      "Work in progress";
    reference "0.2.0";
  }

  grouping static-lsp-common {
    description
      "common definitions for static LSPs";
    leaf next-hop {
      type inet:ip-address;
      description
        "next hop IP address for the LSP";
    }
    leaf incoming-label {
      type mplst:mpls-label;
      description
        "label value on the incoming packet";
    }
    leaf push-label {
      type mplst:mpls-label;
      description
        "label value to push at the current hop for the
         LSP";
    }
  }

  grouping static-lsp-main {
    description
      "grouping for top level list of static LSPs";
    list label-switched-path {
      key "name";
      description
        "list of defined static LSPs";
      leaf name {
        type string;
        description
          "name to identify the LSP";
      }
      container ingress {
        description
          "Static LSPs for which the router is an
           ingress node";
        uses static-lsp-common;
      }
      container transit {
        description
          "static LSPs for which the router is a
           transit node";
        uses static-lsp-common;
      }
      container egress {
        description
          "static LSPs for which the router is a
           egress  node";
        uses static-lsp-common;
      }
    }
  }
  oc-ext:openconfig-version "0.2.1";
}
