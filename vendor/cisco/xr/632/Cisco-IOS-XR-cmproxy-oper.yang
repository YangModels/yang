module Cisco-IOS-XR-cmproxy-oper {
  namespace "http://cisco.com/ns/yang/Cisco-IOS-XR-cmproxy-oper";
  prefix cmproxy-oper;

  import Cisco-IOS-XR-types {
    prefix xr;
  }
  include Cisco-IOS-XR-cmproxy-oper-sub1 {
    revision-date 2015-11-09;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR cmproxy package operational data.
     
     This module contains definitions
     for the following management objects:
       sdr-inventory-vm: Platform VM information
     
     Copyright (c) 2013-2017 by Cisco Systems, Inc.
     All rights reserved.";

  revision 2015-11-09 {
    description
      "IOS XR 6.0 revision.";
  }

  container sdr-inventory-vm {
    config false;
    description
      "Platform VM information";
    container nodes {
      description
        "Node directory";
      list node {
        key "name";
        description
          "Node name";
        container node-entries {
          description
            "VM Information";
          list node-entry {
            key "name";
            description
              "VM information for a node";
            leaf name {
              type xr:Cisco-ios-xr-string;
              description
                "Node name";
            }
            uses CMP-INV-ST;
          }
        }
        leaf name {
          type xr:Cisco-ios-xr-string;
          description
            "Node name";
        }
      }
    }
  }
}
