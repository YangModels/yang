module Cisco-IOS-XR-sysadmin-clear-ncs5500 {
  namespace "http://www.cisco.com/ns/yang/Cisco-IOS-XR-sysadmin-clear";
  prefix calvados_clear;

  import tailf-common {
    prefix tailf;
  }
  import Cisco-IOS-XR-sysadmin-ethsw-esdma-cli-ncs5500 {
    prefix esdma;
  }
  import Cisco-IOS-XR-sysadmin-asic-errors-ael {
    prefix aelclear;
  }
  import Cisco-IOS-XR-sysadmin-fabric-ncs5500 {
    prefix fabric;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains a collection of YANG
     definitions for Cisco IOS-XR SysAdmin configuration.
     
     This module defines the top level container for
     all 'clear' commands for Sysadmin.
     
     Copyright(c) 2015-2017 by Cisco Systems, Inc.
     All rights reserved.";

  revision 2017-01-31 {
    description
      "Changed the namespace and module name";
  }
  revision 2015-03-20 {
    description
      "Created initial 'clear' implementation for Fretta";
  }

  grouping asic_clear {
    tailf:action "statistics" {
      tailf:actionpoint "switch-clear-stats";
    }
  }
  tailf:id "http://cisco.com/panini/calvados/calvados_clear";

  container clear {
    tailf:info "Commands to clear";
    tailf:cli-suppress-show-path;
    container controller {
      tailf:info "Commands to clear controller statistics";
      container switch {
        tailf:info "Clear control plane Ethernet switch statistics";
        uses esdma:switch_clear;
      }
      uses fabric:fabric_clear;
    }
    uses aelclear:ael-clear-asic-errors-grp;
  }
}
