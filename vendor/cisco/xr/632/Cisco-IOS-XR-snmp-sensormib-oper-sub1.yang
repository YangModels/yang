submodule Cisco-IOS-XR-snmp-sensormib-oper-sub1 {
  belongs-to Cisco-IOS-XR-snmp-sensormib-oper {
    prefix Cisco-IOS-XR-snmp-sensormib-oper;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR snmp-sensormib package operational data.
     
     Copyright (c) 2013-2017 by Cisco Systems, Inc.
     All rights reserved.";

  revision 2015-11-09 {
    description
      "IOS XR 6.0 revision.";
  }

  grouping SNMP-SENSOR-INFO-XML {
    description
      "SNMP sensor Info";
    leaf field-validity-bitmap {
      type uint32;
      description
        "Sensor valid bitmap";
    }
    leaf device-description {
      type string {
        length "0..64";
      }
      description
        "Device Name";
    }
    leaf units {
      type string {
        length "0..64";
      }
      description
        "Units of variable being read";
    }
    leaf device-id {
      type uint32;
      description
        "Identifier for this device";
    }
    leaf value {
      type uint32;
      description
        "Current reading of sensor";
    }
    leaf alarm-type {
      type uint32;
      description
        "Indicates threshold violation";
    }
    leaf data-type {
      type uint32;
      description
        "Sensor data type enums";
    }
    leaf scale {
      type uint32;
      description
        "Sensor scale enums";
    }
    leaf precision {
      type uint32;
      description
        "Sensor precision range";
    }
    leaf status {
      type uint32;
      description
        "Sensor operation state enums";
    }
    leaf age-time-stamp {
      type uint32;
      description
        "Age of the sensor value; set to the current time
         if directly access the value from sensor";
    }
    leaf update-rate {
      type uint32;
      description
        "Sensor value update rate;set to 0 if sensor
         value is updated and evaluated immediately";
    }
    leaf measured-entity {
      type uint32;
      description
        "physical entity for which the sensor is taking
         measurements";
    }
  }
}
