module Cisco-IOS-XR-sysadmin-sdr-console {
  namespace "http://www.cisco.com/ns/yang/Cisco-IOS-XR-sysadmin-sdr-console";
  prefix sdr_console;

  import tailf-common {
    prefix tailf;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains a collection of YANG
     definitions for Cisco IOS-XR SysAdmin configuration.
     
     Copyright(c) 2015-2017 by Cisco Systems, Inc.
     All rights reserved.";

  revision 2017-04-12 {
    description
      "Changed the namespace and module name";
  }
  revision 2015-05-11 {
    description
      "Initial version.";
  }

  grouping console-attach-config-group {
    container attach-sdr {
      container runtime {
        tailf:validate "sdr_runtime_console_validate" {
          tailf:dependency ".";
        }
        tailf:info "Configure attach-sdr";
        tailf:cli-drop-node-name;
        list location {
          key "location-rp";
          tailf:info "Location of console attach to apply";
          leaf location-rp {
            type string {
              pattern "((0?[0-9]|1[1-5])/([rR][pP]\\d{1,2}))(/[cC][pP][uU]0)?";
              tailf:info "Location string";
            }
            tailf:info "Enter location to apply the console attach config";
          }
          list tty-name {
            key "ttyname";
            tailf:info "TTY name";
            leaf ttyname {
              type string {
                length "1..30";
                pattern "console1|console2";
                tailf:info "TTY name string [console1 | console2]";
              }
              tailf:info "Enter TTY name";
            }
            leaf sdr-name {
              type string {
                length "1..30";
                pattern "[a-zA-Z0-9_.{}+-]+";
                tailf:info "SDR name string";
              }
              tailf:info "Enter SDR name";
            }
          }
        }
      }
      container boot {
        tailf:validate "sdr_boot_console_validate" {
          tailf:dependency ".";
        }
        tailf:info "Configure attach-sdr at boot";
        list location {
          key "location-rp";
          tailf:info "Location of Console attach to apply";
          leaf location-rp {
            type string {
              pattern "((0?[0-9]|1[1-5])/([rR][pP]\\d{1,2}))(/[cC][pP][uU]0)?";
              tailf:info "Location string";
            }
            tailf:info "Location to apply the console attach config";
          }
          leaf sdr-name {
            type string {
              length "1..30";
              pattern "[a-zA-Z0-9_.{}+-]+";
              tailf:info "SDR name string";
            }
            tailf:info "Enter SDR name";
          }
        }
      }
    }
  }
  tailf:id "http://www.cisco.com/panini/calvados/sdr_mgr/sdr_console";
}
