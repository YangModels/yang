module Cisco-IOS-XR-crypto-ssh-oper {
  namespace "http://cisco.com/ns/yang/Cisco-IOS-XR-crypto-ssh-oper";
  prefix crypto-ssh-oper;

  import Cisco-IOS-XR-types {
    prefix xr;
  }
  include Cisco-IOS-XR-crypto-ssh-oper-sub1 {
    revision-date 2017-05-01;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR crypto-ssh package operational data.
     
     This module contains definitions
     for the following management objects:
       ssh1: Crypto Secure Shell(SSH) data
       ssh: ssh
     
     Copyright (c) 2013-2017 by Cisco Systems, Inc.
     All rights reserved.";

  revision 2017-05-01 {
    description
      "Fixing backward compatibility error in module.";
  }
  revision 2015-06-02 {
    description
      "IOS XR 5.3.2 revision.";
  }
  revision 2015-01-07 {
    description
      "IOS XR 5.3.1 revision.";
  }

  container ssh1 {
    config false;
    description
      "Crypto Secure Shell(SSH) data";
    container kex {
      description
        "key exchange method data";
      container nodes {
        description
          "Node-specific ssh session details";
        list node {
          key "node-name";
          description
            "SSH session details for a particular node";
          leaf node-name {
            type xr:Node-id;
            description
              "Node name";
          }
          uses SSH-SESSION-DETAIL;
        }
      }
    }
  }
  container ssh {
    config false;
    description
      "ssh";
    container session {
      description
        "Crypto SSH session";
      container rekey {
        description
          "SSH session rekey information";
        uses SSH-SESSION-REKEY;
      }
      container brief {
        description
          "SSH session brief information";
        uses SSH-SESSION-BRIEF;
      }
      container detail {
        description
          "SSH session detail information";
        uses SSH-SESSION-DETAIL;
      }
    }
  }
}
