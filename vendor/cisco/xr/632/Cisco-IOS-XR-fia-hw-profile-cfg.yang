module Cisco-IOS-XR-fia-hw-profile-cfg {
  namespace "http://cisco.com/ns/yang/Cisco-IOS-XR-fia-hw-profile-cfg";
  prefix fia-hw-profile-cfg;

  import Cisco-IOS-XR-types {
    prefix xr;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR fia-hw-profile package configuration.
     
     This module contains definitions
     for the following management objects:
       hw-module-profile-config: none
     
     Copyright (c) 2013-2017 by Cisco Systems, Inc.
     All rights reserved.";

  revision 2016-06-22 {
    description
      "Schema added.";
  }
  revision 2015-11-09 {
    description
      "IOS XR 6.0 revision.";
  }

  container hw-module-profile-config {
    description
      "none";
    container profile {
      description
        "Configure profile.";
      container tcam-table {
        description
          "Configure profile for TCAM LC cards";
        container fib-table {
          description
            "FIB table for TCAM LC cards";
          container ipv4-address {
            description
              "IPv4 table for TCAM LC cards";
            container ipv4-unicast {
              description
                "Unicast table for TCAM LC cards";
              container ipv4-unicast-prefix-lengths {
                description
                  "IPv4 Unicast prefix ";
                list ipv4-unicast-prefix-length {
                  key "prefix-length";
                  description
                    "IPv4 Unicast prefix length";
                  leaf ipv4-unicast-prefix-percent {
                    type string;
                    units "percentage";
                    description
                      "curve out percentage of TCAM table
                       entries";
                  }
                  leaf prefix-length {
                    type uint32 {
                      range "0..32";
                    }
                    description
                      "prefix length";
                  }
                }
              }
              leaf ipv4-unicast-percent {
                type uint32 {
                  range "0..100";
                }
                units "percentage";
                description
                  "curve out percentage of TCAM table entries";
              }
            }
          }
          container ipv6-address {
            description
              "IPv6 table for TCAM LC cards";
            container ipv6-unicast {
              description
                "Unicast table for TCAM LC cards";
              container ipv6-unicast-prefix-lengths {
                description
                  "IPv6 Unicast prefix ";
                list ipv6-unicast-prefix-length {
                  key "prefix-length";
                  description
                    "IPv6 Unicast prefix length";
                  leaf ipv6-unicast-prefix-percent {
                    type string;
                    units "percentage";
                    description
                      "curve out percentage of TCAM table
                       entries";
                  }
                  leaf prefix-length {
                    type uint32 {
                      range "0..128";
                    }
                    description
                      "prefix length";
                  }
                }
              }
              leaf ipv6-unicast-percent {
                type uint32 {
                  range "0..100";
                }
                units "percentage";
                description
                  "curve out percentage of TCAM table entries";
              }
            }
          }
        }
      }
      container load-balance {
        description
          "Configure load balance parameters";
        leaf load-balance-profile {
          type int32;
          description
            "Configure load balance parameters";
        }
      }
      container stats {
        description
          "Configure stats";
        leaf counter-profile {
          type int32;
          description
            "Configure stats for qos-enhanced and
             acl-permit";
        }
      }
      container netflows {
        description
          "Configure Netflow profile.";
        list netflow {
          key "ipfix315-enable location-string location-id";
          description
            "none";
          leaf ipfix315-enable {
            type xr:Cisco-ios-xr-string;
            description
              "none";
          }
          leaf location-string {
            type xr:Cisco-ios-xr-string;
            description
              "Location of NETFLOW config";
          }
          leaf location-id {
            type int32;
            description
              "Location ID hex to Decimal 0xffff for all";
          }
          leaf enable-val {
            type int32;
            mandatory true;
            description
              "If Enabled set value to 65535";
          }
        }
      }
      container profile-acl {
        description
          "Configure acl profile";
        leaf egress {
          type boolean;
          description
            "Enabled or disabled";
        }
      }
      container profile-tcam {
        description
          "Configure Tcam Profile";
        container key-format {
          description
            "none";
          container acl-tables {
            description
              "Configure acl profile";
            list acl-table {
              key "address-family location-string location-id";
              description
                "Configure format for acl profile";
              leaf address-family {
                type xr:Cisco-ios-xr-string;
                description
                  "ipv4/ipv6";
              }
              leaf location-string {
                type xr:Cisco-ios-xr-string;
                description
                  "Location string (all) if for all LCs";
              }
              leaf location-id {
                type int32;
                description
                  "Location ID hex to Decimal 0xffff for all";
              }
              leaf source-addr {
                type int32;
                description
                  "Source Address 32 bit qual";
              }
              leaf destination-addr {
                type int32;
                description
                  "Destination Address 32 bit qual";
              }
              leaf source-port {
                type int32;
                description
                  "Source Port";
              }
              leaf dest-port {
                type int32;
                description
                  "Destination Port";
              }
              leaf prot-type {
                type int32;
                description
                  "Protocol Type";
              }
              leaf tcp-flag {
                type int32;
                description
                  "TCP Flags";
              }
              leaf pack-len {
                type int32;
                description
                  "Packet Length";
              }
              leaf frag-bit {
                type int32;
                description
                  "Fragment Bit";
              }
              leaf precedence {
                type int32;
                description
                  "Precedence";
              }
              leaf port-range {
                type int32;
                description
                  "PortRange";
              }
              leaf udf1 {
                type string;
                description
                  "UDF name";
              }
              leaf udf2 {
                type string;
                description
                  "UDF name";
              }
              leaf udf3 {
                type string;
                description
                  "UDF name";
              }
              leaf udf4 {
                type string;
                description
                  "UDF name";
              }
              leaf udf5 {
                type string;
                description
                  "UDF name";
              }
              leaf udf6 {
                type string;
                description
                  "UDF name";
              }
              leaf udf7 {
                type string;
                description
                  "UDF name";
              }
              leaf udf8 {
                type string;
                description
                  "UDF name";
              }
              leaf en-capture {
                type int32;
                description
                  "Enable Capture";
              }
              leaf en-ttl {
                type int32;
                description
                  "Enable Setting TTL";
              }
              leaf en-match {
                type int32;
                description
                  "Enable Matching TTL";
              }
              leaf en-share-acl {
                type int32;
                description
                  "Enable Non Shared Interface ACL";
              }
            }
          }
        }
      }
      container qos {
        description
          "Configure profile.";
        container hqos-enable-all {
          description
            "Configure Hqos profile";
          leaf hqos-enable {
            type int32;
            description
              " Hqos profile value";
          }
        }
        container ingress-model-root-def {
          description
            "Configure Ingress Model Default";
          leaf ingress-model-leaf-def {
            type int32;
            description
              "Ingress Model Default";
          }
        }
        container ingress-models {
          description
            "Configure Ingress Model Root";
          list ingress-model {
            key "node-name";
            description
              "Configure Ingress Model";
            leaf node-name {
              type xr:Cisco-ios-xr-string;
              description
                "NodeName";
            }
            list ingress-model-leaf {
              key "location";
              description
                "Configure Ingress Model Leaf";
              leaf ingress-model-leaf {
                type int32;
                mandatory true;
                description
                  "IngressModelLeaf";
              }
              leaf location {
                type int32;
                description
                  "Location";
              }
            }
          }
        }
        container trunks {
          description
            "Configure Max Trunk Size";
          leaf trunk-size {
            type int32;
            description
              "Max Trunk Size";
          }
        }
        container class-maps-root-def {
          description
            "Configure Class Maps Default";
          leaf class-map-size-def {
            type int32;
            description
              "Class Map Size Default";
          }
        }
        container class-maps {
          description
            "Configure Class Map Root";
          list class-map {
            key "node-name";
            description
              "Configure Class Maps";
            leaf node-name {
              type xr:Cisco-ios-xr-string;
              description
                "NodeName";
            }
            list class-map-size {
              key "location";
              description
                "Class Map Size";
              leaf class-map-size {
                type int32;
                mandatory true;
                description
                  "ClassMapSize";
              }
              leaf location {
                type int32;
                description
                  "Location";
              }
            }
          }
        }
      }
    }
    container fib-scale {
      description
        "Configure Fib for Scale for noTcam LC.";
      container ipv6-unicast-scale-no-tcam {
        description
          "IPv6 table for NOTCAM LC Scale.";
        container scale-ipv6-no-tcam {
          description
            "Scale for IPv6 table for NoTCAM LC.";
          leaf internet-optimized-ipv6-no-tcam {
            type string;
            description
              "Internet-optimized Scale for IPv6 table for
               NoTCAM LC.";
          }
        }
      }
      container ipv4-unicast-scale-no-tcam {
        description
          "IPv4 table for NOTCAM LC Scale.";
        container scale-ipv4-no-tcam {
          description
            "Scale for IPv4 table for NoTCAM LC.";
          leaf optimized-ipv4-no-tcam {
            type string;
            description
              "Optimized Scale for IPv4 table for NoTCAM LC.";
          }
        }
      }
    }
    container tcam {
      description
        "Configure Tcam.";
      container fib-tcam-scale {
        description
          "Configure Fib iscale for Tcam.";
        container ipv4-unicast-scale {
          description
            "IPv4 table for TCAM LC Scale.";
          leaf ipv4-scale {
            type empty;
            description
              "Scale for IPv4 table for TCAM LC.";
          }
        }
      }
    }
  }
}
