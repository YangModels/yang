submodule Cisco-IOS-XR-es-ace-cfg {
  belongs-to Cisco-IOS-XR-es-acl-cfg {
    prefix es-acl-cfg;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ES ACL entry configuration.
     
     Copyright (c) 2015-2018 by Cisco Systems, Inc.
     All rights reserved.";

  revision 2017-05-01 {
    description
      "Fixing backward compatibility error in module.";
  }
  revision 2015-11-09 {
    description
      "Initial revision.";
  }

  typedef es-acl-grant-enum {
    type enumeration {
      enum "deny" {
        value 0;
        description
          "Deny";
      }
      enum "permit" {
        value 1;
        description
          "Permit";
      }
    }
    description
      "ES acl grant enum";
  }

  typedef es-acl-address {
    type string {
      pattern "([0-9a-fA-F]{1,4}(\\.[0-9a-fA-F]{1,4}){2})";
    }
  }

  grouping ES-ACL-CONFIG-ACE {
    description
      "ES ACE entry.";
    leaf grant {
      type es-acl-grant-enum;
      description
        "Whether to forward or drop packets matching the
         ACE.";
    }
    container source-network {
      description
        "Source network settings.";
      leaf source-address {
        type es-acl-address;
        description
          "Source address to match, leave unspecified
           for any.";
      }
      leaf source-wild-card-bits {
        type es-acl-address;
        description
          "Wildcard bits to apply to source address
           (if specified), leave unspecified for no
           wildcarding.";
      }
    }
    container destination-network {
      description
        "Destination network settings.";
      leaf destination-address {
        type es-acl-address;
        description
          "Destination address to match (if a protocol
           was specified), leave unspecified for any.";
      }
      leaf destination-wild-card-bits {
        type es-acl-address;
        description
          "Wildcard bits to apply to destination address
           (if specified), leave unspecified for no
           wildcarding.";
      }
    }
    leaf vlan1 {
      type uint16;
      description
        "VLAN ID/range lower limit";
    }
    leaf vlan2 {
      type uint16;
      description
        "VLAN ID range higher limit";
    }
    leaf cos {
      type uint8;
      description
        "COS value";
    }
    leaf dei {
      type uint8;
      description
        "DEI bit";
    }
    leaf inner-vlan1 {
      type uint16;
      description
        "Inner VLAN ID/range lower limit";
    }
    leaf inner-vlan2 {
      type uint16;
      description
        "Inner VLAN ID range higher limit";
    }
    leaf inner-cos {
      type uint8;
      description
        "Inner COS value";
    }
    leaf inner-dei {
      type uint8;
      description
        "Inner DEI bit";
    }
    leaf remark {
      type string;
      description
        "Comments or a description for the access list.";
    }
    leaf ether-type-number {
      type uint16;
      description
        "Ethernet type Number";
    }
    leaf capture {
      type boolean;
      description
        "Enable capture.";
    }
    leaf log-option {
      type uint8;
      description
        "Whether and how to log matches against this
         entry.";
    }
    leaf sequence-str {
      type string {
        length "1..64";
      }
      description
        "Sequence String for the ace.";
    }
  }
}
