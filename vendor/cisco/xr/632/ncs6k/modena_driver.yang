module modena_driver {
  namespace "http://www.cisco.com/calvados/calvados_controllers/slice_control/modena";
  prefix modena_driver;

  import tailf-common {
    prefix tailf;
  }
  import modena_driver_types {
    prefix modena-driver-types;
  }

  grouping modena_lane_data {
    list modena_lane {
      key "modena_lane_id";
      tailf:callpoint "modena_lane_cp";
      tailf:info "Modena lane detail information";
      tailf:cli-show-template-enter "";
      tailf:cli-show-template
        "Modena lane  information\\\\: 
         modena_lane_id                        \\\\:$(modena_lane_id|ljust:10)
         $(is_data_available == true ?Oper Mode                             \\\\:$(oper_mode|ljust:10)
         :No valid data.
         )
        ";
      tailf:cli-suppress-table;
      leaf modena_lane_id {
        type modena-driver-types:modena_lane_id_type;
      }
      leaf is_data_available {
        type boolean;
        default "false";
        tailf:hidden "internal-command";
      }
      leaf oper_mode {
        type string;
        tailf:hidden "internal-command";
      }
    }
  }

  grouping modena_summary_info {
    list modena_summary {
      key "modena_id";
      tailf:callpoint "modena_summary_cp";
      tailf:cli-no-key-completion;
      tailf:cli-no-match-completion;
      tailf:cli-suppress-table;
      tailf:cli-show-template-enter "";
      tailf:cli-show-template-legend
        "Modena information\\\\: 
         -----------------------------------
        ";
      tailf:cli-show-template
        "$(is_data_available == true ?$(.legend_shown != true ?Modena information\\\\: 
         -----------------------------------
         )modena_id                             \\\\:$(modena_id|ljust:10)
         ready                                 \\\\:$(mready|ljust:10)
         port_ctx_p                            \\\\:$(mport_ctx_p|ljust:10)
         levm                                  \\\\:$(mlevm|ljust:10)
         ctrace_err_hdl                        \\\\:$(mctrace_err_hdl|ljust:10)
         ctrace_evt_hdl                        \\\\:$(mctrace_evt_hdl|ljust:10)
         signature                             \\\\:$(msignature|ljust:10)
         lpc_ready                             \\\\:$(mlpc_ready|ljust:10)
         opaque                                \\\\:$(mopaque|ljust:10)
         nodeid                                \\\\:$(mnodeid|ljust:10)
         slice                                 \\\\:$(mslice|ljust:10)
         port                                  \\\\:$(mport|ljust:10)
         dev_addr                              \\\\:$(mdev_addr|ljust:10)
         rd_func                               \\\\:$(mrd_func|ljust:10)
         wr_func                               \\\\:$(mwr_func|ljust:10)
         Next_Port_CTX                         \\\\:$(mnext|ljust:10)
         :No valid data.
         )
        ";
      leaf modena_id {
        type modena-driver-types:modena_id_type;
      }
      leaf is_data_available {
        type boolean;
        default "false";
        tailf:hidden "internal-command";
      }
      leaf mready {
        type boolean;
        default "false";
        tailf:hidden "internal-command";
      }
      leaf mport_ctx_p {
        type string;
        tailf:hidden "internal-command";
      }
      leaf mlevm {
        type string;
        tailf:hidden "internal-command";
      }
      leaf mctrace_err_hdl {
        type string;
        tailf:hidden "internal-command";
      }
      leaf mctrace_evt_hdl {
        type string;
        tailf:hidden "internal-command";
      }
      leaf msignature {
        type string;
        tailf:hidden "internal-command";
      }
      leaf mlpc_ready {
        type boolean;
        default "false";
        tailf:hidden "internal-command";
      }
      leaf mopaque {
        type string;
        tailf:hidden "internal-command";
      }
      leaf mnodeid {
        type string;
        tailf:hidden "internal-command";
      }
      leaf mslice {
        type uint32;
        tailf:hidden "internal-command";
      }
      leaf mport {
        type uint32;
        tailf:hidden "internal-command";
      }
      leaf mdev_addr {
        type uint8;
        tailf:hidden "internal-command";
      }
      leaf mrd_func {
        type string;
        tailf:hidden "internal-command";
      }
      leaf mwr_func {
        type string;
        tailf:hidden "internal-command";
      }
      leaf mnext {
        type string;
        tailf:hidden "internal-command";
      }
    }
  }

  grouping modena_data_show {
    list modena {
      key "modena_id";
      tailf:info "Modena information";
      tailf:callpoint "modena_cp";
      tailf:cli-no-key-completion;
      tailf:cli-no-match-completion;
      tailf:cli-suppress-table;
      tailf:cli-show-template-enter
        "Modena id\\\\: $(modena_id)
         ------------------------
        ";
      leaf modena_id {
        type modena-driver-types:modena_id_type;
      }
      uses modena_lane_data;
    }
  }
}
