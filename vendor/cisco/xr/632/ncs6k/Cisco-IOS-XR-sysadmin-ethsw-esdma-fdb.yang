module Cisco-IOS-XR-sysadmin-ethsw-esdma-fdb {
  namespace "http://www.cisco.com/ns/yang/Cisco-IOS-XR-sysadmin-ethsw-esdma-fdb";
  prefix esdma_fdb;

  import tailf-common {
    prefix tailf;
  }
  import ietf-yang-types {
    prefix ietf;
  }
  import Cisco-IOS-XR-sysadmin-ethsw-esdma-types {
    prefix esdma_types;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains the YANG definitions
     for the Cisco IOS-XR SysAdmin
     'show controller switch fdb' commands.
     
     Copyright(c) 2011-2017 by Cisco Systems, Inc.
     All rights reserved.";

  revision 2017-05-01 {
    description
      "Namespace change to comply with Cisco guidelines on namespace";
  }
  revision 2016-07-06 {
    description
      "Initial revision with content extracted from esdma_cli.yang.";
  }

  grouping switch-fdb-location {
    container switch-fdb-common {
      tailf:callpoint "esdma_switch_fdb_information";
      tailf:cli-drop-node-name;
      list location {
        key "rack card switch-id";
        tailf:info "Location information for switch FDB information";
        tailf:cli-full-command;
        tailf:cli-key-format "$(1)/$(2)/$(3)";
        tailf:cli-suppress-table;
        tailf:cli-show-template "$(fdb-block/fdb-entry|show)";
        leaf rack {
          type esdma_types:esdma-rack-num-enum;
        }
        leaf card {
          type esdma_types:esdma-cpu;
          description
            "Card to list the switch FDB information for";
        }
        leaf switch-id {
          type esdma_types:esdma-switch-type-enum;
          description
            "Switch type";
        }
        leaf num-entries {
          type uint32;
          description
            "Number of FDB entries in the table.";
          tailf:cli-suppress-show-path;
          tailf:cli-suppress-show-match;
          tailf:alt-name "Total table entries: ";
        }
        leaf has-trunk-entry {
          type uint8;
          description
            "FDB entries contain an entry from the trunk";
          tailf:cli-suppress-show-path;
          tailf:cli-suppress-show-match;
        }
        leaf trunk-entry-message {
          type string;
          description
            "Message displayed when an FDB entry contains an entry for a trunk member port";
          tailf:cli-suppress-show-path;
          tailf:cli-suppress-show-match;
        }
        container fdb-block {
          tailf:cli-drop-node-name;
          tailf:cli-full-show-path;
          tailf:cli-suppress-show-match;
          list fdb-entry {
            key "fdb-index";
            tailf:cli-drop-node-name;
            tailf:cli-table-legend
              "Rack  Card  Switch
               ------------------
               $(../../rack|ljust:4)  $(../../card|ljust:4)  $(../../switch-id|ljust:6)
              ";
            tailf:cli-enforce-table;
            tailf:cli-table-footer
              "$($(../../has-trunk-entry)!=1?:
               $(../../trunk-entry-message)
               )
               Total table entries: $(../../num-entries)";
            leaf fdb-index {
              type uint32;
              tailf:cli-suppress-show-path;
              tailf:cli-suppress-show-match;
              tailf:display-column-name "FDB Index";
            }
            leaf fdb-mac-addr {
              type ietf:mac-address;
              tailf:cli-suppress-show-path;
              tailf:cli-suppress-show-match;
              tailf:display-column-name "MAC Address";
            }
            leaf fdb-vlan {
              type esdma_types:vlan-id-type;
              tailf:cli-suppress-show-path;
              tailf:cli-suppress-show-match;
              tailf:display-column-name "VLAN";
              tailf:cli-value-display-template "$(.)";
            }
            leaf fdb-vlan-hex {
              type leafref {
                path "../fdb-vlan";
              }
              tailf:cli-suppress-show-path;
              tailf:cli-suppress-show-match;
              tailf:display-column-name "";
              tailf:cli-value-display-template "(0x$(.|hex:3))";
            }
            leaf fdb-port {
              type esdma_types:esdma-switch-port-type;
              description
                "Switch port MAC address learned on.";
              tailf:cli-suppress-show-path;
              tailf:cli-suppress-show-match;
              tailf:display-column-name "Src Port";
              tailf:cli-value-display-template "$(.==-1?-:$(.==256?Trunk:$(.)))";
            }
            leaf fdb-trap-entry {
              type esdma_types:esdma-switch-yes-no-enum;
              tailf:cli-suppress-show-path;
              tailf:cli-suppress-show-match;
              tailf:display-column-name "Trap";
            }
            leaf fdb-static-entry {
              type esdma_types:esdma-switch-yes-no-enum;
              tailf:cli-suppress-show-path;
              tailf:cli-suppress-show-match;
              tailf:display-column-name "Static";
            }
            leaf-list fdb-synced-cores {
              type uint8;
              tailf:cli-suppress-show-path;
              tailf:cli-suppress-show-match;
              tailf:display-column-name "Synced Cores";
              tailf:cli-flat-list-syntax;
            }
          }
        }
      }
    }
  }

  grouping switch-fdb-group {
    container fdb {
      tailf:info "Display switch forwarding database";
      container vlan {
        tailf:info "Filter FDB based on VLAN";
        tailf:callpoint "esdma_switch_fdb_vlan_filter";
        list vlan-iter {
          key "vlan";
          tailf:cli-drop-node-name;
          tailf:info "VLAN to filter on";
          tailf:cli-suppress-table;
          leaf vlan {
            type esdma_types:vlan-id-type;
            tailf:info "VLAN to filter on";
          }
          uses switch-fdb-location;
        }
      }
      container mac {
        tailf:info "Filter FDB based on MAC address";
        tailf:callpoint "esdma_switch_fdb_mac_filter";
        list mac-iter {
          key "mac";
          tailf:cli-drop-node-name;
          tailf:info "MAC address to filter on";
          tailf:cli-suppress-table;
          leaf mac {
            type ietf:mac-address;
            tailf:info "MAC address to filter on";
          }
          uses switch-fdb-location;
        }
      }
      container port {
        tailf:info "Filter FDB based on source port";
        tailf:callpoint "esdma_switch_fdb_port_filter";
        list port-iter {
          key "port";
          tailf:cli-drop-node-name;
          tailf:cli-suppress-table;
          leaf port {
            type esdma_types:esdma-switch-port-type;
            description
              "Switch port used for filtering";
            tailf:display-column-name "Switch Port";
          }
          uses switch-fdb-location;
        }
      }
      container statistics {
        tailf:info "Display FDB table statistics";
        tailf:callpoint "esdma_switch_fdb_statistics";
        list location {
          key "rack card switch-id";
          tailf:info "Location information for switch FDB statistics";
          tailf:cli-full-command;
          tailf:cli-key-format "$(1)/$(2)/$(3)";
          tailf:cli-suppress-table;
          tailf:cli-show-template-enter "FDB Maintenance Counters For Switch $(rack)/$(card)/$(switch-id)\n";
          tailf:cli-show-template "$(counter-info|show:indent=4)$(core-id|show)";
          leaf rack {
            type esdma_types:esdma-rack-num-enum;
          }
          leaf card {
            type esdma_types:esdma-cpu;
            description
              "Card";
          }
          leaf switch-id {
            type esdma_types:esdma-switch-type-enum;
            description
              "Switch type";
          }
          container counter-info {
            tailf:cli-drop-node-name;
            tailf:cli-full-show-path;
            leaf fdb-shadow-entries {
              type uint32;
              tailf:alt-name "Current shadow table entries: ";
            }
            leaf fdb-max-shadow-entries {
              type uint32;
              tailf:alt-name "Maximum shadow table entries: ";
            }
            leaf fdb-max-hash-chain {
              type uint32;
              tailf:alt-name "Maximum hash chain depth: ";
            }
            leaf fdb-entries-added {
              type uint32;
              tailf:alt-name "Number of entries added: ";
            }
            leaf fdb-entries-deleted {
              type uint32;
              tailf:alt-name "Number of entries deleted: ";
            }
            leaf fdb-entries-updated {
              type uint32;
              tailf:alt-name "Number of entries updated: ";
            }
            leaf fdb-flushes {
              type uint32;
              tailf:alt-name "Number of FDB flushes: ";
            }
            leaf fdb-address-updates {
              type uint32;
              tailf:alt-name "Address update messages: ";
            }
            leaf fdb-new-addresses {
              type uint32;
              tailf:alt-name "New addresses: ";
            }
            leaf fdb-aged-updates {
              type uint32;
              tailf:alt-name "Aged addresses: ";
            }
            leaf fdb-transplant-updates {
              type uint32;
              tailf:alt-name "Transplanted updates: ";
            }
            leaf fdb-forwarding-updates {
              type uint32;
              tailf:alt-name "Forwarding updates: ";
            }
            leaf fdb-address-insert-errors {
              type uint32;
              tailf:alt-name "Address insert errors: ";
            }
            leaf fdb-address-update-errors {
              type uint32;
              tailf:alt-name "Address update errors: ";
            }
            leaf fdb-memory-errors {
              type uint32;
              tailf:alt-name "FDB memory errors: ";
            }
            leaf fdb-allocation-errors {
              type uint32;
              tailf:alt-name "FDB allocation errors: ";
            }
            leaf fdb-address-updates-queued {
              type uint32;
              tailf:alt-name "Address updates queued: ";
            }
            leaf fdb-address-queue-full {
              type esdma_types:esdma-switch-yes-no-enum;
              tailf:alt-name "Address queue full: ";
            }
            leaf fdb-forwarding-updates-queued {
              type uint32;
              tailf:alt-name "Forwarding updates queued: ";
            }
            leaf fdb-forwarding-queue-full {
              type esdma_types:esdma-switch-yes-no-enum;
              tailf:alt-name "Forwarding queue full: ";
            }
          }
          list core-id {
            key "core";
            tailf:cli-drop-node-name;
            tailf:cli-full-show-path;
            tailf:cli-enforce-table;
            tailf:cli-table-legend
              "
               FDB Table Synchronization Information
              ";
            leaf core {
              type int32;
              tailf:display-column-name "FDB Instance";
              tailf:cli-value-display-template "$(.==256?Shadow:$(.))";
              tailf:cli-column-width "12";
            }
            leaf core-entries {
              type uint32;
              tailf:display-column-name "Total Entries";
              tailf:cli-column-width "13";
            }
            leaf core-static-entries {
              type uint32;
              tailf:display-column-name "Static Entries";
              tailf:cli-column-width "14";
            }
          }
        }
      }
      uses switch-fdb-location;
    }
  }
  tailf:id "http://cisco.com/panini/calvados/esdma/esdma_fdb";
}
