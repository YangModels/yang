module Cisco-IOS-XR-sysadmin-ethsw-esdma-reachable {
  namespace "http://www.cisco.com/ns/yang/Cisco-IOS-XR-sysadmin-ethsw-esdma-reachable";
  prefix esdma_reachable;

  import tailf-common {
    prefix tailf;
  }
  import Cisco-IOS-XR-sysadmin-ethsw-esdma-types {
    prefix esdma_types;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains the YANG definitions
     for the Cisco IOS-XR SysAdmin
     'show controller switch reachable' command.
     
     Copyright(c) 2011-2017 by Cisco Systems, Inc.
     All rights reserved.";

  revision 2017-05-01 {
    description
      "Namespace change to comply with Cisco guidelines on namespace";
  }
  revision 2016-07-06 {
    description
      "Initial revision with content extracted from esdma_cli.yang.";
  }

  grouping switch-reachable-data {
    container reachable {
      tailf:callpoint "esdma_switch_reachable_data";
      tailf:info "Lists all control plane Ethernet switches";
      list location {
        key "rack card switch-id";
        tailf:cli-drop-node-name;
        tailf:cli-full-command;
        tailf:cli-enforce-table;
        tailf:cli-no-match-completion;
        tailf:cli-no-key-completion;
        tailf:cli-full-show-path;
        leaf rack {
          type esdma_types:esdma-rack-num-enum;
          tailf:display-column-name "Rack";
        }
        leaf card {
          type esdma_types:esdma-cpu;
          tailf:display-column-name "Card";
        }
        leaf switch-id {
          type esdma_types:esdma-switch-type-enum;
          tailf:display-column-name "Switch";
        }
      }
    }
  }
  tailf:id "http://cisco.com/panini/calvados/esdma/esdma_reachable";
}
