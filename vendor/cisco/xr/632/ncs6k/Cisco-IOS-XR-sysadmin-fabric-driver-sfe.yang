module Cisco-IOS-XR-sysadmin-fabric-driver-sfe {
  namespace "http://www.cisco.com/ns/yang/Cisco-IOS-XR-sysadmin-fabric-driver-sfe";
  prefix fabric_sfe;

  import tailf-common {
    prefix tailf;
  }
  import Cisco-IOS-XR-sysadmin-fabric-types {
    prefix fabric-types;
  }
  import Cisco-IOS-XR-sysadmin-show-trace {
    prefix show-trace;
  }

  revision 2017-09-26 {
    description
      "To restore the display of link FSM states in SFE link-info CLI output";
  }
  revision 2017-05-01 {
    description
      "Namespace change to comply with Cisco guidelines on namespace";
  }

  grouping sfe_drvr_info {
    list drvr_info {
      key "idx";
      tailf:cli-suppress-table;
      tailf:cli-show-template-enter "";
      tailf:cli-show-template-legend
        "$(.legend_shown != true ?
         =========================================================================
         SFE Driver information
         =========================================================================
         )";
      tailf:cli-show-template
        "
         Driver Version: $(drv_version)   ($(coeff_major_rev).$(coeff_minor_rev))
         
         Functional role: $(func_role),   ISSU role: $(issu_role)
         Rack\\\\: $(rack_name), Type\\\\: $(rack_type), Number\\\\: $(rack_num), IP Address: $(ip_address)
         Startup time       : $(startup_time)
         Availability Masks :
              Card\\\\: 0x$(card_avail_mask|hex)       Asic\\\\: 0x$(asic_avail_mask|hex)       Exp Asic\\\\: 0x$(exp_asic_avail_mask|hex)
         Unicast/Multicast (ratio) \\\\: $(ucmc_ratio)
         +----------------------------------------------------------------+
         |Process  | Connection | Registration| Connection | DLL          |
         |/Lib     | status     | status      | requests   | registration |
         +----------------------------------------------------------------+
         | PM      | $($(pm_conn_active == true ? Active : Inactive)|ljust:11)| $( n/a|ljust:12)| $(num_pm_conn_reqs|rjust:11)| $( n/a|ljust:13)|
         | PL-LOCAL| $($(platform_local_conn_active == true ? Active : Inactive)|ljust:11)| $($(platform_local_reg_active == true ? Active : Inactive)|ljust:12)| $(num_platform_local_conn_reqs|rjust:11)| $( n/a|ljust:13)|
         | FSDB    | $($(fsdb_conn_active == true ? Active : Inactive)|ljust:11)| $($(fsdb_reg_active == true ? Active : Inactive)|ljust:12)| $(num_fsdb_conn_reqs|rjust:11)| $( n/a|ljust:13)|
         | FGID    | $($(fgid_conn_active == true ? Active : Inactive)|ljust:11)| $($(fgid_reg_active == true ? Active : Inactive)|ljust:12)| $(num_fgid_conn_reqs|rjust:11)| $( n/a|ljust:13)|
         | CM      | $($(cm_conn_active == true ? Active : Inactive)|ljust:11)| $($(cm_reg_active == true ? Active : Inactive)|ljust:12)| $(num_cm_conn_reqs|rjust:11)| $( n/a|ljust:13)|
         | CCC     | $($(ccc_conn_active == true ? Active : Inactive)|ljust:11)| $( n/a|ljust:12)| $(num_ccc_conn_reqs|rjust:11)| $( n/a|ljust:13)|
         | GASPP   | $( n/a|ljust:11)| $( n/a|ljust:12)| $( n/a|rjust:11)| $( n/a|ljust:13)|
         | CIH     | $( n/a|ljust:11)| $( n/a|ljust:12)| $( n/a|rjust:11)| $($(is_cih_registered == true ? Yes : No)|ljust:13)|
         +----------------------------------------------------------------+
         
         Asics \\\\:
         HP - HotPlug event,  PON - Power ON reset,     WB - Warm Boot,  A - All
         HR - Hard Reset,     DC  - Disconnect signal,  DL - DownLoad
         +-----------------------------------------------------------------------------------+
         | Asic inst.|card|HP|Asic| Asic  | Admin|plane| Fgid| Asic State |DC| Last  |PON|HR |
         |  (R/S/A\\\\)  |pwrd|  |type| class | /Oper|/grp | DL  |            |  | init  |(#\\\\)|(#\\\\)|
         +-----------------------------------------------------------------------------------+
         $(asic_list|show)+-----------------------------------------------------------------------------------+
        ";
      leaf idx {
        type int32;
      }
      leaf drv_version {
        type uint32;
        tailf:hidden "internal";
      }
      leaf coeff_major_rev {
        type uint32;
        tailf:hidden "internal";
      }
      leaf coeff_minor_rev {
        type uint32;
        tailf:hidden "internal";
      }
      leaf func_role {
        type string;
        tailf:hidden "internal";
      }
      leaf issu_role {
        type string;
        tailf:hidden "internal";
      }
      leaf rack_name {
        type string;
        tailf:hidden "internal";
      }
      leaf rack_type {
        type string;
        tailf:hidden "internal";
      }
      leaf rack_num {
        type string;
        tailf:hidden "internal";
      }
      leaf ip_address {
        type string;
        tailf:hidden "internal";
      }
      leaf card_avail_mask {
        type uint32;
        tailf:hidden "internal";
      }
      leaf asic_avail_mask {
        type uint64;
        tailf:hidden "internal";
      }
      leaf exp_asic_avail_mask {
        type uint64;
        tailf:hidden "internal";
      }
      leaf ucmc_ratio {
        type uint32;
        tailf:hidden "internal";
      }
      leaf pm_conn_active {
        type boolean;
        tailf:hidden "internal";
      }
      leaf platform_local_conn_active {
        type boolean;
        tailf:hidden "internal";
      }
      leaf fsdb_conn_active {
        type boolean;
        tailf:hidden "internal";
      }
      leaf fgid_conn_active {
        type boolean;
        tailf:hidden "internal";
      }
      leaf cm_conn_active {
        type boolean;
        tailf:hidden "internal";
      }
      leaf ccc_conn_active {
        type boolean;
        tailf:hidden "internal";
      }
      leaf issu_mgr_conn_active {
        type boolean;
        tailf:hidden "internal";
      }
      leaf peer_sfe_conn_active {
        type boolean;
        tailf:hidden "internal";
      }
      leaf cxp_conn_active {
        type boolean;
        tailf:hidden "internal";
      }
      leaf pm_reg_active {
        type boolean;
        tailf:hidden "internal";
      }
      leaf platform_local_reg_active {
        type boolean;
        tailf:hidden "internal";
      }
      leaf fsdb_reg_active {
        type boolean;
        tailf:hidden "internal";
      }
      leaf fgid_reg_active {
        type boolean;
        tailf:hidden "internal";
      }
      leaf cm_reg_active {
        type boolean;
        tailf:hidden "internal";
      }
      leaf issu_mgr_reg_active {
        type boolean;
        tailf:hidden "internal";
      }
      leaf peer_sfe_reg_active {
        type boolean;
        tailf:hidden "internal";
      }
      leaf cxp_reg_active {
        type boolean;
        tailf:hidden "internal";
      }
      leaf num_pm_conn_reqs {
        type uint8;
        tailf:hidden "internal";
      }
      leaf num_platform_local_conn_reqs {
        type uint8;
        tailf:hidden "internal";
      }
      leaf num_fsdb_conn_reqs {
        type uint8;
        tailf:hidden "internal";
      }
      leaf num_fgid_conn_reqs {
        type uint8;
        tailf:hidden "internal";
      }
      leaf num_fstats_conn_reqs {
        type uint8;
        tailf:hidden "internal";
      }
      leaf num_cm_conn_reqs {
        type uint8;
        tailf:hidden "internal";
      }
      leaf num_ccc_conn_reqs {
        type uint8;
        tailf:hidden "internal";
      }
      leaf num_issu_mgr_conn_reqs {
        type uint8;
        tailf:hidden "internal";
      }
      leaf num_peer_sfe_conn_reqs {
        type uint8;
        tailf:hidden "internal";
      }
      leaf num_cxp_conn_reqs {
        type uint8;
        tailf:hidden "internal";
      }
      leaf is_gaspp_registered {
        type boolean;
        tailf:hidden "internal";
      }
      leaf is_cih_registered {
        type boolean;
        tailf:hidden "internal";
      }
      leaf startup_time {
        type string;
        tailf:hidden "internal";
      }
      list asic_list {
        key "asic_idx";
        tailf:cli-suppress-table;
        tailf:cli-show-template-enter "";
        tailf:cli-show-template "| $(asic_instance|ljust:10)| $(card_powered|ljust:3)| $(hotplug_event|ljust:1)|$(asic_type|rjust:4)| $(asic_cardname|rjust:7)| $(admin-state|ljust:2)/$(oper_state|ljust:2)|$(fab_plane|rjust:2)/$(fab_group|ljust:2)|$(fgid_download|rjust:5)| $(asic_state|ljust:11)|$(asic_disconnect_signal|rjust:2)| $(last_init_cause|ljust:6)|$(num_pon_resets|rjust:3)|$(num_hard_resets|rjust:3)|\n";
        leaf asic_idx {
          type uint32;
        }
        leaf asic_instance {
          type string;
          tailf:hidden "internal";
        }
        leaf card_present {
          type string;
          tailf:hidden "internal";
        }
        leaf card_powered {
          type string;
          tailf:hidden "internal";
        }
        leaf hotplug_event {
          type uint32;
          tailf:hidden "internal";
        }
        leaf asic_type {
          type string;
          tailf:hidden "internal";
        }
        leaf asic_cardname {
          type string;
          tailf:hidden "internal";
        }
        leaf admin-state {
          type string;
          tailf:hidden "internal";
        }
        leaf oper_state {
          type string;
          tailf:hidden "internal";
        }
        leaf fab_plane {
          type string;
          tailf:hidden "internal";
        }
        leaf fab_group {
          type string;
          tailf:hidden "internal";
        }
        leaf fgid_download {
          type string;
          tailf:hidden "internal";
        }
        leaf asic_state {
          type string;
          tailf:hidden "internal";
        }
        leaf asic_disconnect_signal {
          type string;
          tailf:hidden "internal";
        }
        leaf last_init_cause {
          type string;
          tailf:hidden "internal";
        }
        leaf num_pon_resets {
          type uint32;
          tailf:hidden "internal";
        }
        leaf num_hard_resets {
          type uint32;
          tailf:hidden "internal";
        }
      }
    }
  }

  grouping sfe_link_info_asic_instance {
    list instance {
      key "instance-id";
      tailf:cli-no-key-completion;
      tailf:cli-no-match-completion;
      tailf:cli-show-template-enter "";
      tailf:cli-suppress-table;
      tailf:cli-show-template
        "$(is_show == true ?$(.path ~= rx ? $(.path ~= topo ?
         --------------------------------------------------------------------------------
         Node ID\\\\: $(nodeid_str|ljust:12)  Instance\\\\: $(instance-id)
         
         Flags\\\\: 
            A - Admin Down       B - Bad link conn  C - CRC error      D - Power Down
            E - Link not stEady  F - Far end down   G - Code Gro err   I - Asic Down
            L - No Sig Lock      M - Misalign       N - No FSDB info   P - Plane Down
            R - No Reach Cells   S - Size error     T - Invalid Topo   U - Perm Shut
            V - RcVr end rst     W - FGID prog      X - No CXP         Z - No signal
         --------------------------------------------------------------------------------
         Link ID      Link  Asic  Plane  EN/    Flags        Far-End       Far-End          
                      Spd   Stg. /Group  Oper                Link (FSDB\\\\)   Link (HW\\\\)  
                     (Gbps\\\\)             Status                                    
         --------------------------------------------------------------------------------:$(.path ~= flap ? 
         --------------------------------------------------------------------------------
         Node ID\\\\: $(nodeid_str|ljust:12)  Instance\\\\: $(instance-id)
         $(.path ~= detail ?
         Flags\\\\: 
            A - Admin Down       B - Bad link conn  C - CRC error      D - Power Down
            E - Link not stEady  F - Far end down   G - Code Gro err   I - Asic Down
            L - No Sig Lock      M - Misalign       N - No FSDB info   P - Plane Down
            R - No Reach Cells   S - Size error     T - Invalid Topo   U - Perm Shut
            V - RcVr end rst     W - FGID prog      X - No CXP         Z - No signal
         )--------------------------------------------------------------------------------
         Link ID        Oper       Link       Admin
                        Status     Errors     Shuts
         --------------------------------------------------------------------------------:$(.path ~= stats ? 
         --------------------------------------------------------------------------------
         Node ID\\\\: $(nodeid_str|ljust:12)  Instance\\\\: $(instance-id)
         --------------------------------------------------------------------------------
         $(.path ~= all ?Link ID              Ctrl          Data          Data       Re-Xmit  Async    
                              cells         cells         bytes               FIFO Rate
         :$(.path ~= ctrl ?Link ID                Ctrl     Dropped    
                                cells    rexmit ctrl
         :Link ID              Data          Data        CRC              CE          UCE
                              cells         bytes       errors                          
         ))--------------------------------------------------------------------------------))):$(.path ~= stats ?
         --------------------------------------------------------------------------------
         Node ID\\\\: $(nodeid_str|ljust:12)  Instance\\\\: $(instance-id)
         --------------------------------------------------------------------------------
         $(.path ~= all ?Link ID              Ctrl          Data          Data       Re-Xmit  Async    
                              cells         cells         bytes               FIFO Rate
         :$(.path ~= ctrl ?Link ID                Ctrl 
                                cells
         :Link ID                Data            Data 
                                cells           bytes
         ))--------------------------------------------------------------------------------:
         --------------------------------------------------------------------------------
         Node ID\\\\: $(nodeid_str|ljust:12)  Instance\\\\: $(instance-id)
         $(.path ~= detail ?
         Flags\\\\: 
            A - Admin Down       B - Bad link conn  C - CRC error      D - Power Down
            E - Link not stEady  F - Far end down   G - Code Gro err   I - Asic Down
            L - No Sig Lock      M - Misalign       N - No FSDB info   P - Plane Down
            R - No Reach Cells   S - Size error     T - Invalid Topo   U - Perm Shut
            V - RcVr end rst     W - FGID prog      X - No CXP         Z - No signal
         )--------------------------------------------------------------------------------
         Link ID      Oper   Enable                    
                      Status Status                    
         --------------------------------------------------------------------------------))
         $(link_idx_list|show))";
      leaf instance-id {
        type fabric-types:sfe_instance_type;
      }
      leaf nodeid_str {
        type string;
        tailf:hidden "internal";
      }
      leaf is_show {
        type boolean;
        tailf:hidden "internal";
      }
      list link_idx_list {
        key "link_idx";
        tailf:cli-suppress-table;
        tailf:cli-show-template-enter "";
        tailf:cli-show-template "$(.path ~= rx ?$(.path ~= topo ?$(link_id_str|ljust:12) $(speed|rjust:5)  $(stage|ljust:4) $(fab_plane|rjust:2)/$(fab_group|ljust:3) $(admin-state|rjust:2)/$(oper_state|ljust:3) $(flags|ljust:12) $(far_end_link_fsdb|ljust:13) $(far_end_link_hw|ljust:13)$(.path ~= detail ?$(history|show)):$(.path ~= flap ?$(link_id_str|ljust:14) $(oper_state|ljust:8) $(flap_cnt|rjust:6)    $(num_admin_shuts|rjust:6)    $(fsm_state|rjust:40)$(.path ~= detail ?$(history|show)):$(.path ~= stats ?$(.path ~= all ?$(link_id_str|ljust:12) $(RX_Control_cells_counter|rjust:13) $(RX_Data_cell_counter|rjust:13) $(RX_Data_byte_counter|rjust:13) $(RX_BEC_retransmit|rjust:12) $(RX_Asyn_fifo_rate|rjust:10):$(.path ~= ctrl ?$(link_id_str|ljust:12) $(RX_Control_cells_counter|rjust:15)$(RX_dropped_retransmitted_control|rjust:15) :$(link_id_str|ljust:12) $(RX_Data_cell_counter|rjust:13) $(RX_Data_byte_counter|rjust:13) $(RX_CRC_errors_counter|rjust:12) $(RX_LFEC_FEC_correctable_error|rjust:12) $(RX_LFEC_FEC_uncorrectable_errors|rjust:12)))))):$(.path ~= stats ?$(.path ~= all ?$(link_id_str|ljust:12) $(TX_Control_cells_counter|rjust:13) $(TX_Data_cell_counter|rjust:13) $(TX_Data_byte_counter|rjust:13) $(TX_BEC_retransmit|rjust:12) $(TX_Asyn_fifo_rate|rjust:10):$(.path ~= ctrl ?$(link_id_str|ljust:12) $(TX_Control_cells_counter|rjust:15):$(link_id_str|ljust:12) $(TX_Data_cell_counter|rjust:15) $(TX_Data_byte_counter|rjust:15))):$(link_id_str|ljust:12) $(oper_state|rjust:4)   $(admin-state|rjust:4)     $(fsm_state|rjust:40)$(.path ~= detail ?$(history|show))))\n";
        leaf link_idx {
          type int64;
        }
        leaf link_id_str {
          type string;
          tailf:hidden "internal";
        }
        leaf phy_link {
          type string;
          tailf:hidden "internal";
        }
        leaf speed {
          type string;
          tailf:hidden "internal";
        }
        leaf stage {
          type string;
          tailf:hidden "internal";
        }
        leaf fab_plane {
          type uint32;
          tailf:hidden "internal";
        }
        leaf fab_group {
          type uint32;
          tailf:hidden "internal";
        }
        leaf flap_cnt {
          type uint32;
          tailf:hidden "internal";
        }
        leaf num_admin_shuts {
          type uint32;
          tailf:hidden "internal";
        }
        leaf admin-state {
          type string;
          tailf:hidden "internal";
        }
        leaf oper_state {
          type string;
          tailf:hidden "internal";
        }
        leaf flags {
          type string;
          tailf:hidden "internal";
        }
        leaf far_end_link_fsdb {
          type string;
          tailf:hidden "internal";
        }
        leaf far_end_link_hw {
          type string;
          tailf:hidden "internal";
        }
        leaf coeff1 {
          type uint32;
          tailf:hidden "internal";
        }
        leaf coeff2 {
          type uint32;
          tailf:hidden "internal";
        }
        leaf TX_Control_cells_counter {
          type uint64;
          tailf:hidden "internal";
        }
        leaf TX_Data_cell_counter {
          type uint64;
          tailf:hidden "internal";
        }
        leaf TX_Data_byte_counter {
          type uint64;
          tailf:hidden "internal";
        }
        leaf TX_BEC_retransmit {
          type uint64;
          tailf:hidden "internal";
        }
        leaf TX_Asyn_fifo_rate {
          type uint64;
          tailf:hidden "internal";
        }
        leaf RX_Control_cells_counter {
          type uint64;
          tailf:hidden "internal";
        }
        leaf RX_Data_cell_counter {
          type uint64;
          tailf:hidden "internal";
        }
        leaf RX_Data_byte_counter {
          type uint64;
          tailf:hidden "internal";
        }
        leaf RX_BEC_retransmit {
          type uint64;
          tailf:hidden "internal";
        }
        leaf RX_Asyn_fifo_rate {
          type uint64;
          tailf:hidden "internal";
        }
        leaf RX_CRC_errors_counter {
          type uint64;
          tailf:hidden "internal";
        }
        leaf RX_LFEC_FEC_correctable_error {
          type uint64;
          tailf:hidden "internal";
        }
        leaf RX_LFEC_FEC_uncorrectable_errors {
          type uint64;
          tailf:hidden "internal";
        }
        leaf RX_dropped_retransmitted_control {
          type uint64;
          tailf:hidden "internal";
        }
        leaf fsm_state {
          type string;
          tailf:hidden "internal";
        }
        list history {
          key "history_idx";
          tailf:cli-show-template-legend
            "
             +-----------------------------------------------------------------------------+
             | Timestamp                            Event(s)             Down Reasons      |
             +-----------------------------------------------------------------------------+
            ";
          tailf:cli-show-template "$(time_stamp|ljust:27) $(admin-state|ljust:10)$(oper_state|ljust:10)$(error_state|ljust:10)  $(down_reasons|ljust:12)\n";
          tailf:cli-suppress-table;
          tailf:cli-show-template-enter "";
          leaf history_idx {
            type int32;
          }
          leaf time_stamp {
            type string;
            tailf:hidden "internal";
          }
          leaf admin-state {
            type string;
            tailf:hidden "internal";
          }
          leaf oper_state {
            type string;
            tailf:hidden "internal";
          }
          leaf error_state {
            type string;
            tailf:hidden "internal";
          }
          leaf down_reasons {
            type string;
            tailf:hidden "internal";
          }
        }
      }
    }
  }

  grouping sfe_link_info_stats_asic_instance {
    container stats {
      container data {
        uses sfe_link_info_asic_instance;
      }
      container ctrl {
        uses sfe_link_info_asic_instance;
      }
      container all {
        uses sfe_link_info_asic_instance;
      }
    }
  }

  grouping sfe_statistics_asic_instance {
    list instance {
      key "instance-id";
      tailf:cli-no-key-completion;
      tailf:cli-no-match-completion;
      tailf:cli-suppress-table;
      tailf:cli-show-template-enter "$(stats_output)";
      leaf instance-id {
        type fabric-types:sfe_instance_type;
      }
      leaf stats_output {
        type string;
        tailf:hidden "internal";
      }
    }
  }

  grouping sfe_trace {
    container sfe_driver {
      tailf:cli-incomplete-show-path;
      tailf:cli-drop-node-name;
      uses show-trace:traceable;
    }
  }

  grouping sfe_parse_link_instance {
    list instance {
      key "instance-id";
      tailf:cli-no-key-completion;
      tailf:cli-no-match-completion;
      tailf:cli-show-template-enter "";
      tailf:cli-suppress-table;
      tailf:cli-show-template
        "$(is_show == true ?
         ----------------------------------------------------------------------------------------------------
         Rack    Slot     Asic       Link    Logical  Physical   FAP    Unit    SFI     IP Address    Driver     
                        Instance    Number     slot    slot      /FE           number   for driver    runs on    
         -------------------------------------------------------------------------------------------------------
         $(link_idx_list|show))";
      leaf instance-id {
        type fabric-types:sfe_instance_type;
      }
      leaf is_show {
        type boolean;
        tailf:hidden "internal";
      }
      list link_idx_list {
        key "link_idx";
        tailf:cli-suppress-table;
        tailf:cli-show-template-enter "";
        tailf:cli-show-template "$(rack_id_str|ljust:7) $(slot_id_str|ljust:10) $(asic_inst_id|ljust:8) $(link_num_id|ljust:8) $(log_slot|ljust:9) $(phy_slot|ljust:8) $(fap_id|ljust:8) $(unit|ljust:7) $(sfi_id|ljust:6) $(ip_addr|ljust:15) $(driver_run|ljust:6)\n";
        leaf link_idx {
          type int64;
        }
        leaf rack_id_str {
          type string;
          tailf:hidden "internal";
        }
        leaf slot_id_str {
          type string;
          tailf:hidden "internal";
        }
        leaf asic_inst_id {
          type uint32;
          tailf:hidden "internal";
        }
        leaf link_num_id {
          type uint32;
          tailf:hidden "internal";
        }
        leaf log_slot {
          type uint32;
          tailf:hidden "internal";
        }
        leaf phy_slot {
          type uint32;
          tailf:hidden "internal";
        }
        leaf fap_id {
          type uint32;
          tailf:hidden "internal";
        }
        leaf unit {
          type uint32;
          tailf:hidden "internal";
        }
        leaf sfi_id {
          type uint32;
          tailf:hidden "internal";
        }
        leaf ip_addr {
          type string;
          tailf:hidden "internal";
        }
        leaf driver_run {
          type string;
          tailf:hidden "internal";
        }
      }
    }
  }

  grouping sfe {
    container sfe {
      description
        "Fabric SFE driver commands";
      tailf:hidden "internal-command";
      tailf:info "Fabric SFE driver commands";
      tailf:cli-incomplete-show-path;
      container driver {
        tailf:callpoint "sfe_drvr_cp";
        tailf:hidden "internal-command";
        tailf:info "SFE driver information";
        tailf:cli-incomplete-show-path;
        list rack {
          key "rack_num";
          tailf:cli-show-template-enter "";
          tailf:cli-suppress-table;
          leaf rack_num {
            type fabric-types:fabric_rack_num_type;
          }
          leaf description {
            type string;
            default "rack no.";
          }
          uses sfe_drvr_info;
        }
      }
      container statistics {
        tailf:callpoint "sfe_statistics_cp";
        tailf:hidden "internal-command";
        list location {
          key "loc_str";
          tailf:cli-show-template-enter "";
          tailf:cli-suppress-table;
          leaf loc_str {
            type fabric-types:sfe_location_type;
          }
          leaf description {
            type string;
            default "location (R/S).";
          }
          list asic_types {
            key "asicname";
            tailf:cli-show-template-enter "";
            tailf:cli-suppress-table;
            tailf:cli-no-match-completion;
            tailf:cli-no-key-completion;
            leaf asicname {
              type string;
            }
            list block {
              key "blockname";
              tailf:cli-show-template-enter "";
              tailf:cli-suppress-table;
              tailf:cli-no-match-completion;
              tailf:cli-no-key-completion;
              leaf blockname {
                type string;
              }
              uses sfe_statistics_asic_instance;
            }
          }
        }
      }
      container link-info {
        tailf:callpoint "sfe_link_info_cp";
        tailf:info "Link Information";
        tailf:cli-incomplete-show-path;
        list location {
          key "loc_str";
          tailf:hidden "internal-command";
          tailf:cli-show-template-enter "";
          tailf:cli-suppress-table;
          leaf loc_str {
            type fabric-types:sfe_location_type;
          }
          leaf description {
            type string;
            default "location (R/S)";
          }
          list rx {
            key "start end";
            tailf:cli-no-key-completion;
            tailf:cli-no-match-completion;
            tailf:cli-show-template-enter "";
            tailf:cli-suppress-table;
            leaf start {
              type fabric-types:sfe_link_type;
            }
            leaf end {
              type fabric-types:sfe_link_type;
            }
            container detail {
              container topo {
                uses sfe_link_info_asic_instance;
              }
              container flap {
                uses sfe_link_info_asic_instance;
              }
            }
            container topo {
              uses sfe_link_info_asic_instance;
            }
            container flap {
              uses sfe_link_info_asic_instance;
            }
            uses sfe_link_info_stats_asic_instance;
          }
          list tx {
            key "start end";
            tailf:cli-no-key-completion;
            tailf:cli-no-match-completion;
            tailf:cli-show-template-enter "";
            tailf:cli-suppress-table;
            leaf start {
              type fabric-types:sfe_link_type;
            }
            leaf end {
              type fabric-types:sfe_link_type;
            }
            container detail {
              uses sfe_link_info_asic_instance;
            }
            uses sfe_link_info_asic_instance;
            uses sfe_link_info_stats_asic_instance;
          }
        }
      }
      container diagshell {
        tailf:hidden "internal-command";
        tailf:callpoint "sfe_diagshell_cmd";
        tailf:info "Diag shell cmd";
        tailf:cli-incomplete-show-path;
        list location {
          key "loc_str";
          tailf:cli-show-template-enter "";
          tailf:cli-suppress-table;
          leaf loc_str {
            type fabric-types:sfe_location_type;
          }
          leaf description {
            type string;
            default "location (R/S)";
            tailf:hidden "internal";
          }
          list instance {
            key "instance_num";
            tailf:cli-no-key-completion;
            tailf:cli-no-match-completion;
            tailf:cli-show-template-enter "";
            tailf:cli-suppress-table;
            leaf instance_num {
              type fabric-types:fabric_diag_shell_instance_num_type;
            }
            list diag_cmd {
              key "cmd_str";
              tailf:cli-no-key-completion;
              tailf:cli-no-match-completion;
              tailf:cli-show-template-enter "";
              tailf:cli-suppress-table;
              tailf:cli-show-template "$(bytes|show)";
              tailf:info "File name - double quote enclosed";
              leaf cmd_str {
                type fabric-types:fabric_diag_shell_cmd_type;
              }
              list bytes {
                key "byte_idx";
                tailf:cli-no-key-completion;
                tailf:cli-no-match-completion;
                tailf:cli-show-template-enter "";
                tailf:cli-suppress-table;
                tailf:cli-show-template "$(data)";
                leaf byte_idx {
                  type int64;
                }
                leaf data {
                  type string;
                  tailf:hidden "internal";
                }
              }
            }
          }
        }
      }
      container register {
        tailf:hidden "internal-command";
        tailf:callpoint "sfe_registers_cp";
        tailf:info "Dump the registers";
        tailf:cli-incomplete-show-path;
        list location {
          key "loc_str";
          tailf:cli-show-template-enter "";
          tailf:cli-suppress-table;
          leaf loc_str {
            type fabric-types:sfe_location_type;
          }
          leaf description {
            type string;
            default "location (R/S)";
            tailf:hidden "internal";
          }
          list instance {
            key "instance_num";
            tailf:cli-no-key-completion;
            tailf:cli-no-match-completion;
            tailf:cli-show-template-enter "";
            tailf:cli-suppress-table;
            leaf instance_num {
              type fabric-types:fabric_diag_shell_instance_num_type;
            }
            list bytes {
              key "byte_idx";
              tailf:cli-no-key-completion;
              tailf:cli-no-match-completion;
              tailf:cli-show-template-enter "";
              tailf:cli-suppress-table;
              tailf:cli-show-template "$(data)";
              leaf byte_idx {
                type int64;
              }
              leaf data {
                type string;
                tailf:hidden "internal";
              }
            }
          }
        }
      }
      container dump-file {
        tailf:hidden "internal-command";
        tailf:callpoint "sfe_dump_file";
        tailf:info "Dump file";
        tailf:cli-incomplete-show-path;
        list location {
          key "loc_str";
          tailf:cli-show-template-enter "";
          tailf:cli-suppress-table;
          leaf loc_str {
            type fabric-types:sfe_location_type;
          }
          leaf description {
            type string;
            default "location (R/S)";
            tailf:hidden "internal";
          }
          list file {
            key "file_name";
            tailf:cli-no-key-completion;
            tailf:cli-no-match-completion;
            tailf:cli-show-template-enter "";
            tailf:cli-suppress-table;
            tailf:cli-show-template "$(bytes|show)";
            tailf:info "File name - double quote enclosed";
            leaf file_name {
              type string;
            }
            list bytes {
              key "byte_idx";
              tailf:cli-no-key-completion;
              tailf:cli-no-match-completion;
              tailf:cli-show-template-enter "";
              tailf:cli-suppress-table;
              tailf:cli-show-template "$(data)";
              leaf byte_idx {
                type int64;
              }
              leaf data {
                type string;
                tailf:hidden "internal";
              }
            }
          }
        }
      }
      container parse {
        tailf:callpoint "sfe_parse_link_cp";
        tailf:info "Parse Link Information";
        tailf:cli-incomplete-show-path;
        list location {
          key "loc_str";
          tailf:hidden "internal-command";
          tailf:cli-show-template-enter "";
          tailf:cli-suppress-table;
          leaf loc_str {
            type fabric-types:sfe_location_type;
          }
          leaf description {
            type string;
            default "location (R/S)";
          }
          list link {
            key "start end";
            tailf:cli-no-key-completion;
            tailf:cli-no-match-completion;
            tailf:cli-show-template-enter "";
            tailf:cli-suppress-table;
            leaf start {
              type fabric-types:sfe_link_type;
            }
            leaf end {
              type fabric-types:sfe_link_type;
            }
            uses sfe_parse_link_instance;
          }
        }
      }
    }
    container sfe_trace {
      tailf:hidden "internal-command";
      uses sfe_trace;
    }
  }
  tailf:id "http://www.cisco.com/panini/calvados/fabric/sfe";
}
