module Cisco-IOS-XR-sysadmin-show-trace {
  namespace "http://www.cisco.com/ns/yang/Cisco-IOS-XR-sysadmin-show-trace";
  prefix show_trace;

  import tailf-common {
    prefix tailf;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains a collection of YANG
     definitions for Cisco IOS-XR SysAdmin configuration.
     
     Copyright(c) 2012-2017 by Cisco Systems, Inc.
     All rights reserved.";

  revision 2017-04-12 {
    description
      "Changed namespace and module name";
  }
  revision 2016-05-11 {
    description
      "Initial version.";
  }

  grouping traceable {
    list trace {
      key "buffer";
      config false;
      description
        "show traceable processes";
      tailf:cli-suppress-table;
      tailf:cli-show-template-enter "****";
      tailf:cli-suppress-show-match;
      tailf:cli-show-template "";
      tailf:info "Debug trace information";
      tailf:callpoint "debug_agent_show_trace";
      tailf:cli-incomplete-show-path;
      leaf buffer {
        type string;
        tailf:cli-incomplete-show-path;
      }
      list location {
        key "location_name";
        tailf:cli-suppress-table;
        tailf:cli-show-template-enter "----------------\n";
        tailf:cli-suppress-show-match;
        tailf:cli-incomplete-show-path {
          tailf:cli-min-keys "1";
        }
        leaf location_name {
          type string;
        }
        list all-options {
          key "option";
          tailf:cli-suppress-show-match;
          tailf:cli-drop-node-name;
          tailf:cli-suppress-table;
          tailf:cli-show-template-enter "";
          leaf option {
            type string;
          }
          list trace-blocks {
            tailf:cli-suppress-show-match;
            tailf:cli-suppress-table;
            tailf:cli-show-template-enter "";
            tailf:cli-show-template "$(data)";
            tailf:cli-suppress-show-path;
            leaf data {
              type string;
              description
                "Trace output block";
            }
          }
        }
      }
    }
  }

  grouping traceable_process {
    list instance {
      key "process_name";
      config false;
      description
        "show traceable process instance names";
      tailf:cli-suppress-table;
      tailf:cli-show-template-enter "**process**";
      tailf:cli-suppress-show-match;
      tailf:cli-show-template "";
      tailf:info "Select the process instance to get trace from";
      tailf:cli-incomplete-show-path;
      tailf:callpoint "debug_agent_show_trace_process";
      leaf process_name {
        type string;
        tailf:cli-incomplete-show-path;
      }
      list trace {
        key "buffer";
        config false;
        description
          "show traceable processes";
        tailf:cli-suppress-table;
        tailf:cli-show-template-enter "****";
        tailf:cli-suppress-show-match;
        tailf:cli-show-template "";
        tailf:info "Debug trace information";
        tailf:cli-incomplete-show-path;
        leaf buffer {
          type string;
          tailf:cli-incomplete-show-path;
        }
        list location {
          key "location_name";
          tailf:cli-suppress-table;
          tailf:cli-show-template-enter "----------------\n";
          tailf:cli-suppress-show-match;
          tailf:cli-incomplete-show-path {
            tailf:cli-min-keys "1";
          }
          leaf location_name {
            type string;
          }
          list all-options {
            key "option";
            tailf:cli-suppress-show-match;
            tailf:cli-drop-node-name;
            tailf:cli-suppress-table;
            tailf:cli-show-template-enter "";
            leaf option {
              type string;
            }
            list trace-blocks {
              tailf:cli-suppress-show-match;
              tailf:cli-suppress-table;
              tailf:cli-show-template-enter "";
              tailf:cli-show-template "$(data)";
              tailf:cli-suppress-show-path;
              leaf data {
                type string;
                description
                  "Trace output block";
              }
            }
          }
        }
      }
    }
  }

  grouping traceable_with_keypath_location {
    list trace {
      key "buffer";
      config false;
      tailf:info "Available trace buffers";
      tailf:cli-drop-node-name;
      tailf:cli-show-template-enter "";
      tailf:callpoint "debug_agent_show_trace";
      leaf buffer {
        type string;
      }
      list all-options {
        key "option";
        tailf:info "Trace display options";
        tailf:cli-drop-node-name;
        tailf:cli-show-template-enter "----------------\n";
        leaf option {
          type string;
        }
        list trace-blocks {
          tailf:cli-suppress-show-match;
          tailf:cli-suppress-show-path;
          tailf:cli-show-template-enter "";
          tailf:cli-show-template "$(data)";
          leaf data {
            type string;
          }
        }
      }
    }
  }
  tailf:id "http://cisco.com/calvados/show_trace";
}
