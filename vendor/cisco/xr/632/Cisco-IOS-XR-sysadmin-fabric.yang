module Cisco-IOS-XR-sysadmin-fabric {
  namespace "http://www.cisco.com/ns/yang/Cisco-IOS-XR-sysadmin-fabric";
  prefix fabric;

  import tailf-common {
    prefix tailf;
  }
  import Cisco-IOS-XR-sysadmin-fabric-mgr-fgid {
    prefix fabric-fgid;
  }
  import Cisco-IOS-XR-sysadmin-fabric-mgr-fsdb-server {
    prefix fabric-fsdb;
  }
  import Cisco-IOS-XR-sysadmin-fabric-mgr-fsdb-aggregator {
    prefix fabric-fsdb-aggr;
  }
  import Cisco-IOS-XR-sysadmin-fabric-driver-sfe {
    prefix fabric-sfe;
  }
  import Cisco-IOS-XR-sysadmin-fabric-cxp-ncs6k {
    prefix fabric-cxp;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains a collection of YANG
     definitions for Cisco IOS-XR SysAdmin configuration.
     
     This module defines CLI support of fabric components
     for ncs6k. 
     
     Copyright(c) 2011-2017 by Cisco Systems, Inc.
     All rights reserved.";

  revision 2017-06-15 {
    description
      "Split the file based on the platform";
  }
  revision 2017-05-01 {
    description
      "Namespace change to comply with Cisco guidelines on namespace";
  }

  grouping fabric_action_cmds {
    container fabric_action {
      tailf:cli-drop-node-name;
      tailf:cli-suppress-show-path;
      container fabric {
        description
          "Fabric resource commands";
        tailf:info "Fabric resource commands";
        tailf:cli-suppress-show-path;
        uses fabric-fsdb-aggr:fsdb_aggr_ppu;
      }
    }
  }

  grouping fabric_clear {
    container fabric {
      description
        "Fabric resource commands";
      tailf:info "Fabric resource commands";
      tailf:cli-incomplete-show-path;
      uses fabric-fsdb-aggr:fsdb_aggr_clear;
      uses fabric-fsdb:fsdb_svr_clear;
    }
  }

  grouping fabric {
    container fabric {
      description
        "Fabric resource commands";
      tailf:info "Fabric resource commands";
      tailf:cli-drop-node-name;
      container fabric {
        description
          "Fabric configuration";
        tailf:info "Fabric configuration";
        container fsdbagg {
          tailf:cli-drop-node-name;
          uses fabric-fsdb-aggr:fsdb_agg_conf_plane;
        }
        uses fabric-fgid:fgid_conf_resource;
      }
      container oper {
        config false;
        tailf:callpoint "fabric_oper";
        tailf:cli-incomplete-show-path;
        tailf:cli-drop-node-name;
        tailf:hidden "internal-command";
        uses fabric-cxp:fc_cxp_dom;
        uses fabric-fgid:fgid;
        uses fabric-fsdb-aggr:fsdb_aggr;
        uses fabric-fsdb:fsdb_svr;
      }
    }
    container sfe_oper {
      config false;
      tailf:callpoint "fabric_oper";
      tailf:cli-incomplete-show-path;
      tailf:cli-drop-node-name;
      uses fabric-sfe:sfe;
    }
  }
  tailf:id "http://www.cisco.com/panini/calvados/fabric";
}
