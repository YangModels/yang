module Cisco-IOS-XR-infra-sla-oper {
  namespace "http://cisco.com/ns/yang/Cisco-IOS-XR-infra-sla-oper";
  prefix infra-sla-oper;

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR infra-sla package operational data.
     
     This module contains definitions
     for the following management objects:
       sla: SLA oper commands
       sla-nodes: sla nodes
     
     Copyright (c) 2013-2017 by Cisco Systems, Inc.
     All rights reserved.";

  revision 2015-11-09 {
    description
      "IOS XR 6.0 revision.";
  }

  container sla {
    config false;
    description
      "SLA oper commands";
    container protocols {
      description
        "Table of all SLA protocols";
    }
  }
  container sla-nodes {
    config false;
    description
      "sla nodes";
  }
}
