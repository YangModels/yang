module Cisco-IOS-XR-sysadmin-types {
  namespace "http://www.cisco.com/ns/yang/Cisco-IOS-XR-sysadmin-types";
  prefix calvados_types;

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains definitions
     for the Calvados model objects.
     
     This module contains a collection of YANG
     definitions for Cisco IOS-XR SysAdmin configuration.
     
     This module contains a collection of derived 
     YANG data types specific to Sysadmin.
     
     Copyright(c) 2011-2016 by Cisco Systems, Inc.
     All rights reserved.
     
     Copyright (c) 2012-2017 by Cisco Systems, Inc.
     All rights reserved.";

  revision 2017-01-31 {
    description
      "Changed the namespace and module name";
  }

  typedef rack-id {
    type enumeration {
      enum "L0";
      enum "L1";
      enum "L2";
      enum "L3";
      enum "L4";
      enum "L5";
      enum "L6";
      enum "L7";
      enum "L8";
      enum "L9";
      enum "L10";
      enum "L11";
      enum "L12";
      enum "L13";
      enum "L14";
      enum "L15";
      enum "F0";
      enum "F1";
      enum "F2";
      enum "F3";
    }
    description
      "Identifies the rack number of FCC/LCC.
       LCC racks are identified by numbers rack0..7
       FCC racks are identified by numbers F0..F3";
  }

  typedef slot-id {
    type int32 {
      range "0..15";
    }
    description
      "Identifies a slot number within a rack";
  }

  typedef ce-portid {
    type string {
      pattern "(0?[0-9]|1[1-5]|F[0-3])/(0?[0-9]|1[1-5])/(0?[0-9]|[1-5][0-9])";
    }
  }

  typedef plane-id {
    type uint32 {
      range "0..7";
    }
    description
      "fabric plane identifier";
  }

  typedef sfe-id {
    type int32 {
      range "1..16";
    }
    description
      "falafel device identifier";
  }

  typedef adminstate {
    type enumeration {
      enum "disable";
    }
  }

  typedef generic-oper-status {
    type enumeration {
      enum "up";
      enum "down";
    }
  }

  typedef sfe-oper-state {
    type generic-oper-status;
  }

  typedef ce-oper-state {
    type generic-oper-status;
  }

  typedef generic-ha-role {
    type enumeration {
      enum "no-ha-role";
      enum "Active";
      enum "Standby";
    }
  }

  typedef fabric-link-types {
    type enumeration {
      enum "S1";
      enum "S2";
      enum "S3";
    }
  }

  typedef location-id {
    type string {
      pattern "((([fF][0-3])/(([a-zA-Z]){2}\\d{1,2}))|((0?[0-9]|1[1-5])/((([a-zA-Z]){2,3})?\\d{1,2})))(/[cC][pP][uU]0)?";
    }
    description
      "location identifier";
  }
}
