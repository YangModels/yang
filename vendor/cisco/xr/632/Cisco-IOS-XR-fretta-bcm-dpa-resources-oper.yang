module Cisco-IOS-XR-fretta-bcm-dpa-resources-oper {
  namespace "http://cisco.com/ns/yang/Cisco-IOS-XR-fretta-bcm-dpa-resources-oper";
  prefix fretta-bcm-dpa-resources-oper;

  import Cisco-IOS-XR-types {
    prefix xr;
  }
  include Cisco-IOS-XR-fretta-bcm-dpa-resources-oper-sub2 {
    revision-date 2015-11-09;
  }
  include Cisco-IOS-XR-fretta-bcm-dpa-resources-oper-sub1 {
    revision-date 2015-11-09;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR fretta-bcm-dpa-resources package operational data.
     
     This module contains definitions
     for the following management objects:
       dpa: Stats Data
     
     Copyright (c) 2013-2017 by Cisco Systems, Inc.
     All rights reserved.";

  revision 2015-11-09 {
    description
      "IOS XR 6.0 revision.";
  }

  typedef Max-trap-s {
    type uint32 {
      range "0..4294967295";
    }
    description
      "Max trap s";
  }

  typedef Max-lc-intf-hand-les {
    type uint32 {
      range "0..4294967295";
    }
    description
      "Max lc intf hand les";
  }

  typedef Dpa-table {
    type enumeration {
      enum "test-if" {
        value 0;
        description
          "test if";
      }
      enum "test-nhg" {
        value 1;
        description
          "test nhg";
      }
      enum "test-nh" {
        value 2;
        description
          "test nh";
      }
      enum "test-rt" {
        value 3;
        description
          "test rt";
      }
      enum "test-dynhg" {
        value 4;
        description
          "testdynhg";
      }
      enum "test-ip-punt-policy" {
        value 5;
        description
          "test ippuntpolicy";
      }
      enum "test-punt" {
        value 6;
        description
          "test punt";
      }
      enum "test-punt-policy-stats" {
        value 7;
        description
          "testpuntpolicystats";
      }
      enum "test-async-update" {
        value 8;
        description
          "testasyncupdate";
      }
      enum "test-ddel-q" {
        value 9;
        description
          "test ddel q";
      }
      enum "bdbvi" {
        value 10;
        description
          "bdbvi";
      }
      enum "sys" {
        value 11;
        description
          "sys";
      }
      enum "npu" {
        value 12;
        description
          "npu";
      }
      enum "npuhwid" {
        value 13;
        description
          "npuhwid";
      }
      enum "l1-port" {
        value 14;
        description
          "l1port";
      }
      enum "l2-port" {
        value 15;
        description
          "l2port";
      }
      enum "l2intf" {
        value 16;
        description
          "l2intf";
      }
      enum "mplspwe-port" {
        value 17;
        description
          "mplspweport";
      }
      enum "mhpwe-port" {
        value 18;
        description
          "mhpweport";
      }
      enum "l2xc" {
        value 19;
        description
          "l2xc";
      }
      enum "l2vpnstats" {
        value 20;
        description
          "l2vpnstats";
      }
      enum "l1-ports-tats" {
        value 21;
        description
          "l1portstats";
      }
      enum "l3intf" {
        value 22;
        description
          "l3intf";
      }
      enum "l3intfrxstats" {
        value 23;
        description
          "l3intfrxstats";
      }
      enum "ip-route" {
        value 24;
        description
          "iproute";
      }
      enum "ip6-route" {
        value 25;
        description
          "ip6route";
      }
      enum "punt-policy-stats" {
        value 26;
        description
          "puntpolicystats";
      }
      enum "ip-punt-policy" {
        value 27;
        description
          "ippuntpolicy";
      }
      enum "ip6-punt-policy" {
        value 28;
        description
          "ip6puntpolicy";
      }
      enum "isis-punt-policy" {
        value 29;
        description
          "isispuntpolicy";
      }
      enum "ipnh-group" {
        value 30;
        description
          "ipnhgroup";
      }
      enum "ip6nh-group" {
        value 31;
        description
          "ip6nhgroup";
      }
      enum "ipnh" {
        value 32;
        description
          "ipnh";
      }
      enum "ip6nh" {
        value 33;
        description
          "ip6nh";
      }
      enum "ipvrf" {
        value 34;
        description
          "ipvrf";
      }
      enum "mplsnh" {
        value 35;
        description
          "mplsnh";
      }
      enum "mpls-label" {
        value 36;
        description
          "mplslabel";
      }
      enum "dnx-trap" {
        value 37;
        description
          "dnx trap";
      }
      enum "punt" {
        value 38;
        description
          "punt";
      }
      enum "punt-police-r" {
        value 39;
        description
          "puntpolicer";
      }
      enum "punt-lpts-police-r" {
        value 40;
        description
          "puntlptspolicer";
      }
      enum "punt-stats" {
        value 41;
        description
          "puntstats";
      }
      enum "tm-port" {
        value 42;
        description
          "tmport";
      }
      enum "span-session" {
        value 43;
        description
          "spansession";
      }
      enum "police-rstats" {
        value 44;
        description
          "policerstats";
      }
      enum "tm-ports-tats" {
        value 45;
        description
          "tmportstats";
      }
      enum "l3intftxstats" {
        value 46;
        description
          "l3intftxstats";
      }
      enum "mplstetxstats" {
        value 47;
        description
          "mplstetxstats";
      }
      enum "mplslblstats" {
        value 48;
        description
          "mplslblstats";
      }
      enum "police-r" {
        value 49;
        description
          "policer";
      }
      enum "l2intfrxstats" {
        value 50;
        description
          "l2intfrxstats";
      }
      enum "l2intftxstats" {
        value 51;
        description
          "l2intftxstats";
      }
      enum "dnx-pbr-tt-ipv4" {
        value 52;
        description
          "dnx pbr tt ipv4";
      }
      enum "dnx-pbr-tt-ipv6" {
        value 53;
        description
          "dnx pbr tt ipv6";
      }
      enum "bfdhwoff" {
        value 54;
        description
          "bfdhwoff";
      }
      enum "global" {
        value 55;
        description
          "global";
      }
      enum "lag-port" {
        value 56;
        description
          "lagport";
      }
      enum "qos-profile" {
        value 57;
        description
          "qosprofile";
      }
      enum "tmrate-profile" {
        value 58;
        description
          "tmrateprofile";
      }
      enum "dnx-port-range" {
        value 59;
        description
          "dnx port range";
      }
      enum "ipacl" {
        value 60;
        description
          "ipacl";
      }
      enum "ip6acl" {
        value 61;
        description
          "ip6acl";
      }
      enum "sched-tree" {
        value 62;
        description
          "schedtree";
      }
      enum "tmcos" {
        value 63;
        description
          "tmcos";
      }
      enum "statsagg" {
        value 64;
        description
          "statsagg";
      }
      enum "nhprotect" {
        value 65;
        description
          "nhprotect";
      }
      enum "sampler" {
        value 66;
        description
          "sampler";
      }
      enum "l2qos" {
        value 67;
        description
          "l2qos";
      }
      enum "peer-qos" {
        value 68;
        description
          "peerqos";
      }
      enum "ipqos" {
        value 69;
        description
          "ipqos";
      }
      enum "ip6qos" {
        value 70;
        description
          "ip6qos";
      }
      enum "mplsqos" {
        value 71;
        description
          "mplsqos";
      }
      enum "qosid" {
        value 72;
        description
          "qosid";
      }
      enum "extlif" {
        value 73;
        description
          "extlif";
      }
      enum "elif" {
        value 74;
        description
          "elif";
      }
      enum "ingaclstats" {
        value 75;
        description
          "ingaclstats";
      }
      enum "egraclstats" {
        value 76;
        description
          "egraclstats";
      }
      enum "edpl" {
        value 77;
        description
          "edpl";
      }
      enum "cfmmaid" {
        value 78;
        description
          "cfmmaid";
      }
      enum "cfmdefmps" {
        value 79;
        description
          "cfmdefmps";
      }
      enum "cfmofflmep" {
        value 80;
        description
          "cfmofflmep";
      }
      enum "cfmoffrmep" {
        value 81;
        description
          "cfmoffrmep";
      }
      enum "cfmnonoff" {
        value 82;
        description
          "cfmnonoff";
      }
      enum "cfmhwoffrxstats" {
        value 83;
        description
          "cfmhwoffrxstats";
      }
      enum "ipmc-route" {
        value 84;
        description
          "ipmcroute";
      }
      enum "l2ipmc-route" {
        value 85;
        description
          "l2ipmcroute";
      }
      enum "ipmco-list" {
        value 86;
        description
          "ipmcolist";
      }
      enum "l2mco-list" {
        value 87;
        description
          "l2mcolist";
      }
      enum "ipmc-merge-do-list" {
        value 88;
        description
          "ipmcmergedolist";
      }
      enum "sgfgid-list" {
        value 89;
        description
          "sgfgidlist";
      }
      enum "meshmc" {
        value 90;
        description
          "meshmc";
      }
      enum "l2-bridge" {
        value 91;
        description
          "l2bridge";
      }
      enum "l2-bridge-port" {
        value 92;
        description
          "l2bridgeport";
      }
      enum "l2-bridge-mac" {
        value 93;
        description
          "l2bridgemac";
      }
      enum "l2brmac" {
        value 94;
        description
          "l2brmac";
      }
      enum "ip-tunnel-decap" {
        value 95;
        description
          "iptunneldecap";
      }
      enum "l2vlan-range" {
        value 96;
        description
          "l2vlanrange";
      }
      enum "ip-tunnel-encap" {
        value 97;
        description
          "iptunnelencap";
      }
      enum "rawget" {
        value 98;
        description
          "rawget";
      }
      enum "ip6mc-route" {
        value 99;
        description
          "ip6mcroute";
      }
      enum "l2evpnact-remote-peer-id" {
        value 100;
        description
          "l2evpnactremotepeerid";
      }
      enum "l2evpnact-local-shl" {
        value 101;
        description
          "l2evpnactlocalshl";
      }
      enum "l2evpnact-remote-shl" {
        value 102;
        description
          "l2evpnactremoteshl";
      }
      enum "evpn-iml-range" {
        value 103;
        description
          "evpn imlrange";
      }
      enum "l2-bridge-o-list" {
        value 104;
        description
          "l2bridgeolist";
      }
      enum "l2acl" {
        value 105;
        description
          "l2acl";
      }
      enum "l2evpn-nh" {
        value 106;
        description
          "l2evpn nh";
      }
      enum "l2-bridge-port-sc" {
        value 107;
        description
          "l2bridgeport sc";
      }
      enum "l3intfmctxstats" {
        value 108;
        description
          "l3intfmctxstats";
      }
      enum "tidl-sample" {
        value 109;
        description
          "tidl sample";
      }
      enum "tidl-ref-sample" {
        value 110;
        description
          "tidl ref sample";
      }
      enum "ipacl-prefix" {
        value 111;
        description
          "ipaclprefix";
      }
      enum "ip6acl-prefix" {
        value 112;
        description
          "ip6aclprefix";
      }
      enum "ipacl-port" {
        value 113;
        description
          "ipaclport";
      }
      enum "scaleacl" {
        value 114;
        description
          "scaleacl";
      }
      enum "ipmcf-hop" {
        value 115;
        description
          "ipmcfhop";
      }
      enum "bundle-swoff" {
        value 116;
        description
          "bundle swoff";
      }
      enum "mcidswoff" {
        value 117;
        description
          "mcidswoff";
      }
      enum "dest-map" {
        value 118;
        description
          "destmap";
      }
      enum "l2-bridge-port-pw" {
        value 119;
        description
          "l2bridgeport pw";
      }
      enum "l2evpnact-local-shlstats" {
        value 120;
        description
          "l2evpnactlocalshlstats";
      }
      enum "test-hidden" {
        value 121;
        description
          "testhidden";
      }
      enum "test-local" {
        value 122;
        description
          "testlocal";
      }
      enum "test-repeated" {
        value 123;
        description
          "testrepeated";
      }
      enum "limd" {
        value 124;
        description
          "limd";
      }
      enum "litap" {
        value 125;
        description
          "litap";
      }
      enum "test-xtf" {
        value 126;
        description
          "test xtf";
      }
      enum "ipmcrxstats" {
        value 127;
        description
          "ipmcrxstats";
      }
    }
    description
      "Dpa table";
  }

  container dpa {
    config false;
    description
      "Stats Data";
    container resources {
      description
        "DPA Resources Data";
      container nodes {
        description
          "DPA data for available nodes";
        list node {
          key "node-name";
          description
            "DPA operational data for a particular node";
          container table-datas {
            description
              "DPA Resources table";
            list table-data {
              key "resource";
              description
                "DPA Resources table";
              leaf resource {
                type Dpa-table;
                description
                  "Resource type";
              }
              uses DPA-SYSDB-TABLE-RESOURCE;
            }
          }
          leaf node-name {
            type xr:Node-id;
            description
              "Node ID";
          }
        }
      }
    }
    container stats {
      description
        "Voq or Trap Data";
      container nodes {
        description
          "DPA data for available nodes";
        list node {
          key "node-name";
          description
            "DPA operational data for a particular node";
          container asic-statistics {
            description
              "ASIC statistics table";
            container asic-statistics-for-npu-ids {
              description
                "ASIC statistics";
              list asic-statistics-for-npu-id {
                key "npu-id";
                description
                  "ASIC statistics for a particular NPU";
                leaf npu-id {
                  type int32;
                  description
                    "NPU number";
                }
                uses FIA-EDM-STATS-BRIEF-INFO;
              }
            }
            container asic-statistics-detail-for-npu-ids {
              description
                "Detailed ASIC statistics";
              list asic-statistics-detail-for-npu-id {
                key "npu-id";
                description
                  "Detailed ASIC statistics for a particular
                   NPU";
                leaf npu-id {
                  type int32;
                  description
                    "NPU number";
                }
                uses FIA-EDM-STATS-INFO;
              }
            }
          }
          container npu-numbers {
            description
              "Ingress Stats";
            list npu-number {
              key "npu-id";
              description
                "Stats for a particular npu";
              container display {
                description
                  "show npu specific voq or trap stats";
                container base-numbers {
                  description
                    "Voq stats grouped by voq base numbers";
                  list base-number {
                    key "base-number";
                    description
                      "Voq Base Number for a particular voq";
                    leaf base-number {
                      type Max-lc-intf-hand-les;
                      description
                        "Interface handle";
                    }
                    uses DPA-VOQ-INTF-PORT;
                  }
                }
                container trap-ids {
                  description
                    "Trap stats for a particular npu";
                  list trap-id {
                    key "trap-id";
                    description
                      "Filter by specific trap id";
                    leaf trap-id {
                      type Max-trap-s;
                      description
                        "Trap ID";
                    }
                    uses DPA-TRAP-STATS;
                  }
                }
                container interface-handles {
                  description
                    "Voq stats grouped by interface handle";
                  list interface-handle {
                    key "interface-handle";
                    description
                      "Voq stats for a particular interface
                       handle";
                    leaf interface-handle {
                      type Max-lc-intf-hand-les;
                      description
                        "Interface Handle";
                    }
                    uses DPA-VOQ-INTF-PORT;
                  }
                }
              }
              leaf npu-id {
                type int32;
                description
                  "Npu number";
              }
            }
          }
          leaf node-name {
            type xr:Node-id;
            description
              "Node ID";
          }
        }
      }
    }
  }
}
