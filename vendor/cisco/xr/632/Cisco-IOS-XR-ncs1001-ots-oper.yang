module Cisco-IOS-XR-ncs1001-ots-oper {
  namespace "http://cisco.com/ns/yang/Cisco-IOS-XR-ncs1001-ots-oper";
  prefix ncs1001-ots-oper;

  include Cisco-IOS-XR-ncs1001-ots-oper-sub1 {
    revision-date 2018-01-23;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ncs1001-ots package operational data.
     
     This module contains definitions
     for the following management objects:
       hw-module: ncs1001 hw-module command chain
     
     Copyright (c) 2013-2018 by Cisco Systems, Inc.
     All rights reserved.";

  revision 2018-01-23 {
    description
      "first release.";
  }
  revision 2015-11-09 {
    description
      "IOS XR 6.0 revision.";
  }

  typedef Ots-ampli-trail-data {
    type enumeration {
      enum "all" {
        value 1;
        description
          "Displays Booster and Pre trail data";
      }
      enum "bst" {
        value 2;
        description
          "Displays Booster trail data";
      }
      enum "pre" {
        value 3;
        description
          "Displays Pre trail data";
      }
    }
    description
      "Ots ampli trail data";
  }

  typedef Ots-channels-trail-data {
    type enumeration {
      enum "all" {
        value 1;
        description
          "Displays all channels trail data";
      }
      enum "active" {
        value 2;
        description
          "Displays active channels trail data";
      }
    }
    description
      "Ots channels trail data";
  }

  container hw-module {
    config false;
    description
      "ncs1001 hw-module command chain";
    container slot-tables {
      description
        "Amplifier trail data information";
      list slot-table {
        key "slot-id";
        description
          "Slot Id";
        leaf slot-id {
          type int32;
          description
            "Details associated with a particular slot
             number";
        }
        list amplifier-trail-data {
          key "amplifier-trail-data-type";
          description
            "Trail data information";
          leaf amplifier-trail-data-type {
            type Ots-ampli-trail-data;
            description
              "Select trail data";
          }
          uses OTS-HWMOD-OP;
        }
      }
    }
    container channels-slots {
      description
        "Channels trail data information";
      list channels-slot {
        key "slot-id";
        description
          "Slot Id";
        leaf slot-id {
          type uint32 {
            range "1..3";
          }
          description
            "Details associated with a particular slot
             number";
        }
        list channels-trail-data {
          key "channels-trail-data-type";
          description
            "Trail data information";
          leaf channels-trail-data-type {
            type Ots-channels-trail-data;
            description
              "Select trail data";
          }
          uses OTS-HWMOD-OP;
        }
      }
    }
  }
}
