module Cisco-IOS-XR-sysadmin-fpd-infra-cli-fpd {
  namespace "http://www.cisco.com/ns/yang/Cisco-IOS-XR-sysadmin-fpd-infra-cli-fpd";
  prefix fpd;

  import tailf-common {
    prefix tailf;
  }

  description
    "FPD CLI support for both oper and config";

  revision 2017-05-01 {
    description
      "Namespace change to comply with Cisco guidelines on namespace";
  }
  revision 2011-12-03 {
    description
      "Initial revision.";
  }

  grouping fpd {
    container config {
      description
        "fpd config mode";
      tailf:cli-drop-node-name;
      uses global-fpd-config-group;
    }
  }

  grouping global-fpd-config-group {
    leaf auto-upgrade {
      type enumeration {
        enum "enable";
        enum "disable";
      }
      default "disable";
      config true;
      tailf:info "enable/disable auto fpd upgrade";
    }
  }
  tailf:id "http://cisco.com/calvados/fpd";

  container fpd {
    tailf:info "FPD upgrade commands";
    uses fpd;
  }
}
