submodule Cisco-IOS-XR-mpls-te-oper-sub3 {
  belongs-to Cisco-IOS-XR-mpls-te-oper {
    prefix Cisco-IOS-XR-mpls-te-oper;
  }

  import ietf-inet-types {
    prefix inet;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR mpls-te package operational data.
     
     Copyright (c) 2013-2017 by Cisco Systems, Inc.
     All rights reserved.";

  revision 2017-05-01 {
    description
      "Fixing backward compatibility error in module.";
  }
  revision 2015-11-09 {
    description
      "IOS XR 6.0 revision.";
  }

  typedef Tp-link-state {
    type enumeration {
      enum "down" {
        description
          "TP link state is down";
      }
      enum "admin-down" {
        description
          "TP link state is administratively down";
      }
      enum "up" {
        description
          "TP link state is up";
      }
      enum "unknown" {
        description
          "TP link state is unknown";
      }
    }
    description
      "Transport profile link state";
  }

  grouping MPLS-TE-TP-LINK-INFO {
    description
      "Transport profile link information";
    leaf link-id {
      type uint32;
      description
        "Transport profile link identifier";
    }
    leaf interface {
      type string;
      description
        "Transport profile link interface name";
    }
    leaf next-hop-address {
      type inet:ipv4-address;
      description
        "Transport profile next-hop in IPv4 address
         format";
    }
    leaf link-state {
      type Tp-link-state;
      description
        "Link state";
    }
    leaf available-bandwidth {
      type uint64;
      units "kbit/s";
      description
        "Available bandwidth in Kbps";
    }
  }

  grouping MPLS-TE-TP-LINK-SUMMARY-INFO {
    description
      "Transport profile link summary";
    leaf links {
      type uint32;
      description
        "Number of transport profile links";
    }
  }

  grouping MPLS-TE-TP-DETAIL-LINK-INFO {
    description
      "Transport profile link detail information";
    leaf link-id {
      type uint32;
      description
        "Transport profile link identifier";
    }
    leaf interface {
      type string;
      description
        "Transport profile link interface name";
    }
    leaf next-hop-address {
      type inet:ipv4-address;
      description
        "Transport profile next-hop in IPv4 address
         format";
    }
    leaf link-state {
      type Tp-link-state;
      description
        "Link State";
    }
    leaf ls-ps {
      type uint32;
      description
        "Number of TP LSPs on this TP link";
    }
    leaf reserved-bandwidth {
      type uint64;
      units "kbit/s";
      description
        "Reserved bandwidth in Kbps";
    }
    leaf available-bandwidth {
      type uint64;
      units "kbit/s";
      description
        "Available bandwidth in Kbps";
    }
    leaf unsupported-linecard {
      type boolean;
      description
        "Link is hosted on a linecard that does not
         support MPLS-TP";
    }
  }
}
