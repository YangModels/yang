module Cisco-IOS-XR-sysadmin-sdm-diag {
  namespace "http://cisco.com/calvados/diagnostics";
  prefix diagnostics_actions;

  import tailf-common {
    prefix tailf;
  }

  organization
    "Cisco Systems Inc.";

  revision 2017-03-21 {
    description
      "Added completion point to location and testid
       Suppressed the range using cli-suppress-range";
  }
  revision 2012-08-03 {
    description
      "output string formatting using cli";
  }

  typedef Location {
    type string;
    tailf:info "WORD ;; Fully qualified location specification";
  }

  typedef Test {
    type string;
    description
      "Enter the test Name";
    tailf:info
      "Test Name or ALL ;; Enter Name of the test 
                                               / Select all tests";
  }

  typedef Individual_test {
    type string;
    description
      "Enter the test Name";
    tailf:info "Test Name ;; Enter Name of the test";
  }

  typedef Type_int32 {
    type int32;
    description
      "Enter the value ";
    tailf:info "Enter The value ";
  }

  typedef Hour_Minute {
    type string {
      pattern "([01]?[0-9]|2[0-3]):[0-5][0-9]";
      tailf:info
        "00:00 to 23:59 ;; Enter the hour and minute in 
                                                   hh:mm format";
    }
  }

  container diagnostic {
    tailf:info "Online diagnostic commands";
    container monitor {
      tailf:info "Configure diagnostic monitoring tests";
      container rejected {
        tailf:validate "diag_validate" {
          tailf:dependency ".";
        }
        tailf:cli-drop-node-name;
        list location {
          key "loc";
          tailf:info "Select location";
          tailf:cli-no-key-completion;
          leaf loc {
            type Location;
            tailf:cli-completion-actionpoint "location-complete";
            tailf:cli-suppress-range;
          }
          list test {
            key "test_id run";
            tailf:info "Select a test name";
            tailf:cli-no-key-completion;
            leaf test_id {
              type Individual_test;
              tailf:cli-completion-actionpoint "test_name-complete";
              tailf:cli-suppress-range;
            }
            leaf run {
              type enumeration {
                enum "disable" {
                  value 1;
                }
              }
              tailf:info "Set Disable of the test";
              tailf:cli-drop-node-name;
              tailf:cli-suppress-range;
            }
          }
        }
      }
      container interval {
        tailf:validate "diag_validate" {
          tailf:dependency ".";
        }
        tailf:info "Configure diagnostic monitoring tests interval";
        list location {
          key "loc";
          tailf:info "Select location";
          tailf:cli-no-key-completion;
          leaf loc {
            type Location;
            tailf:cli-suppress-range;
            tailf:cli-completion-actionpoint "location-complete";
          }
          list test {
            key "test_id";
            tailf:info "Select a test name";
            tailf:cli-no-key-completion;
            tailf:cli-full-no;
            leaf test_id {
              type Individual_test;
              tailf:cli-suppress-range;
              tailf:cli-completion-actionpoint "test_name-complete";
            }
            leaf days {
              type int32 {
                range "0..20";
                tailf:info "0 to 20 ;; Number of days";
              }
              mandatory true;
              tailf:info "Enter number of days  0 to 20";
              tailf:validate "validate_interval" {
                tailf:dependency ".";
              }
            }
            leaf time {
              type string {
                pattern "([01]?[0-9]|2[0-3]):[0-5][0-9]:[0-5][0-9]";
                tailf:info
                  "00:00:00 to 23:59:59 ;; Time 
                   information in hh:mm:ss format. Ex. For 
                   5 second, [00:00:05]";
              }
              mandatory true;
              tailf:validate "validate_interval" {
                tailf:dependency ".";
              }
              tailf:info
                "Time information in hh:mm:ss format. 
                         Ex. For 5 seconds, [00:00:05]";
            }
          }
        }
      }
      container threshold {
        tailf:validate "diag_validate" {
          tailf:dependency ".";
        }
        tailf:info "Configure diagnostic monitoring failure threshold";
        list location {
          key "loc";
          tailf:info "Select location";
          tailf:cli-no-key-completion;
          leaf loc {
            type Location;
            tailf:cli-completion-actionpoint "location-complete";
            tailf:cli-suppress-range;
          }
          list test {
            key "test_id";
            tailf:info "Select a test name";
            tailf:cli-no-key-completion;
            leaf test_id {
              type Individual_test;
              tailf:cli-suppress-range;
              tailf:cli-completion-actionpoint "test_name-complete";
            }
            leaf failure-count {
              type int32 {
                range "1..99";
                tailf:info "1 to 99 ;; Enter the Threshold ";
              }
              mandatory true;
              tailf:info "Setting failure threshold count";
            }
          }
        }
      }
    }
    container schedule {
      tailf:info "Configure diagnostic schedule for a card";
      container start {
        tailf:validate "diag_validate" {
          tailf:dependency ".";
        }
        list location {
          key "loc";
          tailf:info "Select location";
          tailf:cli-no-key-completion;
          leaf loc {
            type Location;
            tailf:cli-completion-actionpoint "location-complete";
            tailf:cli-suppress-range;
          }
          list test {
            key "test_id";
            tailf:info "Select a test name";
            tailf:cli-no-key-completion;
            leaf test_id {
              type Individual_test;
              tailf:cli-suppress-range;
              tailf:cli-completion-actionpoint "test_name-complete";
            }
            list daily {
              key "hour_min";
              tailf:info "Daily schedule";
              tailf:cli-no-key-completion;
              leaf hour_min {
                type Hour_Minute;
                tailf:cli-suppress-range;
              }
            }
            list on {
              key "month day_of_month year hour_min";
              tailf:info "Absolute schedule";
              tailf:cli-no-key-completion;
              tailf:cli-suppress-key-sort;
              tailf:validate "validate_date" {
                tailf:dependency ".";
              }
              leaf month {
                type enumeration {
                  enum "JAN";
                  enum "FEB";
                  enum "MAR";
                  enum "APR";
                  enum "MAY";
                  enum "JUN";
                  enum "JUL";
                  enum "AUG";
                  enum "SEP";
                  enum "OCT";
                  enum "NOV";
                  enum "DEC";
                }
                tailf:cli-suppress-range;
                tailf:info "Enter the month to start the test";
              }
              leaf day_of_month {
                type int32 {
                  range "1..31";
                  tailf:info
                    "1 - 31 ;; Enter date in the 
                         month to start the test ";
                }
                tailf:cli-suppress-range;
              }
              leaf year {
                type int32 {
                  range "2013..2099";
                  tailf:info "2013 - 2099 ;; Enter year";
                }
                tailf:cli-suppress-range;
              }
              leaf hour_min {
                type Hour_Minute;
                tailf:cli-suppress-range;
              }
            }
            list weekly {
              key "daysofweek hour_min";
              tailf:info "Weekly schedule";
              tailf:cli-suppress-key-sort;
              tailf:cli-no-key-completion;
              leaf daysofweek {
                type enumeration {
                  enum "SUN";
                  enum "MON";
                  enum "TUE";
                  enum "WED";
                  enum "THR";
                  enum "FRI";
                  enum "SAT";
                }
                tailf:cli-suppress-range;
                tailf:info "Enter the day in the week";
              }
              leaf hour_min {
                type Hour_Minute;
                tailf:cli-suppress-range;
              }
            }
          }
        }
      }
    }
    container status {
      config false;
      tailf:callpoint "diag_status";
      tailf:info "show diagnostic status";
      list location_index {
        key "data_idx";
        tailf:info "to populate the location index";
        tailf:cli-suppress-table;
        tailf:cli-show-template-enter "";
        tailf:cli-show-template
          "
           $(description|ljust:11) $(curr_running_tst_runby)
           ---------------------------------------------------------------------------
          ";
        tailf:cli-show-template-legend
          "
           <BU> - Bootup Diagnostics,   <HM>   - Health Monitoring Diagnostics,
           <OD> - OnDemand Diagnostics, <SCHD> - Scheduled Diagnostics
           ===========================================================================
           Location    Current Running Test  Status                             Run by
           ---------------------------------------------------------------------------";
        leaf data_idx {
          type int32;
        }
        leaf description {
          type string;
          tailf:hidden "internal";
        }
        leaf curr_running_tst_runby {
          type string;
          tailf:hidden "internal";
        }
      }
    }
    container diag_start {
      config false;
      tailf:cli-drop-node-name;
      tailf:hidden "internal-command";
      tailf:callpoint "diag_ondemand_cli_cp";
      tailf:info "Show diagnostic start";
      list location {
        key "loc";
        leaf loc {
          type Location;
        }
        leaf description {
          type string;
          default "port.";
        }
        list test {
          key "test_type";
          leaf test_type {
            type Test;
          }
          leaf description {
            type string;
            default "Test.";
          }
          tailf:action "start" {
            tailf:actionpoint "diagnostic_start";
            tailf:info "Diagnostic Start command";
            input;
            output {
              leaf response_str {
                type string;
                tailf:cli-drop-node-name;
              }
            }
          }
        }
      }
    }
    container diag_stop {
      config false;
      tailf:cli-drop-node-name;
      tailf:hidden "internal-command";
      tailf:callpoint "diag_ondemand_cli_cp";
      tailf:info "Show diagnostic stop";
      list location {
        key "loc";
        leaf loc {
          type Location;
        }
        leaf description {
          type string;
          default "port.";
        }
        list test {
          key "test_type";
          leaf test_type {
            type Test;
          }
          leaf description {
            type string;
            default "Test.";
          }
          tailf:action "stop" {
            tailf:actionpoint "diagnostic_stop";
            tailf:info "Diagnostic Stop command";
            input;
          }
        }
      }
    }
    container content {
      config false;
      tailf:callpoint "show_diag_content";
      tailf:info "show diagnostic content";
      tailf:hidden "internal-command";
      list location {
        key "loc";
        leaf loc {
          type Location;
        }
        leaf description {
          type string;
          default "port.";
        }
        list data_list {
          key "data_idx";
          tailf:cli-suppress-table;
          tailf:cli-show-template-enter "";
          tailf:cli-show-template
            "
             $(id|ljust:4) $(test_name|ljust:34) $(attribute|ljust:12)  $(timeinfo|ljust:17)  $(threshold|ljust)
            ";
          tailf:cli-show-template-legend
            "
             Diagnostics test suite attributes: 
             M/C/* - Minimal bootup level test / Complete bootup level test / NA
             B/*   - Basic ondemand test / NA 
             P/V/* - Per port test / Per device test / NA 
             D/N/* - Disruptive test / Non-disruptive test / NA 
             S/*   - Only applicable to standby unit / NA 
             X/*   - Not a health monitoring test / NA 
             F/*   - Fixed monitoring interval test / NA 
             E/*   - Always enabled monitoring test / NA 
             A/I   - Monitoring is active / Monitoring is inactive 
             
                                                                  Test Interval     thre-  
             ID   Test Name                          Attributes   (day hh:mm:ss)    shold  
             ==== ================================== ============ ================= =====  
            ";
          leaf data_idx {
            type int32;
          }
          leaf id {
            type int32;
            description
              "To display the test information";
            tailf:hidden "internal";
          }
          leaf test_name {
            type string;
            tailf:hidden "internal";
          }
          leaf attribute {
            type string;
            tailf:hidden "internal";
          }
          leaf timeinfo {
            type string;
            tailf:hidden "internal";
          }
          leaf threshold {
            type int32;
            tailf:hidden "internal";
          }
        }
      }
    }
    container result {
      config false;
      tailf:callpoint "show_diag_result";
      tailf:info "show diagnostic result";
      tailf:hidden "internal-command";
      list location {
        key "loc";
        tailf:cli-show-template-enter
          "
           Diag Information For : ";
        tailf:cli-no-key-completion;
        tailf:cli-no-match-completion;
        leaf loc {
          type Location;
        }
        leaf description {
          type string;
          default "port.";
        }
        list test {
          key "test_type";
          leaf test_type {
            type Test;
            description
              "test name|all";
          }
          leaf description {
            type string;
            default "port.";
          }
          list detail {
            key "det";
            tailf:cli-drop-node-name;
            leaf det {
              type string;
            }
            list data_list {
              key "data_idx";
              tailf:cli-suppress-table;
              tailf:cli-show-template-enter "";
              tailf:cli-show-template
                "$(sl_no)) $(test_name) -------> $(test_result)$(detail_flag==1?
                 Error code ------------------> $(err_code) $(err_description)
                 Test type -------------------> $(test_type)
                 HM test count ---------------> $(hm_test_count)
                 ONDEMAND test count ---------> $(od_test_count)
                 SCHED test count ------------> $(sched_test_count)
                 Total run count -------------> $(run_cnt)
                 Last test execution time ----> $(lt_exe_time)First test failure time -----> $(ft_fail_time)Last test failure time ------> $(lt_fail_time)Last test pass time ---------> $(lt_pass_time)Total failure count ---------> $(total_fail_cnt)
                 Consecutive failure count ---> $(cons_fail_cnt)
                 Additional information ------> $(more_info)
                 ___________________________________________________________________________)
                 
                ";
              tailf:cli-show-template-legend
                "
                 
                 Test results: (P = Pass, F = Fail, U = Untested, T = Timedout, A = Aborted, S = Stopped)
                 ___________________________________________________________________________
                 
                ";
              leaf data_idx {
                type int32;
              }
              leaf detail_flag {
                type int32;
                tailf:hidden "internal";
              }
              leaf sl_no {
                type int32;
                tailf:hidden "internal";
              }
              leaf test_name {
                type string;
                tailf:hidden "internal";
              }
              leaf test_result {
                type string;
                tailf:hidden "internal";
              }
              leaf err_code {
                type int32;
                tailf:hidden "internal";
              }
              leaf err_description {
                type string;
                tailf:hidden "internal";
              }
              leaf test_type {
                type string;
                tailf:hidden "internal";
              }
              leaf hm_test_count {
                type int32;
                tailf:hidden "internal";
              }
              leaf od_test_count {
                type int32;
                tailf:hidden "internal";
              }
              leaf sched_test_count {
                type int32;
                tailf:hidden "internal";
              }
              leaf run_cnt {
                type int32;
                tailf:hidden "internal";
              }
              leaf lt_exe_time {
                type string;
                tailf:hidden "internal";
              }
              leaf ft_fail_time {
                type string;
                tailf:hidden "internal";
              }
              leaf lt_fail_time {
                type string;
                tailf:hidden "internal";
              }
              leaf lt_pass_time {
                type string;
                tailf:hidden "internal";
              }
              leaf total_fail_cnt {
                type int32;
                tailf:hidden "internal";
              }
              leaf cons_fail_cnt {
                type int32;
                tailf:hidden "internal";
              }
              leaf more_info {
                type string;
                tailf:hidden "internal";
              }
            }
          }
        }
      }
    }
  }
}
