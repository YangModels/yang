module Cisco-IOS-XR-sysadmin-cm {
  namespace "http://www.cisco.com/ns/yang/Cisco-IOS-XR-sysadmin-cm";
  prefix cmh;

  import tailf-common {
    prefix tailf;
  }
  import tailf-xsd-types {
    prefix xs;
  }
  import Cisco-IOS-XR-sysadmin-types {
    prefix calvados;
  }
  import ietf-yang-types {
    prefix yang;
  }
  import ietf-inet-types {
    prefix inet;
  }
  import Cisco-IOS-XR-sysadmin-show-trace-cm {
    prefix cm;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains a collection of YANG
     definitions for Cisco IOS-XR SysAdmin configuration.
     
     The System Admin Manager (CM)
     
     Copyright(c) 2010-2017 by Cisco Systems, Inc.
     All rights reserved.";

  revision 2017-04-12 {
    description
      "Changed the namespace and module name";
  }
  revision 2016-05-11 {
    description
      "Initial version";
  }

  typedef area_type {
    type enumeration {
      enum "SYSTEM";
      enum "RACK";
      enum "UNKNOWN";
    }
  }

  typedef hex8ValueType {
    type xs:hexBinary {
      tailf:value-length "8";
    }
  }

  grouping nodeInfoGroup {
    container summary {
      config false;
      description
        "System Admin Manager Node Inventory. All accesses are 
         read-only. CLI show command looks like show node-inventory
         location <location>";
      tailf:info "Show System Admin Manager node inventory";
      tailf:callpoint "nodei";
      list node_locations {
        key "node_location";
        tailf:cli-drop-node-name;
        tailf:cli-enforce-table;
        leaf node_location {
          type calvados:location-id;
          tailf:alt-name "location";
          tailf:display-column-name "Location";
          tailf:cli-expose-key-name;
          tailf:cli-allow-range;
        }
        list nodei {
          key "ip_address";
          tailf:cli-drop-node-name;
          tailf:cli-no-key-completion;
          uses nodeInfoSummary;
        }
      }
    }
    container detail {
      config false;
      description
        "System Admin Manager Node Inventory. All accesses are 
         read-only. CLI show command looks like show node-inventory
         location <location>";
      tailf:info "Show System Admin Manager node inventory";
      tailf:callpoint "noded";
      list node_locations {
        key "node_location";
        tailf:cli-drop-node-name;
        tailf:cli-enforce-table;
        leaf node_location {
          type calvados:location-id;
          tailf:alt-name "location";
          tailf:display-column-name "Location";
          tailf:cli-expose-key-name;
        }
        list nodei {
          key "ip_address";
          tailf:cli-drop-node-name;
          tailf:cli-no-key-completion;
          uses nodeInfoSummary;
          uses nodeInfoDetail;
        }
      }
    }
  }

  grouping nodeInfoSummary {
    description
      "All the parameters needed to describe a node as
       represented in CM.";
    leaf type {
      type string;
      description
        "Node Type";
      tailf:display-column-name "Type";
      tailf:cli-column-width "8";
      tailf:cli-suppress-show-path;
      tailf:cli-suppress-show-match;
    }
    leaf ip_address {
      type inet:ip-address;
      description
        "IP address of the node";
      tailf:display-column-name "IP Address";
      tailf:cli-suppress-show-path;
      tailf:cli-suppress-show-match;
    }
    leaf mac_address {
      type yang:mac-address;
      description
        "Node MAC";
      tailf:display-column-name "MAC Address";
      tailf:cli-suppress-show-path;
      tailf:cli-suppress-show-match;
    }
    leaf card_serial {
      type string;
      description
        "Card serial# the node belongs to";
      tailf:display-column-name "Card Serial";
      tailf:cli-column-width "11";
      tailf:cli-suppress-show-path;
      tailf:cli-suppress-show-match;
    }
    leaf nti {
      type uint32;
      description
        "Node NTI";
      tailf:display-column-name "NTI";
      tailf:cli-column-width "4";
      tailf:cli-suppress-show-path;
      tailf:cli-suppress-show-match;
    }
  }

  grouping nodeInfoDetail {
    description
      "All the parameters needed to describe a node as
       represented in CM.";
    leaf restart {
      type boolean;
      description
        "Node in Restart";
      tailf:display-column-name "Restart";
      tailf:cli-column-width "7";
      tailf:cli-suppress-show-path;
      tailf:cli-suppress-show-match;
    }
    leaf data {
      type hex8ValueType;
      description
        "Node Data";
      tailf:display-column-name "Node Data";
      tailf:cli-column-width "16";
      tailf:cli-suppress-show-path;
      tailf:cli-suppress-show-match;
    }
    leaf sdr {
      type string;
      description
        "SDR Name the node belongs to";
      tailf:cli-suppress-show-path;
      tailf:cli-suppress-show-match;
    }
  }

  grouping cardInfo {
    description
      "All the parameters needed to describe a card as
       represented in CM.";
    leaf node_id {
      type string;
      description
        "Node name";
      tailf:display-column-name "Node Id";
      tailf:cli-suppress-show-path;
      tailf:cli-suppress-show-match;
    }
    leaf card_type {
      type string;
      description
        "Card Type";
      tailf:display-column-name "Type";
      tailf:cli-suppress-show-path;
      tailf:cli-suppress-show-match;
    }
    leaf hw_state {
      type string;
      description
        "Card State";
      tailf:display-column-name "HW state";
      tailf:cli-suppress-show-path;
      tailf:cli-suppress-show-match;
    }
    leaf sw_state {
      type string;
      description
        "Card Software State";
      tailf:display-column-name "SW state";
      tailf:cli-suppress-show-path;
      tailf:cli-suppress-show-match;
    }
    leaf slot {
      type uint32;
      description
        "Card Slot Number";
      tailf:display-column-name "Slot";
      tailf:cli-suppress-show-path;
      tailf:cli-suppress-show-match;
    }
    leaf card_serial {
      type string;
      description
        "Serial Number of the Card";
      tailf:display-column-name "Card Serial";
      tailf:cli-suppress-show-path;
      tailf:cli-suppress-show-match;
    }
    leaf cti {
      type uint32;
      description
        "Card CTI";
      tailf:display-column-name "CTI";
      tailf:cli-suppress-show-path;
      tailf:cli-suppress-show-match;
    }
  }

  grouping rackInfo {
    description
      "All the parameters needed to describe a rack as
       represented in CM.";
    leaf rack_number {
      type int32;
      description
        "Rack Number";
      tailf:display-column-name "Rack Number";
      tailf:cli-suppress-show-path;
      tailf:cli-suppress-show-match;
    }
    leaf rack_serial {
      type string;
      description
        "Serial Number of the Rack";
      tailf:display-column-name "Rack Serial";
      tailf:cli-suppress-show-path;
      tailf:cli-suppress-show-match;
    }
    leaf rack_state {
      type int32;
      description
        "Rack State";
      tailf:display-column-name "State";
      tailf:cli-suppress-show-path;
      tailf:cli-suppress-show-match;
    }
  }

  grouping serviceInfo {
    description
      "All the parameters needed to describe a service as
       represented in CM.";
    leaf svc_name {
      type string;
      description
        "Service Name";
      tailf:display-column-name "Service Name";
      tailf:cli-suppress-show-path;
      tailf:cli-suppress-show-match;
    }
    leaf placement_first {
      type string;
      description
        "Serial Number of the first card selected";
      tailf:display-column-name "Card Serial";
      tailf:cli-suppress-show-path;
      tailf:cli-suppress-show-match;
    }
    leaf nodeid_first {
      type string;
      description
        "Node id of the first card selected";
      tailf:display-column-name "Node Id";
      tailf:cli-suppress-show-path;
      tailf:cli-suppress-show-match;
    }
    leaf placement_second {
      type string;
      description
        "Serial Number of the second card selected";
      tailf:display-column-name "Card Serial";
      tailf:cli-suppress-show-path;
      tailf:cli-suppress-show-match;
    }
    leaf nodeid_second {
      type string;
      description
        "Node id of the second card selected";
      tailf:display-column-name "Node Id";
      tailf:cli-suppress-show-path;
      tailf:cli-suppress-show-match;
    }
    leaf svc_load {
      type uint8;
      description
        "Service Load";
      tailf:display-column-name "Load";
      tailf:cli-suppress-show-path;
      tailf:cli-suppress-show-match;
    }
  }

  grouping sdrInfo {
    description
      "All the parameters needed to describe a SDR as
       represented in CM.";
    leaf sdr_id {
      type uint32;
      description
        "SDR ID";
      tailf:display-column-name "Id";
      tailf:cli-suppress-show-path;
      tailf:cli-suppress-show-match;
    }
    leaf sdr_name {
      type string;
      description
        "SDR NAME";
      tailf:display-column-name "Name";
      tailf:cli-suppress-show-path;
      tailf:cli-suppress-show-match;
    }
    leaf sdr_vlan_baseid {
      type uint8;
      description
        "SDR VLAN ID";
      tailf:display-column-name "VLAN Id";
      tailf:cli-suppress-show-path;
      tailf:cli-suppress-show-match;
    }
    leaf sdr_version {
      type uint64;
      description
        "SDR Image Version";
      tailf:display-column-name "Version";
      tailf:cli-suppress-show-path;
      tailf:cli-suppress-show-match;
    }
  }

  grouping ldrInfo {
    description
      "All the parameters needed to describe leader statistics.";
    leaf syslead {
      type string;
      description
        "Primary System Leader";
      tailf:cli-suppress-show-path;
      tailf:cli-suppress-show-match;
    }
    leaf bkup_syslead {
      type string;
      description
        "Backup System Leader";
      tailf:cli-suppress-show-path;
      tailf:cli-suppress-show-match;
    }
    leaf racklead {
      type string;
      description
        "Primary Rack Leader";
      tailf:cli-suppress-show-path;
      tailf:cli-suppress-show-match;
    }
    leaf bkup_racklead {
      type string;
      description
        "Backup Rack Leader";
      tailf:cli-suppress-show-path;
      tailf:cli-suppress-show-match;
    }
    leaf l1_dis {
      type string;
      description
        "L1 DIS";
      tailf:cli-suppress-show-path;
      tailf:cli-suppress-show-match;
    }
    leaf l2_dis {
      type string;
      description
        "L2 DIS";
      tailf:cli-suppress-show-path;
      tailf:cli-suppress-show-match;
    }
  }

  grouping nbrInfo {
    description
      "All the parameters needed to describe a topology neighbor";
    leaf nbr_system_id {
      type string;
      description
        "Neighbor System ID";
      tailf:cli-suppress-show-path;
      tailf:cli-suppress-show-match;
      tailf:display-column-name "System ID";
    }
    leaf nbr_area_type {
      type string;
      description
        "Neighbor Area Type";
      tailf:cli-suppress-show-path;
      tailf:cli-suppress-show-match;
      tailf:display-column-name "Level";
    }
    leaf nbr_interface {
      type string;
      description
        "Adjacency Interface";
      tailf:cli-suppress-show-path;
      tailf:cli-suppress-show-match;
      tailf:display-column-name "Interface";
    }
    leaf nbr_state {
      type string;
      description
        "Neighbor State";
      tailf:cli-suppress-show-path;
      tailf:cli-suppress-show-match;
      tailf:display-column-name "State";
    }
    leaf nbr_holdtime {
      type uint64;
      description
        "Neighbor Hold Time";
      tailf:cli-suppress-show-path;
      tailf:cli-suppress-show-match;
      tailf:display-column-name "Holdtime";
    }
    leaf nbr_uptime {
      type xs:duration;
      description
        "Neighbor Up Time";
      tailf:cli-suppress-show-path;
      tailf:cli-suppress-show-match;
      tailf:display-column-name "Uptime";
    }
  }

  grouping lspdbInfo {
    description
      "All the parameters needed to describe a lsps from lspdb";
    leaf lsp_id {
      type string;
      description
        "LSP System ID";
      tailf:cli-drop-node-name;
    }
    leaf lsp_area_type {
      type area_type;
      description
        "LSP Area Type";
      tailf:cli-drop-node-name;
    }
    leaf lsp_sequence {
      type uint32;
      description
        "LSP sequence number";
      tailf:cli-suppress-show-path;
      tailf:cli-suppress-show-match;
    }
    leaf lsp_core {
      type string;
      description
        "LSP core data bits";
      tailf:cli-suppress-show-path;
      tailf:cli-suppress-show-match;
    }
    leaf-list lsp_tlvs {
      type string;
      description
        "LSP TLV data";
      tailf:cli-suppress-show-path;
      tailf:cli-suppress-show-match;
      tailf:display-column-name "TLV Data";
      tailf:cli-drop-node-name;
      tailf:cli-list-syntax;
      tailf:cli-flat-list-syntax;
    }
  }

  augment "/cm:cm" {
    container lsp {
      config false;
      description
        "System Admin Manager lspdb of a location";
      tailf:info "Show cm lsp database";
      tailf:callpoint "lspdbi";
      list lspdb_locations {
        key "lspdb_location";
        tailf:cli-drop-node-name;
        tailf:cli-suppress-table;
        tailf:cli-show-template-enter
          "
           LSP Update database for : $(lspdb_location)
          ";
        leaf lspdb_location {
          type calvados:location-id;
          tailf:alt-name "location";
          tailf:cli-expose-key-name;
        }
        list lspdbi {
          key "lsp_id lsp_area_type";
          tailf:cli-drop-node-name;
          tailf:cli-suppress-table;
          tailf:cli-show-template-legend " ";
          tailf:cli-show-template-enter " ";
          tailf:cli-no-key-completion;
          tailf:cli-show-template
            "----------------------------------------------------------------------
             LSP Id\\\\: $(lsp_id)      Scope \\\\: $(lsp_area_type)
             Sequence Num\\\\: $(lsp_sequence)                      $(lsp_core)
             TLV code  length          Data
             $(lsp_tlvs|show:noalign)
            ";
          uses lspdbInfo;
        }
      }
    }
  }
  tailf:id "http://cisco.com/calvados/cm";

  container node-inventory {
    config false;
    description
      "System Admin Manager Node Inventory. All accesses are 
       read-only. CLI show command looks like show node-inventory
       location <location>";
    tailf:info "Show System Admin Manager node inventory";
    uses nodeInfoGroup;
  }
  container card-inventory {
    config false;
    description
      "System Admin Manager Card Inventory. All accesses are 
       read-only. CLI show command looks like show card-inventory
       location <location>";
    tailf:info "Show System Admin Manager card inventory";
    tailf:callpoint "cardi";
    list card_locations {
      key "card_location";
      tailf:cli-drop-node-name;
      tailf:cli-enforce-table;
      leaf card_location {
        type calvados:location-id;
        tailf:alt-name "location";
        tailf:cli-expose-key-name;
        tailf:display-column-name "Location";
        tailf:cli-allow-range;
      }
      list cardi {
        key "card_serial";
        tailf:cli-no-key-completion;
        tailf:cli-drop-node-name;
        uses cardInfo;
      }
    }
  }
  container rack-inventory {
    config false;
    description
      "System Admin Manager Rack Inventory";
    tailf:info "Show System Admin Manager rack inventory";
    tailf:callpoint "racki";
    list rack_locations {
      key "rack_location";
      tailf:cli-drop-node-name;
      tailf:cli-enforce-table;
      leaf rack_location {
        type calvados:location-id;
        tailf:alt-name "location";
        tailf:display-column-name "Location";
        tailf:cli-expose-key-name;
      }
      list racki {
        key "rack_serial";
        tailf:cli-no-key-completion;
        tailf:cli-drop-node-name;
        uses rackInfo;
      }
    }
  }
  container system-service-inventory {
    config false;
    description
      "System Admin Manager System Services Inventory";
    tailf:info "Show System Admin Manager system-services inventory";
    tailf:callpoint "ssvci";
    list ssvc_locations {
      key "ssvc_location";
      tailf:cli-drop-node-name;
      tailf:cli-enforce-table;
      leaf ssvc_location {
        type calvados:location-id;
        tailf:alt-name "location";
        tailf:display-column-name "Location";
        tailf:cli-expose-key-name;
      }
      list ssvci {
        key "svc_name";
        tailf:cli-no-key-completion;
        tailf:cli-drop-node-name;
        uses serviceInfo;
      }
    }
  }
  container rack-service-inventory {
    config false;
    description
      "System Admin Manager Rack Services Inventory";
    tailf:info "Show System Admin Manager rack-services inventory";
    tailf:callpoint "rsvci";
    list rsvc_locations {
      key "rsvc_location";
      tailf:cli-drop-node-name;
      tailf:cli-enforce-table;
      leaf rsvc_location {
        type calvados:location-id;
        tailf:alt-name "location";
        tailf:display-column-name "Location";
        tailf:cli-expose-key-name;
      }
      list rsvci {
        key "svc_name";
        tailf:cli-no-key-completion;
        tailf:cli-drop-node-name;
        tailf:cli-suppress-table;
        uses serviceInfo;
      }
    }
  }
  container sdr-inventory {
    config false;
    description
      "System Admin Manager SDR Inventory";
    tailf:info "Show System Admin Manager SDR inventory";
    tailf:callpoint "sdri";
    list sdr_locations {
      key "sdr_location";
      tailf:cli-drop-node-name;
      tailf:cli-enforce-table;
      leaf sdr_location {
        type calvados:location-id;
        tailf:alt-name "location";
        tailf:display-column-name "Location";
        tailf:cli-expose-key-name;
      }
      list sdri {
        key "sdr_name";
        tailf:cli-no-key-completion;
        tailf:cli-drop-node-name;
        tailf:cli-suppress-table;
        uses sdrInfo;
      }
    }
  }
  container leader-statistics {
    config false;
    description
      "System Admin Manager Leader Statistics";
    tailf:info "Show System Admin Manager Leader Election Information";
    tailf:callpoint "ldri";
    list ldr_locations {
      key "ldr_location";
      tailf:cli-drop-node-name;
      tailf:cli-suppress-table;
      tailf:cli-show-template
        " Service Name      Mac               IP Address   Node
          -------------------------------------------------------
          System Lead       $(syslead)
          Backup Sys Lead   $(bkup_syslead)
          Rack Lead         $(racklead)
          Backup Rack Lead  $(bkup_racklead)
          L1 DIS            $(l1_dis)
          L2 DIS            $(l2_dis)
        ";
      leaf ldr_location {
        type calvados:location-id;
        tailf:alt-name "location";
        tailf:cli-expose-key-name;
      }
      uses ldrInfo;
    }
  }
  container topology-neighbors {
    config false;
    description
      "System Admin Manager Neighbors of a location";
    tailf:info "Show topology neighbors";
    tailf:callpoint "nbri";
    list nbr_locations {
      key "nbr_location";
      tailf:cli-drop-node-name;
      tailf:cli-enforce-table;
      leaf nbr_location {
        type calvados:location-id;
        tailf:alt-name "location";
        tailf:display-column-name "Location";
        tailf:cli-expose-key-name;
      }
      list nbri {
        key "nbr_system_id nbr_area_type";
        tailf:cli-no-key-completion;
        tailf:cli-drop-node-name;
        tailf:cli-suppress-table;
        uses nbrInfo;
      }
    }
  }
  container placement {
    tailf:action "reoptimize" {
      tailf:actionpoint "reoptimize-point";
      description
        "Reoptimize Placement for System Scope Services";
    }
  }
}
