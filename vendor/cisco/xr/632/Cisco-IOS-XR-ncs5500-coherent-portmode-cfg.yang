module Cisco-IOS-XR-ncs5500-coherent-portmode-cfg {
  namespace "http://cisco.com/ns/yang/Cisco-IOS-XR-ncs5500-coherent-portmode-cfg";
  prefix ncs5500-coherent-portmode-cfg;

  import Cisco-IOS-XR-ifmgr-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ncs5500-coherent-portmode package configuration.
     
     This YANG module augments the
       Cisco-IOS-XR-ifmgr-cfg
     module with configuration data.
     
     Copyright (c) 2013-2017 by Cisco Systems, Inc.
     All rights reserved.";

  revision 2015-11-09 {
    description
      "IOS XR 6.0 revision.";
  }

  typedef Diff-sel {
    type enumeration {
      enum "disable" {
        value 0;
        description
          "disable differential";
      }
      enum "enable" {
        value 1;
        description
          "enable differential";
      }
    }
    description
      "Diff sel";
  }

  typedef Fec-sel {
    type enumeration {
      enum "15percent" {
        value 0;
        description
          "FEC 15";
      }
      enum "25percent" {
        value 1;
        description
          "FEC 25";
      }
    }
    description
      "Fec sel";
  }

  typedef Speed-sel {
    type enumeration {
      enum "100g" {
        value 100000000;
        description
          "Speed 100";
      }
      enum "150g" {
        value 150000000;
        description
          "Speed 150";
      }
      enum "200g" {
        value 200000000;
        description
          "Speed 200";
      }
    }
    description
      "Speed sel";
  }

  augment "/a1:interface-configurations/a1:interface-configuration" {
    description
      "This augment extends the configuration data of
       'Cisco-IOS-XR-ifmgr-cfg'";
    container portmode {
      description
        "Configure through port-mode";
      leaf speed-sel {
        type Speed-sel;
        description
          "Select speed";
      }
      leaf fec-sel {
        type Fec-sel;
        description
          "Select Fec";
      }
      leaf diff-sel {
        type Diff-sel;
        description
          "Select Diff";
      }
    }
  }
}
