module Cisco-IOS-XR-sysadmin-tacacs-tacacs-server {
  namespace "http://www.cisco.com/ns/yang/Cisco-IOS-XR-sysadmin-tacacs-tacacs-server";
  prefix tacacs-server;

  import tailf-common {
    prefix tailf;
  }
  import ietf-inet-types {
    prefix inet;
  }

  organization
    "Cisco Systems";
  contact
    "aaa-ng-tacacs-dev@cisco.com";
  description
    "This module defines the TACACS+ data model.";

  revision 2017-05-10 {
    description
      "Namespace changed from tacacs to Cisco-IOS-XR-sysadmin-tacacs-tacacs-server";
  }
  revision 2015-06-06 {
    description
      "Initial creation";
  }

  typedef passwdStr {
    type tailf:aes-cfb-128-encrypted-string;
    tailf:info "TACACS+ server secret";
  }
  tailf:id "http://cisco.com/calvados/tacacs";

  container tacacs-server {
    tailf:info "TACACS+ Server";
    list host {
      key "ip port";
      max-elements "10";
      ordered-by user;
      tailf:info "Host information";
      tailf:callpoint "data_tacacs_server" {
        tailf:transaction-hook "object";
      }
      tailf:validate "val_tacacs_server" {
        tailf:dependency ".";
      }
      leaf ip {
        type inet:ip-address;
        tailf:info "Server IPv4 address";
      }
      leaf port {
        type inet:port-number {
          range "1 .. 65535";
        }
        tailf:info "Server Port";
      }
      leaf timeout {
        type uint32 {
          range "1 .. 1000";
        }
        tailf:info "Server Timeout";
      }
      leaf key {
        type passwdStr;
        tailf:info "Server Key";
      }
    }
    leaf timeout {
      type uint32 {
        range "1 .. 1000";
      }
      tailf:info "Server Timeout";
    }
    leaf key {
      type passwdStr;
      tailf:info "Server Key";
    }
  }
}
