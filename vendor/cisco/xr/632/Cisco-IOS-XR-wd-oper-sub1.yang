submodule Cisco-IOS-XR-wd-oper-sub1 {
  belongs-to Cisco-IOS-XR-wd-oper {
    prefix Cisco-IOS-XR-wd-oper;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR wd package operational data.
     
     Copyright (c) 2013-2017 by Cisco Systems, Inc.
     All rights reserved.";

  revision 2015-11-09 {
    description
      "IOS XR 6.0 revision.";
  }

  typedef Overload-ctrl-notif {
    type enumeration {
      enum "disabled" {
        description
          "Diabled";
      }
      enum "enabled" {
        description
          "Enabled";
      }
    }
    description
      "Overload control notification";
  }

  typedef Memory-state {
    type enumeration {
      enum "unknown" {
        value 0;
        description
          "Memory state unknown";
      }
      enum "normal" {
        value 1;
        description
          "Memory state normal";
      }
      enum "minor" {
        value 2;
        description
          "Memory state minor";
      }
      enum "severe" {
        value 3;
        description
          "Memory state severe";
      }
      enum "critical" {
        value 4;
        description
          "Memory state critical";
      }
    }
    description
      "Memory state options";
  }

  grouping LAST-THR-INFO {
    description
      "Last throttle details";
    leaf throttle-duration {
      type uint32;
      units "second";
      description
        "Last throttle duration in seconds";
    }
    leaf start-time {
      type string {
        length "0..25";
      }
      description
        "Last throttle start time in format :day-of-week
         month date-of-month HH:MM:SS year eg: Thu Feb 1
         18:32:14 2011";
    }
    leaf stop-time {
      type string {
        length "0..25";
      }
      description
        "Last throttle stop time in format :day-of-week
         month date-of-month HH:MM:SS year eg: Thu Feb 1
         18:32:14 2011";
    }
  }

  grouping CUR-THR-INFO {
    description
      "Current throttle details";
    leaf throttle-duration {
      type uint32;
      units "second";
      description
        "Current throttle duration in seconds";
    }
    leaf start-time {
      type string {
        length "0..25";
      }
      description
        "Current throttle start time in format 
         :day-of-week month date-of-month HH:MM:SS year
         eg: Thu Feb 1 18:32:14 2011";
    }
  }

  grouping OVERLOAD-CONTROL {
    description
      "Overload control state information";
    container current-throttle {
      description
        "Current throttle information";
      uses CUR-THR-INFO;
    }
    leaf overload-control-notification {
      type Overload-ctrl-notif;
      description
        "State of overload control notification";
    }
    leaf default-wdsysmon-throttle {
      type uint32;
      description
        "Default resmon throttle";
    }
    leaf configured-wdsysmon-throttle {
      type uint32;
      description
        "Configured resmon throttle";
    }
    list last-throttle {
      max-elements "20";
      description
        "Last throttle information";
      uses LAST-THR-INFO;
    }
  }

  grouping MEMORY-DETAILS {
    description
      "Memory information";
    leaf physical-memory {
      type uint32;
      units "byte";
      description
        "Physical memory in bytes";
    }
    leaf free-memory {
      type uint64;
      units "byte";
      description
        "Free memory in bytes";
    }
    leaf memory-state {
      type Memory-state;
      description
        "State of memory";
    }
  }

  grouping CONF-MEM-THRESHOLD {
    description
      "Configured memory threshold";
    leaf minor {
      type uint32;
      units "byte";
      description
        "Minor memory threshold in bytes";
    }
    leaf severe {
      type uint32;
      units "byte";
      description
        "Severe memory threshold in bytes";
    }
    leaf critical {
      type uint64;
      units "byte";
      description
        "Critical memory in bytes";
    }
  }

  grouping MEMORY-THRESHOLD {
    description
      "Memory threshold";
    container configured-memory {
      description
        "Configured memory";
      uses CONF-MEM-THRESHOLD;
    }
    container memory {
      description
        "Memory Information";
      uses MEMORY-DETAILS;
    }
  }
}
