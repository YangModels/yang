module Cisco-IOS-XR-sysadmin-hw-module {
  namespace "http://www.cisco.com/ns/yang/Cisco-IOS-XR-sysadmin-hw-module";
  prefix calvados_hw_module;

  import tailf-common {
    prefix tailf;
  }
  import Cisco-IOS-XR-sysadmin-sm-hw-mod {
    prefix shelf_mgr;
  }
  import Cisco-IOS-XR-sysadmin-led-mgr-ui {
    prefix led_mgr;
  }
  import Cisco-IOS-XR-sysadmin-fpd-infra-cli-shhwfpd {
    prefix shhwfpd;
  }
  import Cisco-IOS-XR-sysadmin-obfl-conf {
    prefix obflconf;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains a collection of YANG
     definitions for Cisco IOS-XR SysAdmin configuration.
     
     This module defines the top level container for
     all 'hw-module' commands for Sysadmin.
     
     Copyright(c) 2012-2017 by Cisco Systems, Inc.
     All rights reserved.";

  revision 2017-01-31 {
    description
      "Changed the namespace and module name";
  }
  revision 2012-07-03 {
    description
      "Created initial 'hw-module' refactorization";
  }
  tailf:id "http://cisco.com/panini/calvados/calvados_hw_module";

  container hw-module {
    tailf:info "Hardware Module commands";
    tailf:cli-incomplete-show-path;
    container config {
      config true;
      tailf:cli-drop-node-name;
      uses shelf_mgr:hw-module-config-group;
      uses led_mgr:hw-module-config-group;
      uses obflconf:hw-module-config-group;
    }
    container oper {
      config false;
      tailf:cli-drop-node-name;
      tailf:callpoint "hw_module";
      list location {
        key "location";
        tailf:info "Location of hardware module";
        tailf:cli-incomplete-show-path;
        leaf location {
          type string;
          tailf:info "Hardware module location";
        }
        container actions {
          tailf:cli-drop-node-name;
          uses shelf_mgr:hw-module-action-group;
        }
        container show {
          tailf:cli-drop-node-name;
        }
      }
    }
    uses shhwfpd:hw-module-oper-group;
  }
}
