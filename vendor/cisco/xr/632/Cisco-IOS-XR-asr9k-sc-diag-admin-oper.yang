module Cisco-IOS-XR-asr9k-sc-diag-admin-oper {
  namespace "http://cisco.com/ns/yang/Cisco-IOS-XR-asr9k-sc-diag-admin-oper";
  prefix asr9k-sc-diag-admin-oper;

  import Cisco-IOS-XR-types {
    prefix xr;
  }
  include Cisco-IOS-XR-asr9k-sc-diag-admin-oper-sub1 {
    revision-date 2015-11-09;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR asr9k-sc-diag package
     admin-plane operational data.
     
     This module contains definitions
     for the following management objects:
       diag: Diag admin operational data
     
     Copyright (c) 2013-2017 by Cisco Systems, Inc.
     All rights reserved.";

  revision 2015-11-09 {
    description
      "IOS XR 6.0 revision.";
  }

  container diag {
    config false;
    description
      "Diag admin operational data";
    container racks {
      description
        "Diag operational data for available racks";
      list rack {
        key "rack-name";
        description
          "Diag operational data for a particular rack";
        container fan-traies {
          description
            "Fan tray table operational data";
          list fan-tray {
            key "fan-tray-name";
            description
              "Fan tray operational data";
            container detail {
              description
                "Diag detailed information";
              uses DIAG-DETAIL;
            }
            leaf fan-tray-name {
              type xr:Cisco-ios-xr-string;
              description
                "Fan tray name";
            }
          }
        }
        container power-supplies {
          description
            "Power supply table operational data";
          list power-supply {
            key "power-supply-name";
            description
              "Power supply operational data";
            container detail {
              description
                "Diag detailed information";
              uses DIAG-DETAIL;
            }
            leaf power-supply-name {
              type xr:Cisco-ios-xr-string;
              description
                "Power supply name";
            }
          }
        }
        container slots {
          description
            "Diag operational data for all available slots";
          list slot {
            key "slot-name";
            description
              "Diag operational data for a particular slot";
            container detail {
              description
                "Slot detailed information";
              uses DIAG-SLOT-DETAIL;
            }
            container instances {
              description
                "Diag operational data for all available
                 instances";
              list instance {
                key "instance-name";
                description
                  "Diag operational data for a particular
                   instance";
                container detail {
                  description
                    "Diag detailed information";
                  uses DIAG-DETAIL;
                }
                leaf instance-name {
                  type xr:Cisco-ios-xr-string;
                  description
                    "Instance name";
                }
              }
            }
            leaf slot-name {
              type xr:Cisco-ios-xr-string;
              description
                "Slot name";
            }
          }
        }
        container chassis {
          description
            "Chassis information";
          uses DIAG-CHASSIS;
        }
        container summary {
          description
            "Summary information";
          uses DIAG-SUMMARY;
        }
        leaf rack-name {
          type int32;
          description
            "Rack name";
        }
      }
    }
  }
}
