module Cisco-IOS-XR-sysadmin-show-trace-vmm {
  namespace "http://www.cisco.com/ns/yang/Cisco-IOS-XR-sysadmin-show-trace-vmm";
  prefix vm_managerh;

  import tailf-common {
    prefix tailf;
  }
  import Cisco-IOS-XR-sysadmin-show-trace {
    prefix show_trace;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains a collection of YANG
     definitions for Cisco IOS-XR SysAdmin configuration.
     
     Copyright(c) 2012-2017 by Cisco Systems, Inc.
     All rights reserved.";

  revision 2017-04-12 {
    description
      "Changed the namespace and module name";
  }
  revision 2016-05-12 {
    description
      "Initial Version";
  }
  tailf:id "http://cisco.com/calvados/vm_manager";

  container vmm {
    config false;
    tailf:cdb-oper;
    tailf:cli-incomplete-show-path;
    tailf:info "Show VM Manager information";
    container vm_manager {
      tailf:cli-show-template "";
      tailf:cli-drop-node-name;
      uses show_trace:traceable;
    }
  }
}
