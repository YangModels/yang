module Cisco-IOS-XR-sysadmin-led-mgr-ui {
  namespace "http://www.cisco.com/ns/yang/Cisco-IOS-XR-sysadmin-led-mgr-ui";
  prefix led_mgr;

  import tailf-common {
    prefix tailf;
  }
  import Cisco-IOS-XR-sysadmin-show-trace {
    prefix show_trace;
  }

  organization
    "Cisco Systems Inc.";
  description
    "This module provides CLI for Status, ATTN, ALARM LED's.";

  revision 2017-05-01 {
    description
      "Namespace change to comply with Cisco guidelines on namespace";
  }
  revision 2012-03-25 {
    description
      "changed leds to location, and added all";
  }
  revision 2012-03-15 {
    description
      "Initial revision of led commands, march 25 changed leds to
       location";
  }

  grouping hw-module-config-group {
    uses hw-module-attention-led-config-group;
  }

  grouping hw-module-attention-led-config-group {
    container attention-led {
      tailf:info "Enable attention LED (Blue) ON";
      list location {
        key "location";
        tailf:info "R/S;; Attention LED location for applicable card";
        tailf:validate "attn_led_loc_validate" {
          tailf:dependency ".";
        }
        leaf location {
          type string {
            pattern "([0-255])|((0?[0-9]|1[0-5])/(FC(0?[0-5])))|((0?[0-9]|1[0-5])/(RP(0?[0-1])))|((0?[0-9]|1[0-5])/(0?[0-9]|1[0-5]))|((F[0-3])/(FC(0?[0-9]|1[0-1])))|((F[0-3])/(SC(0?[0-1])))|(0?[0-9]/(SC(0?[0-1])))|(0?[0-9]/(FT(0?[0-2])))|(0?[0-9]/(PM(0?[0-9])))";
          }
          mandatory true;
          tailf:info
            "R/S;; Location to (keep) attention-led on
             rack(0-15 or F0-F3)
             slot(RP0-RP1 or SC0-SC1
                  or 0-7 or FC0-FC11)";
        }
      }
    }
  }
  tailf:id "http://www.cisco.com/panini/calvados/led_mgr";

  container led {
    config false;
    description
      "Calvados Led Manager Status, Attn, Alarm inventory";
    tailf:info "Show status, alarm and attention LED information";
    tailf:callpoint "show_led_location_cp";
    tailf:cli-show-template "$(location|show)";
    list location {
      key "location";
      tailf:info "Select node location";
      tailf:cli-full-command;
      tailf:cli-no-match-completion;
      tailf:cli-suppress-table;
      tailf:cli-show-template-enter "";
      tailf:cli-show-template-legend
        "=============================================================
         Location  LED Name                      Mode         Color  
         =============================================================
        ";
      tailf:cli-show-template
        "$(.legend_shown!=true?=============================================================
         Location  LED Name                      Mode         Color  
         =============================================================
         )$(location)        
         $(led_attributes|show)";
      leaf location {
        type string;
        tailf:display-column-name "Location";
      }
      list led_attributes {
        key "led_name";
        tailf:cli-no-match-completion;
        tailf:cli-drop-node-name;
        tailf:callpoint "show_led_sensor_cp";
        tailf:cli-suppress-table;
        tailf:cli-show-template-enter "";
        tailf:cli-show-template "          $(led_name|ljust:28)  $(led_mode|ljust:10)  $(led_color|ljust:8)  \n";
        leaf led_name {
          type string;
        }
        leaf led_mode {
          type string;
        }
        leaf led_color {
          type string;
        }
      }
    }
    uses show_trace:traceable;
  }
}
