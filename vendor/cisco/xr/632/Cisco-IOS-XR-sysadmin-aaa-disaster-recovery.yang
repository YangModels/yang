module Cisco-IOS-XR-sysadmin-aaa-disaster-recovery {
  namespace "http://www.cisco.com/ns/yang/Cisco-IOS-XR-sysadmin-aaa-disaster-recovery";
  prefix disaster-recovery;

  import tailf-common {
    prefix tailf;
  }
  import tailf-aaa {
    prefix aaa;
  }

  organization
    "Cisco Systems Inc.";
  contact
    "clos-mgbl@cisco.com";
  description
    "This module defines the system users authentication 
     credentials and virtual IP that can be modified in 
     runtime.";

  revision 2017-05-10 {
    description
      "Namespace changed from disaster-recovery to Cisco-IOS-XR-sysadmin-aaa-disaster-recovery";
  }
  revision 2011-06-20 {
    description
      "Initial revision";
  }

  augment "/aaa:aaa" {
    container disaster-recovery {
      tailf:info "Disaster Recovery user information";
      tailf:cli-sequence-commands;
      tailf:cli-compact-syntax;
      tailf:cli-full-no;
      leaf username {
        type leafref {
          path "/aaa:aaa/aaa:authentication/aaa:users/aaa:user/aaa:name";
        }
        tailf:cli-incomplete-command;
        tailf:info
          "                                                            
           The username with which you can login to system                         
           in case of normal authentication failure case.                          
          ";
      }
      leaf password {
        type tailf:md5-digest-string;
        tailf:info
          "                                                            
           The password with which you can login to system                         
           in case of normal authentication failure case.                          
          ";
      }
    }
  }
  tailf:id "http://www.cisco.com/ns/calvados/confd_helper/disaster-recovery";
}
