module Cisco-IOS-XR-sysadmin-ethsw-esdma-clear {
  namespace "http://www.cisco.com/ns/yang/Cisco-IOS-XR-sysadmin-ethsw-esdma-clear";
  prefix esdma_clear;

  import tailf-common {
    prefix tailf;
  }
  import Cisco-IOS-XR-sysadmin-ethsw-esdma-types {
    prefix esdma_types;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains the YANG definitions
     for the Cisco IOS-XR SysAdmin
     'clear controller switch' commands.
     
     Copyright(c) 2011-2017 by Cisco Systems, Inc.
     All rights reserved.";

  revision 2017-05-01 {
    description
      "Namespace change to comply with Cisco guidelines on namespace";
  }
  revision 2016-07-06 {
    description
      "Initial revision with content extracted from esdma_cli.yang.";
  }

  grouping switch-clear-statistics {
    container statistics {
      tailf:info "Clears the Ethernet switch interface statistics";
      tailf:callpoint "esdma-clear-switch-location-helper";
      list location {
        key "rack card switch-id";
        tailf:info "Location for a switch interface statistics clear operation";
        tailf:cli-key-format "$(1)/$(2)/$(3)";
        leaf rack {
          type esdma_types:esdma-rack-num-enum;
        }
        leaf card {
          type esdma_types:esdma-cpu;
        }
        leaf switch-id {
          type esdma_types:esdma-switch-type-enum;
        }
        tailf:action "all" {
          tailf:info "Clear statistics for all switch ports";
          tailf:actionpoint "esdma-switch-clear-stats-all";
          tailf:confirm-text "Clear all switch port statistics ?" {
            tailf:confirm-default "true";
          }
          output {
            leaf result {
              type string;
              mandatory true;
            }
          }
        }
      }
    }
  }

  grouping switch-clear-mlap {
    container mlap {
      tailf:info "Commands for clearing MLAP statistics";
      container statistics {
        tailf:info "Clears the MLAP interface statistics";
        tailf:callpoint "esdma-clear-mlap-location-helper";
        list location {
          key "rack card switch-id";
          tailf:info "Location for an MLAP statistics clear operation";
          tailf:cli-key-format "$(1)/$(2)/$(3)";
          leaf rack {
            type esdma_types:esdma-rack-num-enum;
          }
          leaf card {
            type esdma_types:esdma-cpu;
          }
          leaf switch-id {
            type esdma_types:esdma-switch-type-enum;
          }
          tailf:action "all" {
            tailf:info "Clear statistics for all switch ports";
            tailf:actionpoint "esdma-mlap-clear-stats-all";
            tailf:confirm-text "Clear all MLAP statistics ?" {
              tailf:confirm-default "true";
            }
            output {
              leaf result {
                type string;
                mandatory true;
              }
            }
          }
        }
      }
    }
  }

  grouping switch-clear-sdr {
    container sdr {
      tailf:info "Commands for clearing SDR packet statistics";
      container statistics {
        tailf:info "Clears the SDR packet statistics";
        tailf:callpoint "esdma-clear-sdr-location-helper";
        list location {
          key "rack card switch-id";
          tailf:info "Location for an SDR packet statistics clear operation";
          tailf:cli-key-format "$(1)/$(2)/$(3)";
          leaf rack {
            type esdma_types:esdma-rack-num-enum;
          }
          leaf card {
            type esdma_types:esdma-cpu;
          }
          leaf switch-id {
            type esdma_types:esdma-switch-type-enum;
          }
          tailf:action "all" {
            tailf:info "Clear packet statistics for all SDRs";
            tailf:actionpoint "esdma-sdr-clear-stats-all";
            tailf:confirm-text "Clear all SDR packet statistics ?" {
              tailf:confirm-default "true";
            }
            output {
              leaf result {
                type string;
                mandatory true;
              }
            }
          }
        }
      }
    }
  }

  grouping switch-clear-fdb {
    container fdb {
      tailf:info "Commands for clearing switch forwarding database";
      tailf:callpoint "esdma-clear-switch-location-helper";
      list location {
        key "rack card switch-id";
        tailf:info "Location to clear the switch forwarding database";
        tailf:cli-key-format "$(1)/$(2)/$(3)";
        leaf rack {
          type esdma_types:esdma-rack-num-enum;
        }
        leaf card {
          type esdma_types:esdma-cpu;
        }
        leaf switch-id {
          type esdma_types:esdma-switch-type-enum;
        }
        tailf:action "all" {
          tailf:info "Clear all dynamic FDB entries";
          tailf:actionpoint "esdma-fdb-clear-all";
          tailf:confirm-text "Clear all dynamic FDB entries ?" {
            tailf:confirm-default "true";
          }
          output {
            leaf result {
              type string;
              mandatory true;
            }
          }
        }
      }
    }
  }
  tailf:id "http://cisco.com/panini/calvados/esdma/esdma_clear";
}
