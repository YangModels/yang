module Cisco-IOS-XR-sysadmin-ethsw-esdma-vlan {
  namespace "http://www.cisco.com/ns/yang/Cisco-IOS-XR-sysadmin-ethsw-esdma-vlan";
  prefix esdma_vlan;

  import tailf-common {
    prefix tailf;
  }
  import Cisco-IOS-XR-sysadmin-ethsw-esdma-types {
    prefix esdma_types;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains the YANG definitions
     for the Cisco IOS-XR SysAdmin
     'show controller switch vlan' commands.
     
     Copyright(c) 2011-2017 by Cisco Systems, Inc.
     All rights reserved.";

  revision 2017-05-01 {
    description
      "Namespace change to comply with Cisco guidelines on namespace";
  }
  revision 2016-07-06 {
    description
      "Initial revision with content extracted from esdma_cli.yang.";
  }

  grouping sdr-list-summary {
    list sdr-id {
      key "sdr";
      tailf:cli-drop-node-name;
      tailf:cli-suppress-show-path;
      tailf:cli-suppress-show-match;
      tailf:cli-enforce-table;
      leaf sdr {
        type esdma_types:esdma-sdr-id;
        tailf:display-column-name "SDR Identifier";
      }
      leaf esd-sdr-name {
        type string;
        tailf:display-column-name "SDR Name";
      }
      list vlan-id {
        key "vlan";
        tailf:cli-drop-node-name;
        leaf vlan {
          type esdma_types:vlan-id-type;
          tailf:display-column-name "VLAN";
          tailf:cli-value-display-template "$(.)";
        }
        leaf vlan-hex {
          type leafref {
            path "../vlan";
          }
          tailf:display-column-name "";
          tailf:cli-value-display-template "(0x$(.|hex:3))";
        }
        leaf vlan-use {
          type string;
          tailf:display-column-name "VLAN Use";
        }
      }
    }
  }

  grouping sdr-list {
    list sdr-id {
      key "sdr";
      tailf:cli-drop-node-name;
      tailf:cli-table-legend
        "Rack  Card  Switch  Rack Serial Number
         --------------------------------------
         $(../rack|ljust:4)  $(../card|ljust:4)  $(../switch-id|ljust:6)  $(../serial-num|ljust:18)
        ";
      tailf:cli-enforce-table;
      leaf sdr {
        type esdma_types:esdma-sdr-id;
        tailf:display-column-name "SDR Identifier";
      }
      leaf esd-sdr-name {
        type string;
        tailf:display-column-name "SDR Name";
      }
      list vlan-id {
        key "vlan";
        tailf:cli-drop-node-name;
        leaf vlan {
          type esdma_types:vlan-id-type;
          tailf:display-column-name "VLAN";
          tailf:cli-value-display-template "$(.)";
        }
        leaf vlan-hex {
          type leafref {
            path "../vlan";
          }
          tailf:display-column-name "";
          tailf:cli-value-display-template "(0x$(.|hex:3))";
        }
        leaf vlan-use {
          type string;
          tailf:display-column-name "VLAN Use";
        }
      }
    }
  }

  grouping vlan-information-group {
    container information {
      tailf:info "VLAN use information";
      tailf:callpoint "esdma_switch_vlan_information";
      tailf:cli-show-template "$(summary|show)";
      list location {
        key "rack card switch-id";
        tailf:info "Location information for switch VLAN information";
        tailf:cli-full-command;
        tailf:cli-suppress-table;
        tailf:cli-key-format "$(1)/$(2)/$(3)";
        tailf:cli-show-template "$(sdr-id|show)";
        leaf rack {
          type esdma_types:esdma-rack-num-enum;
        }
        leaf card {
          type esdma_types:esdma-cpu;
          description
            "Card to list the switch VLAN information for";
        }
        leaf switch-id {
          type esdma_types:esdma-switch-type-enum;
          description
            "Switch type";
        }
        leaf serial-num {
          type string;
          description
            "Rack serial number";
          tailf:cli-suppress-show-path;
          tailf:cli-suppress-show-match;
        }
        uses sdr-list;
      }
      container summary {
        tailf:info "System information for switch VLAN information";
        tailf:cli-drop-node-name;
        tailf:cli-suppress-show-path;
        tailf:cli-suppress-show-match;
        uses sdr-list-summary;
      }
    }
  }

  grouping vlan-rule-info {
    list rule-id {
      tailf:cli-suppress-show-path;
      tailf:cli-suppress-show-match;
      leaf direction {
        type esdma_types:switch-data-direction-enum;
        description
          "Packet direction this rule applies to";
        tailf:display-column-name "Packet Direction";
      }
      leaf match-table {
        type esdma_types:switch-table-type-enum;
        tailf:display-column-name "Match Table";
      }
      leaf match-type {
        type esdma_types:switch-match-type-enum;
        tailf:display-column-name "Match Criteria";
      }
      leaf match-vlan-id {
        type esdma_types:vlan-id-type;
        tailf:display-column-name "VLAN";
        tailf:cli-value-display-template "$(.!=0?$(.):-)";
      }
      leaf action {
        type esdma_types:switch-action-type-enum;
        tailf:display-column-name "Action";
        tailf:cli-preformatted;
      }
      leaf action-vlan-id {
        type esdma_types:vlan-id-type;
        tailf:display-column-name "Action VLAN";
        tailf:cli-value-display-template "$(.!=0?$(.):-)";
      }
    }
  }

  grouping vlan-detail-group {
    container vlan-detail {
      tailf:cli-drop-node-name;
      tailf:cli-incomplete-show-path;
      tailf:callpoint "esdma_switch_vlan_detail_rules";
      list vlan-id {
        key "vlan";
        tailf:cli-drop-node-name;
        tailf:cli-incomplete-show-path;
        tailf:info "VLAN identifier to retrieve detail for";
        leaf vlan {
          type esdma_types:vlan-id-type;
          tailf:cli-drop-node-name;
        }
        container rules {
          tailf:cli-incomplete-show-path;
          tailf:info "Display VLAN rules for specific VLAN";
          tailf:callpoint "esdma_switch_vlan_detail_rules";
          list location {
            key "rack card switch-id";
            tailf:info "Location information for switch VLAN detail";
            tailf:cli-full-command;
            tailf:cli-suppress-table;
            tailf:cli-key-format "$(1)/$(2)/$(3)";
            leaf rack {
              type esdma_types:esdma-rack-num-enum;
            }
            leaf card {
              type esdma_types:esdma-cpu;
              description
                "Card that owns a switch of interest";
            }
            leaf switch-id {
              type esdma_types:esdma-switch-type-enum;
              description
                "Switch type";
            }
            list port-iter {
              key "port";
              tailf:cli-drop-node-name;
              leaf port {
                type esdma_types:esdma-switch-port-type;
                description
                  "Switch port";
                tailf:display-column-name "Switch Port";
              }
              uses vlan-rule-info;
            }
          }
        }
      }
    }
  }

  grouping vlan-summary-group {
    container rules {
      tailf:cli-incomplete-show-path;
      tailf:callpoint "esdma_switch_vlan_summary_rules_data";
      tailf:info "Display VLAN rule summary";
      list location {
        key "rack card switch-id";
        tailf:info "Location information for switch VLAN rule summary";
        tailf:cli-full-command;
        tailf:cli-suppress-table;
        tailf:cli-key-format "$(1)/$(2)/$(3)";
        leaf rack {
          type esdma_types:esdma-rack-num-enum;
        }
        leaf card {
          type esdma_types:esdma-cpu;
          description
            "Card that owns a switch of interest to display the VLAN configuration for";
        }
        leaf switch-id {
          type esdma_types:esdma-switch-type-enum;
          description
            "Switch type";
        }
        list port-iter {
          key "port";
          tailf:cli-drop-node-name;
          leaf port {
            type esdma_types:esdma-switch-port-type;
            description
              "Switch port";
            tailf:display-column-name "Switch Port";
          }
          list vlan-id {
            key "vlan";
            tailf:cli-drop-node-name;
            tailf:cli-suppress-show-path;
            tailf:cli-suppress-show-match;
            leaf vlan {
              type esdma_types:vlan-id-type;
              description
                "This VLAN represents a VLAN membership for this switch port. Multiple rules may exist to support this VLAN.";
              tailf:cli-drop-node-name;
              tailf:cli-value-display-template "$(.!=0?$(.):-)";
            }
            uses vlan-rule-info;
          }
        }
      }
    }
  }

  grouping vlan-membership-group {
    container membership {
      tailf:cli-incomplete-show-path;
      tailf:callpoint "esdma_switch_vlan_membership_data";
      tailf:info "List switch port membership of VLANs";
      list location {
        key "rack card switch-id";
        tailf:info "Location information for switch VLAN membership";
        tailf:cli-key-format "$(1)/$(2)/$(3)";
        tailf:cli-show-template "$(vlan-id|show)";
        leaf rack {
          type esdma_types:esdma-rack-num-enum;
        }
        leaf card {
          type esdma_types:esdma-cpu;
          description
            "Card that owns a switch of interest to display the VLAN configuration for";
        }
        leaf switch-id {
          type esdma_types:esdma-switch-type-enum;
          description
            "Switch type";
        }
        list vlan-id {
          key "vlan";
          tailf:cli-drop-node-name;
          tailf:cli-enforce-table;
          leaf vlan {
            type esdma_types:vlan-id-type;
            tailf:display-column-name "VLAN";
            tailf:cli-value-display-template "$(.)";
          }
          leaf vlan-hex {
            type leafref {
              path "../vlan";
            }
            tailf:cli-suppress-show-path;
            tailf:cli-suppress-show-match;
            tailf:display-column-name "";
            tailf:cli-value-display-template "(0x$(.|hex:3))";
          }
          leaf-list port {
            type uint8;
            tailf:cli-suppress-show-path;
            tailf:cli-suppress-show-match;
            tailf:display-column-name "Port";
            tailf:cli-flat-list-syntax;
            tailf:cli-column-width "40";
          }
        }
      }
    }
  }

  grouping switch-vlan-group {
    container vlan {
      tailf:info "Control Plane Ethernet VLAN Information";
      tailf:cli-incomplete-show-path;
      uses vlan-summary-group;
      uses vlan-information-group;
      uses vlan-detail-group;
      uses vlan-membership-group;
    }
  }

  grouping switch-vlan-group-ncs5500 {
    container vlan {
      tailf:info "Control Plane Ethernet VLAN Information";
      tailf:cli-incomplete-show-path;
      uses vlan-information-group;
      uses vlan-membership-group;
    }
  }
  tailf:id "http://cisco.com/panini/calvados/esdma/esdma_vlan";
}
