module Cisco-IOS-XR-sysadmin-ethsw-esdma-trace {
  namespace "http://www.cisco.com/ns/yang/Cisco-IOS-XR-sysadmin-ethsw-esdma-trace";
  prefix esdma_trace;

  import tailf-common {
    prefix tailf;
  }
  import Cisco-IOS-XR-sysadmin-show-trace {
    prefix show_trace;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains the YANG definitions
     for the Cisco IOS-XR SysAdmin
     'show controller switch trace' commands.
     
     Copyright(c) 2011-2017 by Cisco Systems, Inc.
     All rights reserved.";

  revision 2017-05-01 {
    description
      "Namespace change to comply with Cisco guidelines on namespace";
  }
  revision 2016-07-06 {
    description
      "Initial revision with content extracted from esdma_cli.yang.";
  }

  grouping esd-ctrace {
    container esd {
      tailf:cli-drop-node-name;
      tailf:cli-incomplete-show-path;
      uses show_trace:traceable_process;
    }
  }

  grouping esd-ctrace-ncs5500 {
    container trace {
      tailf:info "Display traces for an ESD process instance";
      tailf:cli-incomplete-show-path;
      tailf:callpoint "esdma_switch_trace";
      list location {
        key "location_str";
        tailf:info "Location of the ESD process instance";
        tailf:cli-incomplete-show-path;
        leaf location_str {
          type string;
          tailf:cli-value-display-template "$(.==0/0/LC-SW?0/LC0/LC-SW:$(.==0/1/LC-SW?0/LC1/LC-SW:$(.==0/2/LC-SW?0/LC2/LC-SW:$(.==0/3/LC-SW?0/LC3/LC-SW:$(.==0/4/LC-SW?0/LC4/LC-SW:$(.==0/5/LC-SW?0/LC5/LC-SW:$(.==0/6/LC-SW?0/LC6/LC-SW:$(.==0/7/LC-SW?0/LC7/LC-SW:$(.==0/8/LC-SW?0/LC8/LC-SW:$(.==0/9/LC-SW?0/LC9/LC-SW:$(.==0/10/LC-SW?0/LC10/LC-SW:$(.==0/11/LC-SW?0/LC11/LC-SW:$(.==0/12/LC-SW?0/LC12/LC-SW:$(.==0/13/LC-SW?0/LC13/LC-SW:$(.==0/14/LC-SW?0/LC14/LC-SW:$(.==0/15/LC-SW?0/LC15/LC-SW:$(.)))))))))))))))))";
        }
        container esd {
          tailf:display-when "not(contains(../location_str, 'EPC-SW')) and not(contains(../location_str, 'EOBC-SW'))";
          tailf:cli-drop-node-name;
          uses show_trace:traceable_with_keypath_location;
        }
        container esd-EPC-SW {
          tailf:display-when "contains(../location_str, 'EPC-SW')";
          tailf:cli-drop-node-name;
          uses show_trace:traceable_with_keypath_location;
        }
        container esd-EOBC-SW {
          tailf:display-when "contains(../location_str, 'EOBC-SW')";
          tailf:cli-drop-node-name;
          uses show_trace:traceable_with_keypath_location;
        }
      }
    }
  }

  grouping esdma-ctrace {
    container esdma {
      tailf:cli-drop-node-name;
      uses show_trace:traceable;
    }
  }
  tailf:id "http://cisco.com/panini/calvados/esdma/esdma_trace";
}
