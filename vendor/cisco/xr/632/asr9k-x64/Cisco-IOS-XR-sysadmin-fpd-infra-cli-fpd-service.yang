module Cisco-IOS-XR-sysadmin-fpd-infra-cli-fpd-service {
  namespace "http://www.cisco.com/ns/yang/Cisco-IOS-XR-sysadmin-fpd-infra-cli-fpd-service";
  prefix upgrade;

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains definitions
     for the Calvados model objects.
     
     Copyright (c) 2012-2017 by Cisco Systems, Inc.
     All rights reserved.";

  revision 2017-05-01 {
    description
      "Namespace change to comply with Cisco guidelines on namespace";
  }

  list location {
    key "loc";
    config false;
    leaf loc {
      type string;
    }
    list fpd2 {
      key "name";
      config false;
      leaf name {
        type string;
      }
    }
  }
}
