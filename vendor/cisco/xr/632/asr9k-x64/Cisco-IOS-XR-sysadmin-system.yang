module Cisco-IOS-XR-sysadmin-system {
  namespace "http://www.cisco.com/ns/yang/Cisco-IOS-XR-sysadmin-system";
  prefix calvados_system;

  import tailf-common {
    prefix tailf;
  }
  import ietf-inet-types {
    prefix inet;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains a collection of YANG
     definitions for Cisco IOS-XR SysAdmin configuration.
     
     This module defines the system users authentication 
     credentials and virtual IP that can be modified in
     runtime. 
     
     Copyright(c) 2011-2017 by Cisco Systems, Inc.
     All rights reserved.";

  revision 2017-01-31 {
    description
      "Changed the namespace and module name";
  }
  revision 2011-06-20 {
    description
      "Initial revision";
  }

  typedef file-name-type {
    type string;
    tailf:info "WORD;;Name of the folder or file";
  }

  typedef screen-length {
    type uint64 {
      range "0 .. 32000";
      tailf:info "<0-32000>;;Number of lines on screen (0 for no pausing).";
    }
  }

  typedef screen-width {
    type uint64 {
      range "0 .. 512";
      tailf:info "<0-512>;;Number of characters on a screen line.";
    }
  }

  typedef ipv4-subnet-mask-ip {
    type inet:ip-address;
    tailf:info "subnet-mask ip";
  }

  typedef ipv6-prefix {
    type uint8 {
      range "0..128";
    }
    tailf:info "ipv6 prefix 0-128 ";
  }

  typedef calvados-ipv4-with-optional-subnet-bits {
    type string {
      pattern "(([0-9]|[1-9][0-9]|1[0-9][0-9]|2[0-4][0-9]|25[0-5])\\.){3}([0-9]|[1-9][0-9]|1[0-9][0-9]|2[0-4][0-9]|25[0-5])(/(([0-9])|([1-2][0-9])|(3[0-2])))?";
    }
    description
      "The ipv4-prefix type represents an IPv4 address prefix.
       The prefix length is given by the number following the
       slash character and must be less than or equal to 32.";
    tailf:info "A.B.C.D/subnet-bits IPv4 address/subnet-bits or A.B.C.D subnet-ip ";
  }

  typedef calvados-ipv6-with-optional-prefix {
    type string {
      pattern "((:|[0-9a-fA-F]{0,4}):)([0-9a-fA-F]{0,4}:){0,5}((([0-9a-fA-F]{0,4}:)?(:|[0-9a-fA-F]{0,4}))|(((25[0-5]|2[0-4][0-9]|[01]?[0-9]?[0-9])\\.){3}(25[0-5]|2[0-4][0-9]|[01]?[0-9]?[0-9])))(/(([0-9])|([0-9]{2})|(1[0-1][0-9])|(12[0-8])))?";
      pattern "(([^:]+:){6}(([^:]+:[^:]+)|(.*\\..*)))|((([^:]+:)*[^:]+)?::(([^:]+:)*[^:]+)?)(/.+)?";
    }
    description
      "The ipv6-prefix type represents an IPv6 address prefix.
       The prefix length is given by the number following the
       slash character and must be less than or equal 128.";
    tailf:info "X:X::X/prefix IPv6/prefix or X:X::X prefix IPv6 addresss and prefix";
  }

  grouping config_sync_clear_inconsistency {
    container configuration {
      tailf:action "inconsistencies" {
        tailf:exec "/opt/cisco/calvados/bin/vrfch.sh" {
          tailf:args "CTRL_VRF /opt/cisco/calvados/script/confd_config_backup_standalone.sh";
        }
        output {
          list node {
            leaf ip {
              type string;
            }
            leaf status {
              type string;
            }
          }
        }
      }
    }
  }
  tailf:id "http://www.cisco.com/ns/calvados/confd_helper/calvados_system";

  container mgmt {
    tailf:cli-incomplete-command;
    tailf:info
      "
        configure management interface IP address.
      ";
    container ipv4 {
      tailf:cli-sequence-commands {
        tailf:cli-reset-all-siblings;
      }
      tailf:cli-full-no;
      leaf address {
        type calvados-ipv4-with-optional-subnet-bits;
        must "true() = contains(../subnet-mask-ip, '.') or true() = contains(../address, '/')" {
          error-message
            "you must provide subnet, it must be of the form
             A.B.C.D/subnet-bits or A.B.C.D subnet-ip";
          tailf:dependency "../subnet-mask-ip";
        }
        tailf:cli-drop-node-name;
        tailf:info
          "
            IP address of the interface.
          ";
        tailf:cli-run-template "$(.?mgmt ipv4 $(.) $(../subnet-mask-ip)\\n)";
      }
      leaf subnet-mask-ip {
        type ipv4-subnet-mask-ip;
        must "false() = contains(../address, '/')" {
          error-message
            "you already provided subnet earlier it must be of the form
             A.B.C.D/subnet-bits or A.B.C.D subnet-ip";
          tailf:dependency "../address";
        }
        tailf:cli-drop-node-name;
        tailf:info
          "
             Subnet Mask Bits.
          ";
        tailf:cli-run-template "";
      }
    }
    container ipv6 {
      tailf:cli-full-no;
      tailf:cli-sequence-commands {
        tailf:cli-reset-all-siblings;
      }
      leaf address {
        type calvados-ipv6-with-optional-prefix;
        must "true() = (../prefix) or true() = contains(../address, '/')" {
          error-message
            "you must provide prefix.It must be of the form
             X:X::X/prefix or X:X::X prefix";
          tailf:dependency "../prefix";
        }
        tailf:cli-drop-node-name;
        tailf:info
          "
            IP address of the interface.
          ";
        tailf:cli-run-template "$(.?mgmt ipv6 $(.) $(../prefix)\\n)";
      }
      leaf prefix {
        type ipv6-prefix;
        must "false() = contains(../address, '/')" {
          error-message
            "you already provided prefix earlier it must be of 
             form X:X::X/prefix or X:X::X prefix";
          tailf:dependency "../address";
        }
        tailf:cli-drop-node-name;
        tailf:info
          "
            IPv6 Prefix
          ";
        tailf:cli-run-template "";
      }
    }
  }
}
