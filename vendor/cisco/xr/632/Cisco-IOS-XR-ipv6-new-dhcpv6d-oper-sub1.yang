submodule Cisco-IOS-XR-ipv6-new-dhcpv6d-oper-sub1 {
  belongs-to Cisco-IOS-XR-ipv6-new-dhcpv6d-oper {
    prefix Cisco-IOS-XR-ipv6-new-dhcpv6d-oper;
  }

  import ietf-inet-types {
    prefix inet;
  }
  import ietf-yang-types {
    prefix yang;
  }
  import Cisco-IOS-XR-types {
    prefix xr;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR ipv6-new-dhcpv6d package operational data.
     
     Copyright (c) 2013-2017 by Cisco Systems, Inc.
     All rights reserved.";

  revision 2015-11-09 {
    description
      "IOS XR 6.0 revision.";
  }

  typedef Bag-dhcpv6d-fsm-state {
    type enumeration {
      enum "server-initializing" {
        value 0;
        description
          "Server initializing state for client binding";
      }
      enum "server-waiting-dpm" {
        value 1;
        description
          "Server waiting on DPM to validate subscriber";
      }
      enum "server-waiting-daps" {
        value 2;
        description
          "Server waiting on DAPS to assign/free
           addr/prefix";
      }
      enum "server-waiting-client" {
        value 3;
        description
          "Server waiting for a request from the client";
      }
      enum "server-waiting-subscriber" {
        value 4;
        description
          "Server waiting for iedge response for the
           session";
      }
      enum "server-waiting-rib" {
        value 5;
        description
          "Server waiting for RIB response for route add";
      }
      enum "server-bound-client" {
        value 6;
        description
          "Server bound state to the client";
      }
      enum "proxy-initializing" {
        value 10;
        description
          "Proxy initializing state for client binding";
      }
      enum "proxy-waiting-dpm" {
        value 11;
        description
          "Proxy waiting on DPM to validate subscriber";
      }
      enum "proxy-waiting-daps" {
        value 12;
        description
          "Proxy waiting on DAPS to assign/free prefix(ND)";
      }
      enum "proxy-waiting-client-server" {
        value 13;
        description
          "Proxy waiting for a msg from the client/srv";
      }
      enum "proxy-waiting-subscriber" {
        value 14;
        description
          "Proxy waiting on iedge to sub session resp";
      }
      enum "proxy-waiting-rib" {
        value 15;
        description
          "Proxy waiting on RIB response";
      }
      enum "proxy-bound-client" {
        value 16;
        description
          "Proxy bound state to the client";
      }
    }
    description
      "Bag dhcpv6d fsm state";
  }

  typedef Bag-dhcpv6d-ia-id {
    type enumeration {
      enum "iana" {
        value 0;
        description
          "Non-temporary Addresses assigned ";
      }
      enum "iapd" {
        value 1;
        description
          "Prefix delegeated to client      ";
      }
      enum "iata" {
        value 2;
        description
          "Temporary Addresses - not supported ";
      }
    }
    description
      "Bag dhcpv6d ia id";
  }

  typedef Bag-dhcpv6d-intf-serg-role {
    type enumeration {
      enum "none" {
        value 0;
        description
          "DHCPv6 Interface SERG role NONE";
      }
      enum "master" {
        value 1;
        description
          "DHCPv6 Interface SERG role Master";
      }
      enum "slave" {
        value 2;
        description
          "DHCPv6 Interface SERG role Slave";
      }
    }
    description
      "Bag dhcpv6d intf serg role";
  }

  typedef Bag-dhcpv6d-intf-srg-role {
    type enumeration {
      enum "none" {
        value 0;
        description
          "DHCPv6 Interface SRG role NONE";
      }
      enum "master" {
        value 1;
        description
          "DHCPv6 Interface SRG role Master";
      }
      enum "slave" {
        value 2;
        description
          "DHCPv6 Interface SRG role Slave";
      }
    }
    description
      "Bag dhcpv6d intf srg role";
  }

  typedef Lease-limit {
    type enumeration {
      enum "none" {
        description
          "Lease limit type none";
      }
      enum "interface" {
        description
          "Lease limit type interface";
      }
      enum "circuit-id" {
        description
          "Lease limit type circuit ID";
      }
      enum "remote-id" {
        description
          "Lease limit type remote ID";
      }
    }
    description
      "Profile lease limit type";
  }

  typedef Bag-dhcpv6d-sub-mode {
    type enumeration {
      enum "base" {
        value 0;
        description
          "DHCPv6 Base mode";
      }
      enum "server" {
        value 1;
        description
          "DHCPv6 Server mode";
      }
      enum "proxy" {
        value 2;
        description
          "DHCPv6 Proxy mode";
      }
    }
    description
      "Bag dhcpv6d sub mode";
  }

  typedef String-ifname {
    type string {
      length "0..65";
    }
    description
      "String ifname";
  }

  typedef String-vrf {
    type string {
      length "0..33";
    }
    description
      "String vrf";
  }

  typedef Ipv6-address {
    type inet:ipv6-address;
    description
      "IPV6 Address type";
  }

  typedef Dhcpv6-issu-version {
    type enumeration {
      enum "version1" {
        value 0;
        description
          "Version 1";
      }
      enum "version2" {
        value 1;
        description
          "Version 2";
      }
    }
    description
      "Dhcpv6 issu version";
  }

  typedef Dhcp-issu-phase {
    type enumeration {
      enum "phase-not-started" {
        value 0;
        description
          "An ISSU event has not started";
      }
      enum "phase-load" {
        value 1;
        description
          "ISSU Load Phase";
      }
      enum "phase-run" {
        value 2;
        description
          "ISSU Run Phase";
      }
      enum "phase-completed" {
        value 3;
        description
          "An ISSU event has completed successfully";
      }
      enum "phase-aborted" {
        value 4;
        description
          "An ISSU event has aborted";
      }
    }
    description
      "Dhcp issu phase";
  }

  typedef Dhcpv6-issu-role {
    type enumeration {
      enum "role-primary" {
        value 0;
        description
          "Primary role";
      }
      enum "role-secondary" {
        value 1;
        description
          "Secondary role";
      }
    }
    description
      "Dhcpv6 issu role";
  }

  grouping IPV6-DHCPV6D-RELAY-ROUTE-BINDING {
    description
      "DHCPv6 relay route entry";
    leaf duid {
      type string;
      description
        "Client DUID";
    }
    leaf client-id-xr {
      type uint32;
      description
        "Client unique identifier";
    }
    leaf prefix-length {
      type uint8;
      description
        "length of prefix";
    }
    leaf prefix {
      type Ipv6-address;
      description
        "DHCPV6 IPv6 Prefix allotted to client";
    }
    leaf vrf-name {
      type string {
        length "0..33";
      }
      description
        "DHCPv6 client/subscriber Vrf name";
    }
    leaf lifetime {
      type uint32;
      description
        "Client route lifetime";
    }
    leaf rem-life-time {
      type uint32;
      description
        "Client route remaining lifetime";
    }
    leaf interface-name {
      type string {
        length "0..65";
      }
      description
        "Interface name";
    }
    leaf next-hop-addr {
      type Ipv6-address;
      description
        "Next hop is our address";
    }
    leaf ia-id {
      type uint32;
      description
        "IA_ID of this IA";
    }
    leaf relay-profile-name {
      type string {
        length "0..65";
      }
      description
        "Relay Profile name";
    }
  }

  grouping IPV6-DHCPV6D-RELAY-BINDINGS-SUMMARY {
    description
      "DHCPv6 relay binding summary";
    leaf clients {
      type uint32;
      description
        "Total number of clients";
    }
  }

  grouping IPV6-DHCPV6D-RELAY-STATS {
    description
      "DHCPv6 relay statistics";
    list ipv6-dhcpv6d-relay-stat {
      description
        "ipv6 dhcpv6d relay stat";
      container statistics {
        description
          "Relay statistics";
        uses IPV6-DHCPV6D-FILTERED-STATS;
      }
      leaf vrf-name {
        type string {
          length "0..33";
        }
        description
          "DHCPv6 L3 VRF name";
      }
    }
  }

  grouping IPV6-DHCPV6D-SERVER-BINDING-OPTIONS {
    description
      "DHCPv6 server binding inserted option values";
    leaf mac-address-xr {
      type string;
      description
        "Client MAC address";
    }
    leaf duid-xr {
      type string;
      description
        "Client DUID";
    }
    leaf dns-count {
      type uint8;
      description
        "DNS address count";
    }
    leaf opt17 {
      type string;
      description
        "Client Option 17 value";
    }
    leaf-list dns-address {
      type Ipv6-address;
      max-elements "8";
      description
        "DNS addresses";
    }
  }

  grouping IPV6-DHCPV6D-SERVER-STATS {
    description
      "DHCPv6 server statistics";
    list ipv6-dhcpv6d-server-stat {
      description
        "ipv6 dhcpv6d server stat";
      container statistics {
        description
          "Server statistics";
        uses IPV6-DHCPV6D-FILTERED-STATS;
      }
      leaf vrf-name {
        type string {
          length "0..33";
        }
        description
          "DHCPv6 L3 VRF name";
      }
    }
  }

  grouping IPV6-DHCPV6D-SERVER-INTERFACE {
    description
      "DHCPv6 server interface";
    leaf server-vrf-name {
      type string {
        length "0..33";
      }
      description
        "VRF name";
    }
    leaf server-interface-mode {
      type Bag-dhcpv6d-sub-mode;
      description
        "Mode of interface";
    }
    leaf is-server-interface-ambiguous {
      type uint32;
      description
        "Is interface ambiguous";
    }
    leaf server-interface-profile-name {
      type string {
        length "0..65";
      }
      description
        "Name of profile attached to the interface";
    }
    leaf server-interface-lease-limit-type {
      type Lease-limit;
      description
        "Lease limit type on interface";
    }
    leaf server-interface-lease-limits {
      type uint32;
      description
        "Lease limit count on interface";
    }
    leaf srg-role {
      type Bag-dhcpv6d-intf-srg-role;
      description
        "DHCPv6 Interface SRG role";
    }
    leaf serg-role {
      type Bag-dhcpv6d-intf-serg-role;
      description
        "DHCPv6 Interface SERG role";
    }
    leaf mac-throttle {
      type boolean;
      description
        "Mac Throttle Status";
    }
    leaf srg-vrf-name {
      type string {
        length "0..33";
      }
      description
        "SRG VRF name";
    }
    leaf srgp2p {
      type boolean;
      description
        "SRG P2P Status";
    }
  }

  grouping IPV6-DHCPV6D-SERVER-INTERFACE-REFERENCE {
    description
      "DHCPv6 server profile reference";
    list ipv6-dhcpv6d-server-interface-reference {
      description
        "ipv6 dhcpv6d server interface reference";
      leaf server-reference-interface-name {
        type string {
          length "0..65";
        }
        description
          "Interface name";
      }
    }
  }

  grouping TIME-BAG {
    description
      "Time in diffrent formats";
    leaf seconds {
      type uint32;
      units "second";
      description
        "DHCPV6 client lease in seconds";
    }
    leaf time {
      type string {
        length "0..10";
      }
      description
        "Time in format HH:MM:SS";
    }
  }

  grouping IPV6-DHCPV6D-SERVER-PROFILE {
    description
      "DHCPv6 server profile parameters";
    container lease {
      description
        "Server lease time";
      uses TIME-BAG;
    }
    container interface-references {
      description
        "Interface references";
      uses IPV6-DHCPV6D-SERVER-INTERFACE-REFERENCE;
    }
    leaf profile-name {
      type string {
        length "0..65";
      }
      description
        "Server profile name";
    }
    leaf domain-name {
      type string {
        length "0..65";
      }
      description
        "Server domain name";
    }
    leaf profile-dns {
      type uint8;
      description
        "DNS address count";
    }
    leaf aftr-name {
      type string {
        length "0..65";
      }
      description
        "Server aftr name";
    }
    leaf framed-addr-pool-name {
      type string {
        length "0..65";
      }
      description
        "Server framed address pool name";
    }
    leaf delegated-prefix-pool-name {
      type string {
        length "0..65";
      }
      description
        "Server delegated prefix pool name";
    }
    leaf rapid-commit {
      type boolean;
      description
        "Rapid Commit";
    }
    leaf-list profile-dns-address {
      type Ipv6-address;
      max-elements "8";
      description
        "DNS addresses";
    }
  }

  grouping IPV6-DHCPV6D-SERVER-BINDING {
    description
      "DHCPv6 server binding entry";
    container ia-id-pd {
      description
        "List of DHCPv6 IA_ID/PDs";
      uses BAG-DHCPV6D-IA-ID-PD-INFO;
    }
    leaf duid {
      type string;
      description
        "Client DUID";
    }
    leaf client-id-xr {
      type uint32;
      description
        "Client unique identifier";
    }
    leaf client-flag {
      type uint32;
      description
        "DHCPV6 client flag";
    }
    leaf subscriber-label {
      type uint32;
      description
        "DHCPV6 subscriber label";
    }
    leaf vrf-name {
      type string {
        length "0..33";
      }
      description
        "DHCPVV6 client/subscriber VRF name";
    }
    leaf mac-address {
      type string;
      description
        "Client MAC address";
    }
    leaf ia-id-p-ds {
      type uint32;
      description
        "Number of ia_id/pd";
    }
    leaf link-local-address {
      type Ipv6-address;
      description
        "DHCPV6 IPv6 client link local address";
    }
    leaf interface-name {
      type xr:Interface-name;
      description
        "DHCPV6 access interface to client";
    }
    leaf access-vrf-name {
      type string {
        length "0..33";
      }
      description
        "DHCPV6 access VRF name to client";
    }
    leaf server-binding-tags {
      type uint8;
      description
        "DHCPV6 VLAN tag count";
    }
    leaf server-binding-outer-tag {
      type uint32;
      description
        "DHCPV6 VLAN Outer VLAN";
    }
    leaf server-binding-inner-tag {
      type uint32;
      description
        "DHCPV6 VLAN Inner VLAN";
    }
    leaf pool-name {
      type string {
        length "0..64";
      }
      description
        "DHCPV6 pool name";
    }
    leaf profile-name {
      type string {
        length "0..64";
      }
      description
        "DHCPV6 profile name";
    }
    leaf framed-ipv6-prefix {
      type Ipv6-address;
      description
        "DHCPV6 framed ipv6 addess used by ND";
    }
    leaf framed-prefix-length {
      type uint8;
      description
        "DHCPV6 framed ipv6 prefix length used by ND";
    }
    leaf class-name {
      type string {
        length "0..64";
      }
      description
        "DHCPV6 class name";
    }
    leaf rx-remote-id {
      type string {
        length "0..771";
      }
      description
        "DHCPV6 received Remote ID";
    }
    leaf rx-interface-id {
      type string {
        length "0..771";
      }
      description
        "DHCPV6 received Interface ID";
    }
    leaf prefix-pool-name {
      type string {
        length "0..64";
      }
      description
        "DHCPV6 server prefix pool name";
    }
    leaf address-pool-name {
      type string {
        length "0..64";
      }
      description
        "DHCPV6 server address pool name";
    }
    leaf dns-server-count {
      type uint32;
      description
        "DNS server count";
    }
    leaf is-nak-next-renew {
      type boolean;
      description
        "Is true if DHCPv6 next renew from client will be
         NAK'd";
    }
    leaf srg-state {
      type uint32;
      description
        "DHCPV6 SRG state";
    }
    leaf srg-intf-role {
      type uint32;
      description
        "DHCPV6 SRG Intf Role";
    }
    leaf srgp2p {
      type boolean;
      description
        "SRG P2P Status";
    }
    leaf srg-vrf-name {
      type string {
        length "0..33";
      }
      description
        "DHCPV6 SRG VRF NAME";
    }
    leaf sesrg-state {
      type uint32;
      description
        "DHCPV6 SERG state";
    }
    leaf serg-intf-role {
      type uint32;
      description
        "DHCPV6 SERG Intf Role";
    }
  }

  grouping BAG-DHCPV6D-SERVER-BINDINGS-SUMMARY {
    description
      "DHCPv6 server bindings summary for IANA/IAPD";
    leaf initializing-clients {
      type uint32;
      description
        "Number of clients in init state";
    }
    leaf dpm-waiting-clients {
      type uint32;
      description
        "Number of clients waiting on DPM to validate
         subscriber";
    }
    leaf daps-waiting-clients {
      type uint32;
      description
        "Number of clients waiting on DAPS to assign/free
         addr/prefix";
    }
    leaf request-waiting-clients {
      type uint32;
      description
        "Number of clients waiting for a request from the
         client";
    }
    leaf iedge-waiting-clients {
      type uint32;
      description
        "Number of clients waiting for iedge for the
         session";
    }
    leaf rib-waiting-clients {
      type uint32;
      description
        "Number of clients in waiting for RIB response";
    }
    leaf bound-clients {
      type uint32;
      description
        "Number of clients in bound state";
    }
  }

  grouping IPV6-DHCPV6D-SERVER-BINDINGS-SUMMARY {
    description
      "DHCPv6 server bindings summary";
    container iana {
      description
        "IANA server binding summary";
      uses BAG-DHCPV6D-SERVER-BINDINGS-SUMMARY;
    }
    container iapd {
      description
        "IAPD server binding summary";
      uses BAG-DHCPV6D-SERVER-BINDINGS-SUMMARY;
    }
    leaf clients {
      type uint32;
      description
        "Total number of clients";
    }
  }

  grouping IPV6-DHCPV6D-BASE-BINDING {
    description
      "DHCPV6 base binding entry";
    leaf mac-address {
      type string;
      description
        "DHCPV6 client MAC address";
    }
    leaf vrf-name {
      type string {
        length "0..33";
      }
      description
        "DHCPV6 client/subscriber VRF name";
    }
    leaf server-vrf-name {
      type string {
        length "0..33";
      }
      description
        "DHCPV6 server VRF name";
    }
    leaf ipv6-address {
      type Ipv6-address;
      description
        "DHCPV6 IPv6 address";
    }
    leaf server-ipv6-address {
      type Ipv6-address;
      description
        "DHCPV6 server IPv6 address";
    }
    leaf reply-server-ipv6-address {
      type Ipv6-address;
      description
        "DHCPV6 reply server IPv6 address";
    }
    leaf lease-time {
      type uint32;
      units "second";
      description
        "Lease time in seconds";
    }
    leaf remaining-lease-time {
      type uint32;
      units "second";
      description
        "Remaining lease time in seconds";
    }
    leaf state {
      type Bag-dhcpv6d-fsm-state;
      description
        "DHCPV6 client state";
    }
    leaf interface-name {
      type xr:Interface-name;
      description
        "DHCPV6 access interface to client";
    }
    leaf access-vrf-name {
      type string {
        length "0..33";
      }
      description
        "DHCPV6 access interface VRF name";
    }
    leaf base-binding-tags {
      type uint8;
      description
        "DHCPV6 VLAN tag count";
    }
    leaf base-binding-outer-tag {
      type uint32;
      description
        "DHCPV6 VLAN Outer VLAN";
    }
    leaf base-binding-inner-tag {
      type uint32;
      description
        "DHCPV6 VLAN Inner VLAN";
    }
    leaf profile-name {
      type string {
        length "0..64";
      }
      description
        "DHCPV6 profile name";
    }
    leaf is-nak-next-renew {
      type boolean;
      description
        "Is true if DHCPV6 next renew from client will be
         NAK'd";
    }
    leaf subscriber-label {
      type uint32;
      description
        "DHCPV6 subscriber label";
    }
    leaf old-subscriber-label {
      type uint32;
      description
        "DHCPV6 old subscriber label";
    }
    leaf rx-client-duid {
      type string {
        length "0..771";
      }
      description
        "DHCPV6 received client DUID";
    }
    leaf tx-client-uid {
      type string {
        length "0..771";
      }
      description
        "DHCPV6 transmitted client DUID";
    }
    leaf rx-remote-id {
      type string {
        length "0..771";
      }
      description
        "DHCPV6 received Remote ID";
    }
    leaf tx-remote-id {
      type string {
        length "0..771";
      }
      description
        "DHCPV6 transmitted Remote ID";
    }
    leaf rx-interface-id {
      type string {
        length "0..771";
      }
      description
        "DHCPV6 received Interface ID";
    }
    leaf tx-interface-id {
      type string {
        length "0..771";
      }
      description
        "DHCPV6 transmitted Interface ID";
    }
  }

  grouping IPV6-DHCPD-DATABASE {
    description
      "IPv6 DHCP database";
    leaf configured {
      type boolean;
      description
        "Database feature configured";
    }
    leaf version {
      type uint32;
      description
        "Current file version";
    }
    leaf full-file-write-interval {
      type uint32;
      units "minute";
      description
        "Full file write interval in minutes";
    }
    leaf last-full-write-file-name {
      type string {
        length "0..64";
      }
      description
        "Last full write file name";
    }
    leaf last-full-write-time {
      type uint32;
      description
        "Last full write time since epoch";
    }
    leaf full-file-write-count {
      type uint32;
      description
        "Full file write count";
    }
    leaf failed-full-file-write-count {
      type uint32;
      description
        "Failed full file write count";
    }
    leaf full-file-record-count {
      type uint32;
      description
        "Full file record count";
    }
    leaf last-full-file-write-error-timestamp {
      type uint32;
      description
        "Last full file write error timestamp since epoch";
    }
    leaf incremental-file-write-interval {
      type uint32;
      units "minute";
      description
        "Incremental file write interval in minutes";
    }
    leaf last-incremental-write-file-name {
      type string {
        length "0..64";
      }
      description
        "Last incremental write file name";
    }
    leaf last-incremental-write-time {
      type uint32;
      description
        "Last incremental write time since epoch";
    }
    leaf incremental-file-write-count {
      type uint32;
      description
        "Incremental file write count";
    }
    leaf failed-incremental-file-write-count {
      type uint32;
      description
        "Failed incremental file write count";
    }
    leaf incremental-file-record-count {
      type uint32;
      description
        "Incremental file record count";
    }
    leaf last-incremental-file-write-error-timestamp {
      type uint32;
      description
        "Last incremental file write error timestamp
         since epoch";
    }
  }

  grouping BAG-DHCPV6D-PROXY-BINDINGS-SUMMARY {
    description
      "DHCPv6 proxy bindings summary for IANA/IAPD";
    leaf initializing-clients {
      type uint32;
      description
        "Number of clients in init state";
    }
    leaf dpm-waiting-clients {
      type uint32;
      description
        "Number of clients waiting on DPM to validate
         subscriber";
    }
    leaf daps-waiting-clients {
      type uint32;
      description
        "Number of clients waiting on DAPS to assign/free
         prefix(ND)";
    }
    leaf msg-waiting-clients {
      type uint32;
      description
        "Number of clients waiting for a message from the
         client/server";
    }
    leaf iedge-waiting-clients {
      type uint32;
      description
        "Number of clients waiting on iedge to subscriber
         session";
    }
    leaf rib-waiting-clients {
      type uint32;
      description
        "Number of clients in waiting on RIB response";
    }
    leaf bound-clients {
      type uint32;
      description
        "Number of clients in bound state";
    }
  }

  grouping IPV6-DHCPV6D-PROXY-BINDINGS-SUMMARY {
    description
      "DHCPv6 proxy bindings summary";
    container iana {
      description
        "IANA proxy binding summary";
      uses BAG-DHCPV6D-PROXY-BINDINGS-SUMMARY;
    }
    container iapd {
      description
        "IAPD proxy binding summary";
      uses BAG-DHCPV6D-PROXY-BINDINGS-SUMMARY;
    }
    leaf clients {
      type uint32;
      description
        "Total number of clients";
    }
  }

  grouping BAG-DHCPV6D-ADDR-ATTRB {
    description
      "BAG DHCPV6D ADDR ATTRB";
    list bag-dhcpv6d-addr-attrb {
      description
        "bag dhcpv6d addr attrb";
      leaf prefix {
        type inet:ipv6-address;
        description
          "IPv6 prefix";
      }
      leaf prefix-length {
        type uint8;
        description
          "Prefix length";
      }
      leaf lease-time {
        type uint32;
        units "second";
        description
          "Lease time in seconds";
      }
      leaf remaining-lease-time {
        type uint32;
        units "second";
        description
          "Remaining lease time in seconds";
      }
    }
  }

  grouping BAG-DHCPV6D-IA-ID-PD-INFO {
    description
      "BAG DHCPV6D IA ID PD INFO";
    list bag-dhcpv6d-ia-id-pd-info {
      description
        "bag dhcpv6d ia id pd info";
      container addresses {
        description
          "List of addresses in this IA";
        uses BAG-DHCPV6D-ADDR-ATTRB;
      }
      leaf ia-type {
        type Bag-dhcpv6d-ia-id;
        description
          "IA type";
      }
      leaf ia-id {
        type uint32;
        description
          "IA_ID of this IA";
      }
      leaf flags {
        type uint32;
        description
          "FSM Flag for this IA";
      }
      leaf total-address {
        type uint16;
        description
          "Total address in this IA";
      }
      leaf state {
        type Bag-dhcpv6d-fsm-state;
        description
          "State";
      }
    }
  }

  grouping IPV6-DHCPV6D-PROXY-BINDING {
    description
      "DHCPv6 proxy binding entry";
    container ia-id-pd {
      description
        "List of DHCPv6 IA_ID/PDs";
      uses BAG-DHCPV6D-IA-ID-PD-INFO;
    }
    leaf duid {
      type string;
      description
        "Client DUID";
    }
    leaf client-flag {
      type uint32;
      description
        "DHCPV6 client flag";
    }
    leaf subscriber-label {
      type uint32;
      description
        "DHCPV6 subscriber label";
    }
    leaf vrf-name {
      type string {
        length "0..33";
      }
      description
        "DHCPVV6 client/subscriber VRF name";
    }
    leaf mac-address {
      type string;
      description
        "Client MAC address";
    }
    leaf ia-id-p-ds {
      type uint32;
      description
        "Number of ia_id/pd";
    }
    leaf interface-name {
      type xr:Interface-name;
      description
        "DHCPV6 access interface to client";
    }
    leaf access-vrf-name {
      type string {
        length "0..33";
      }
      description
        "DHCPV6 access VRF name to client";
    }
    leaf proxy-binding-tags {
      type uint8;
      description
        "DHCPV6 VLAN tag count";
    }
    leaf proxy-binding-outer-tag {
      type uint32;
      description
        "DHCPV6 VLAN Outer VLAN";
    }
    leaf proxy-binding-inner-tag {
      type uint32;
      description
        "DHCPV6 VLAN Inner VLAN";
    }
    leaf class-name {
      type string {
        length "0..64";
      }
      description
        "DHCPV6 class name";
    }
    leaf pool-name {
      type string {
        length "0..64";
      }
      description
        "DHCPV6 pool name";
    }
    leaf rx-remote-id {
      type string {
        length "0..771";
      }
      description
        "DHCPV6 received Remote ID";
    }
    leaf tx-remote-id {
      type string {
        length "0..771";
      }
      description
        "DHCPV6 transmitted Remote ID";
    }
    leaf rx-interface-id {
      type string {
        length "0..771";
      }
      description
        "DHCPV6 received Interface ID";
    }
    leaf tx-interface-id {
      type string {
        length "0..771";
      }
      description
        "DHCPV6 transmitted Interface ID";
    }
    leaf server-ipv6-address {
      type Ipv6-address;
      description
        "DHCPV6 server IPv6 address";
    }
    leaf profile-name {
      type string {
        length "0..65";
      }
      description
        "DHCPV6 profile name";
    }
    leaf framed-ipv6-prefix {
      type Ipv6-address;
      description
        "DHCPV6 framed ipv6 addess used by ND";
    }
    leaf framed-prefix-length {
      type uint8;
      description
        "DHCPV6 framed ipv6 prefix length used by ND";
    }
    leaf is-nak-next-renew {
      type boolean;
      description
        "Is true if DHCP next renew from client will be
         NAK'd";
    }
    leaf srg-state {
      type uint32;
      description
        "DHCPV6 SRG state";
    }
    leaf srg-intf-role {
      type uint32;
      description
        "DHCPV6 SRG Intf Role";
    }
    leaf srgp2p {
      type boolean;
      description
        "SRG P2P Status";
    }
    leaf srg-vrf-name {
      type string {
        length "0..33";
      }
      description
        "DHCPV6 SRG VRF NAME";
    }
    leaf serg-state {
      type uint32;
      description
        "DHCPV6 SERG state";
    }
    leaf serg-intf-role {
      type uint32;
      description
        "DHCPV6 SERG Intf Role";
    }
  }

  grouping IPV6-DHCPV6D-PROXY-STATS {
    description
      "DHCPv6 proxy statistics";
    list ipv6-dhcpv6d-proxy-stat {
      description
        "ipv6 dhcpv6d proxy stat";
      container statistics {
        description
          "Proxy statistics";
        uses IPV6-DHCPV6D-FILTERED-STATS;
      }
      leaf vrf-name {
        type string {
          length "0..33";
        }
        description
          "DHCPv6 L3 VRF name";
      }
    }
  }

  grouping IPV6-DHCPV6D-PROXY-INTERFACE {
    description
      "DHCPv6 proxy interface";
    leaf proxy-vrf-name {
      type string {
        length "0..33";
      }
      description
        "VRF name";
    }
    leaf proxy-interface-mode {
      type Bag-dhcpv6d-sub-mode;
      description
        "Mode of interface";
    }
    leaf is-proxy-interface-ambiguous {
      type uint32;
      description
        "Is interface ambiguous";
    }
    leaf proxy-interface-profile-name {
      type string {
        length "0..65";
      }
      description
        "Name of profile attached to the interface";
    }
    leaf proxy-interface-lease-limit-type {
      type Lease-limit;
      description
        "Lease limit type on interface";
    }
    leaf proxy-interface-lease-limits {
      type uint32;
      description
        "Lease limit count on interface";
    }
    leaf srg-role {
      type Bag-dhcpv6d-intf-srg-role;
      description
        "DHCPv6 Interface SRG role";
    }
    leaf serg-role {
      type Bag-dhcpv6d-intf-serg-role;
      description
        "DHCPv6 Interface SERG role";
    }
    leaf mac-throttle {
      type boolean;
      description
        "Mac Throttle Status";
    }
    leaf srg-vrf-name {
      type string {
        length "0..33";
      }
      description
        "SRG VRF name";
    }
    leaf srgp2p {
      type boolean;
      description
        "SRG P2P Status";
    }
  }

  grouping IPV6-DHCPV6D-PROXY-INTERFACE-REFERENCE {
    description
      "DHCPv6 proxy profile reference";
    list ipv6-dhcpv6d-proxy-interface-reference {
      description
        "ipv6 dhcpv6d proxy interface reference";
      leaf proxy-reference-interface-name {
        type string {
          length "0..65";
        }
        description
          "Interface name";
      }
    }
  }

  grouping IPV6-DHCPV6D-PROXY-VRF-REFERENCE {
    description
      "DHCPv6 proxy profile reference";
    list ipv6-dhcpv6d-proxy-vrf-reference {
      description
        "ipv6 dhcpv6d proxy vrf reference";
      leaf proxy-reference-vrf-name {
        type string {
          length "0..33";
        }
        description
          "VRF name";
      }
    }
  }

  grouping IPV6-DHCPV6D-PROXY-IID-REFERENCE {
    description
      "DHCPv6 proxy profile iid reference";
    list ipv6-dhcpv6d-proxy-iid-reference {
      description
        "ipv6 dhcpv6d proxy iid reference";
      leaf proxy-iid-interface-name {
        type string {
          length "0..65";
        }
        description
          "Interface name for interface id";
      }
      leaf proxy-interface-id {
        type string {
          length "0..257";
        }
        description
          "Interface id";
      }
    }
  }

  grouping IPV6-DHCPV6D-PROXY-PROFILE {
    description
      "DHCPv6 proxy profile parameters";
    container interface-id-references {
      description
        "Interface id references";
      uses IPV6-DHCPV6D-PROXY-IID-REFERENCE;
    }
    container vrf-references {
      description
        "VRF references";
      uses IPV6-DHCPV6D-PROXY-VRF-REFERENCE;
    }
    container interface-references {
      description
        "Interface references";
      uses IPV6-DHCPV6D-PROXY-INTERFACE-REFERENCE;
    }
    leaf profile-name {
      type string {
        length "0..65";
      }
      description
        "Proxy profile name";
    }
    leaf remote-id {
      type string {
        length "0..257";
      }
      description
        "Remote id";
    }
    leaf profile-link-address {
      type Ipv6-address;
      description
        "Link address";
    }
    leaf proxy-profile-linkaddress-from-ra-enable {
      type boolean;
      description
        "LinkAddress From RA mesage";
    }
    leaf-list profile-helper-address {
      type Ipv6-address;
      max-elements "8";
      description
        "Helper addresses";
    }
    leaf-list vrf-name {
      type String-vrf;
      max-elements "8";
      description
        "VRF names";
    }
    leaf-list interface-name {
      type String-ifname;
      max-elements "8";
      description
        "Interface names";
    }
  }

  grouping IPV6-DHCPV6D-MAC-THROTTLE {
    description
      "IPv6 DHCP Mac Throttle";
    leaf binding-chaddr {
      type yang:hex-string;
      description
        "Client MAC address";
    }
    leaf ifname {
      type string {
        length "0..65";
      }
      description
        "DHCP access interface";
    }
    leaf state {
      type uint32;
      description
        "State of entry";
    }
    leaf time-left {
      type uint32;
      units "second";
      description
        "Time Left in secs";
    }
  }

  grouping IPV6-DHCPV6D-FILTERED-STATS {
    description
      "DHCPv6 filtered statistics";
    leaf received-packets {
      type uint64;
      description
        "Received packets";
    }
    leaf transmitted-packets {
      type uint64;
      description
        "Transmitted packets";
    }
    leaf dropped-packets {
      type uint64;
      description
        "Dropped packets";
    }
  }

  grouping IPV6-DHCPV6D-TYPE {
    description
      "DHCPv6 packets";
    container solicit {
      description
        "DHCPV6 solicit packets";
      uses IPV6-DHCPV6D-FILTERED-STATS;
    }
    container advertise {
      description
        "DHCPV6 advertise packets";
      uses IPV6-DHCPV6D-FILTERED-STATS;
    }
    container request {
      description
        "DHCPV6 request packets";
      uses IPV6-DHCPV6D-FILTERED-STATS;
    }
    container reply {
      description
        "DHCPV6 reply packets";
      uses IPV6-DHCPV6D-FILTERED-STATS;
    }
    container confirm {
      description
        "DHCPV6 confirm packets";
      uses IPV6-DHCPV6D-FILTERED-STATS;
    }
    container decline {
      description
        "DHCPV6 decline packets";
      uses IPV6-DHCPV6D-FILTERED-STATS;
    }
    container renew {
      description
        "DHCPV6 renew packets";
      uses IPV6-DHCPV6D-FILTERED-STATS;
    }
    container rebind {
      description
        "DHCPV6 rebind packets";
      uses IPV6-DHCPV6D-FILTERED-STATS;
    }
    container release {
      description
        "DHCPV6 release packets";
      uses IPV6-DHCPV6D-FILTERED-STATS;
    }
    container reconfig {
      description
        "DHCPV6 reconfig packets";
      uses IPV6-DHCPV6D-FILTERED-STATS;
    }
    container inform {
      description
        "DHCPV6 inform packets";
      uses IPV6-DHCPV6D-FILTERED-STATS;
    }
    container relay-forward {
      description
        "DHCPV6 relay forward packets";
      uses IPV6-DHCPV6D-FILTERED-STATS;
    }
    container relay-reply {
      description
        "DHCPV6 relay reply packets";
      uses IPV6-DHCPV6D-FILTERED-STATS;
    }
    container lease-query {
      description
        "DHCPV6 lease query packets";
      uses IPV6-DHCPV6D-FILTERED-STATS;
    }
    container lease-query-reply {
      description
        "DHCPV6 lease query reply packets";
      uses IPV6-DHCPV6D-FILTERED-STATS;
    }
    container lease-query-done {
      description
        "DHCPV6 lease query done packets";
      uses IPV6-DHCPV6D-FILTERED-STATS;
    }
    container lease-query-data {
      description
        "DHCPV6 lease query data packets";
      uses IPV6-DHCPV6D-FILTERED-STATS;
    }
  }

  grouping IPV6-DHCPD-ISSU-STATUS {
    description
      "ISSU Data";
    leaf process-start-time {
      type uint64;
      units "nanosecond";
      description
        "Timestamp for the process start time in
         nanoseconds since Epoch, i.e. since 00:00:00 UTC
         , January 1, 1970";
    }
    leaf issu-sync-complete-time {
      type uint64;
      units "nanosecond";
      description
        "Timestamp for the ISSU sync complete in
         nanoseconds since Epoch, i.e. since 00:00:00 UTC
         , January 1, 1970";
    }
    leaf issu-sync-start-time {
      type uint64;
      units "nanosecond";
      description
        "Timestamp for the ISSU sync start in nanoseconds
         since Epoch, i.e. since 00:00:00 UTC, January 1,
         1970";
    }
    leaf issu-ready-time {
      type uint64;
      units "nanosecond";
      description
        "Timestamp for the ISSU ready declaration in
         nanoseconds since Epoch, i.e. since 00:00:00 UTC
         , January 1, 1970";
    }
    leaf big-bang-time {
      type uint64;
      units "nanosecond";
      description
        "Timestamp for the Big Bang notification time in
         nanoseconds since Epoch, i.e. since 00:00:00 UTC
         , January 1, 1970";
    }
    leaf primary-role-time {
      type uint64;
      units "nanosecond";
      description
        "Timestamp for the change to Primary role
         notification time in nanoseconds since Epoch, i
         .e. since 00:00:00 UTC, January 1, 1970";
    }
    leaf issu-ready-issu-mgr-connection {
      type boolean;
      description
        "Whether or not DHCP is currently connected to
         ISSU Manager during the ISSU Load Phase";
    }
    leaf role {
      type Dhcpv6-issu-role;
      description
        "The current role of the DHCP process";
    }
    leaf phase {
      type Dhcp-issu-phase;
      description
        "The current ISSU phase of the DHCP process";
    }
    leaf version {
      type Dhcpv6-issu-version;
      description
        "The current version of the DHCP process in the
         context of an ISSU";
    }
  }
}
