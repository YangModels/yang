submodule Cisco-IOS-XR-ppp-ma-oper-sub2 {
  belongs-to Cisco-IOS-XR-ppp-ma-oper {
    prefix Cisco-IOS-XR-ppp-ma-oper;
  }

  import Cisco-IOS-XR-types {
    prefix xr;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR ppp-ma package operational data.
     
     Copyright (c) 2013-2017 by Cisco Systems, Inc.
     All rights reserved.";

  revision 2015-11-09 {
    description
      "IOS XR 6.0 revision.";
  }

  typedef Ppp-lcp-mp-mbr-state {
    type enumeration {
      enum "ppp-lcp-mp-mbr-state-detached" {
        description
          "Detached member";
      }
      enum "ppp-lcp-mp-mbr-state-lcp-not-negotiated" {
        description
          "LCP has not been negotiated";
      }
      enum "ppp-lcp-mp-mbr-state-link-noise" {
        description
          "Link Noise detected";
      }
      enum "ppp-lcp-mp-mbr-state-bundle-shutdown" {
        description
          "Multilink Bundle is shutdown";
      }
      enum "ppp-lcp-mp-mbr-state-mrru-rejected" {
        description
          "MRRU has been rejected";
      }
      enum "ppp-lcp-mp-mbr-state-mrru-mismatch" {
        description
          "MRRU mismatch";
      }
      enum "ppp-lcp-mp-mbr-state-ed-mismatch" {
        description
          "ED mismatch";
      }
      enum "ppp-lcp-mp-mbr-state-auth-name-mismatch" {
        description
          "Authenticated name mismatch";
      }
      enum "ppp-lcp-mp-mbr-state-mcmp-rejected" {
        description
          "MCMP option rejected by peer";
      }
      enum "ppp-lcp-mp-mbr-state-mcmp-not-negotiated" {
        description
          "MCMP option not negotiated";
      }
      enum "ppp-lcp-mp-mbr-state-mcmp-local-mismatch" {
        description
          "Local MCMP class mismatch";
      }
      enum "ppp-lcp-mp-mbr-state-mcmp-peer-mismatch" {
        description
          "Peer MCMP class mismatch";
      }
      enum "ppp-lcp-mp-mbr-state-standby-up" {
        description
          "SSO Standby up";
      }
      enum "ppp-lcp-mp-mbr-state-active" {
        description
          "Active member";
      }
    }
    description
      "MP member states";
  }

  typedef Ppp-sso-fsm-state {
    type enumeration {
      enum "ppp-sso-state-not-ready-0" {
        value 0;
        description
          "Not ready";
      }
      enum "ppp-sso-state-standby-unnegd-1" {
        value 1;
        description
          "S UnNegd";
      }
      enum "ppp-sso-state-active-down-2" {
        value 2;
        description
          "A Down";
      }
      enum "ppp-sso-state-deactivating-3" {
        value 3;
        description
          "Deactivating";
      }
      enum "ppp-sso-state-active-unnegd-4" {
        value 4;
        description
          "A UnNegd";
      }
      enum "ppp-sso-state-standby-negd-5" {
        value 5;
        description
          "S Negd";
      }
      enum "ppp-sso-state-activating-6" {
        value 6;
        description
          "Activating";
      }
      enum "ppp-sso-state-active-negd-7" {
        value 7;
        description
          "A Negd";
      }
    }
    description
      "Ppp sso fsm state";
  }

  typedef Ppp-fsm-state {
    type enumeration {
      enum "ppp-fsm-state-initial-0" {
        value 0;
        description
          "Connection Idle";
      }
      enum "ppp-fsm-state-starting-1" {
        value 1;
        description
          "This layer required, but lower layer down";
      }
      enum "ppp-fsm-state-closed-2" {
        value 2;
        description
          "Lower layer up, but this layer not required";
      }
      enum "ppp-fsm-state-stopped-3" {
        value 3;
        description
          "Listening for a Config Request";
      }
      enum "ppp-fsm-state-closing-4" {
        value 4;
        description
          "Shutting down due to local change";
      }
      enum "ppp-fsm-state-stopping-5" {
        value 5;
        description
          "Shutting down due to peer's actions";
      }
      enum "ppp-fsm-state-req-sent-6" {
        value 6;
        description
          "Config Request Sent";
      }
      enum "ppp-fsm-state-ack-rcvd-7" {
        value 7;
        description
          "Config Ack Received";
      }
      enum "ppp-fsm-state-ack-sent-8" {
        value 8;
        description
          "Config Ack Sent";
      }
      enum "ppp-fsm-state-opened-9" {
        value 9;
        description
          "Connection Open";
      }
    }
    description
      "Ppp fsm state";
  }

  typedef Im-state {
    type uint32;
    description
      "Im state";
  }

  typedef Ncp-ident {
    type enumeration {
      enum "cdpcp" {
        value 1;
        description
          "CDP control protocol";
      }
      enum "ipcp" {
        value 2;
        description
          "IPv4 control protocol";
      }
      enum "ipcpiw" {
        value 3;
        description
          "IPv4 Interworking control protocol";
      }
      enum "ipv6cp" {
        value 4;
        description
          "IPv6 control protocol";
      }
      enum "mplscp" {
        value 5;
        description
          "MPLS control protocol";
      }
      enum "osicp" {
        value 6;
        description
          "OSI (CLNS) control protocol";
      }
    }
    description
      "Ncp ident";
  }

  grouping PPP-OPER-SSO-FSM-STATE {
    description
      "PPP SSO FSM State";
    leaf is-running {
      type boolean;
      description
        "Is SSO FSM Running";
    }
    leaf state {
      type Ppp-sso-fsm-state;
      description
        "SSO FSM State";
    }
  }

  grouping PPP-OPER-SSO-STATE {
    description
      "PPP SSO State";
    container lcp-state {
      description
        "LCP SSO State";
      uses PPP-OPER-SSO-FSM-STATE;
    }
    container of-us-auth-state {
      description
        "Of-us Authentication SSO State";
      uses PPP-OPER-SSO-FSM-STATE;
    }
    container of-peer-auth-state {
      description
        "Of-peer Authentication SSO State";
      uses PPP-OPER-SSO-FSM-STATE;
    }
    container ipcp-state {
      description
        "IPCP SSO State";
      uses PPP-OPER-SSO-FSM-STATE;
    }
    leaf session-id-xr {
      type uint32;
      description
        "SSRP Session ID";
    }
    leaf interface {
      type xr:Interface-name;
      description
        "Interface";
    }
  }

  grouping PPP-OPER-SSO-SUMMARY-STATES {
    description
      "Summary of SSO FSM States";
    leaf total {
      type uint16;
      description
        "Total number of SSO FSMs running";
    }
    leaf-list count {
      type uint16;
      max-elements "8";
      description
        "Number of SSO FSMs in each State";
    }
  }

  grouping PPP-OPER-SSO-SUMMARY {
    description
      "PPP SSO Summary information";
    container lcp-states {
      description
        "LCP SSO FSM States";
      uses PPP-OPER-SSO-SUMMARY-STATES;
    }
    container of-us-auth-states {
      description
        "Of-us Authentication SSO FSM States";
      uses PPP-OPER-SSO-SUMMARY-STATES;
    }
    container of-peer-auth-states {
      description
        "Of-peer Authentication SSO FSM States";
      uses PPP-OPER-SSO-SUMMARY-STATES;
    }
    container ipcp-states {
      description
        "IPCP SSO FSM States";
      uses PPP-OPER-SSO-SUMMARY-STATES;
    }
  }

  grouping PPP-OPER-SSO-ERROR {
    description
      "PPP SSO Error";
    leaf is-error {
      type boolean;
      description
        "Is SSO Error";
    }
    leaf error {
      type uint32;
      description
        "SSO Error";
    }
    leaf context {
      type uint32;
      description
        "Context";
    }
  }

  grouping PPP-OPER-SSO-ALERTS {
    description
      "PPP SSO Alerts information";
    container lcp-error {
      description
        "LCP SSO Error";
      uses PPP-OPER-SSO-ERROR;
    }
    container of-us-auth-error {
      description
        "Of-us Authentication SSO Error";
      uses PPP-OPER-SSO-ERROR;
    }
    container of-peer-auth-error {
      description
        "Of-peer Authentication SSO Error";
      uses PPP-OPER-SSO-ERROR;
    }
    container ipcp-error {
      description
        "IPCP SSO Error";
      uses PPP-OPER-SSO-ERROR;
    }
  }
}
