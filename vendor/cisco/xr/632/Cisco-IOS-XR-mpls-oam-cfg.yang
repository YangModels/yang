module Cisco-IOS-XR-mpls-oam-cfg {
  namespace "http://cisco.com/ns/yang/Cisco-IOS-XR-mpls-oam-cfg";
  prefix mpls-oam-cfg;

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR mpls-oam package configuration.
     
     This module contains definitions
     for the following management objects:
       mpls-oam: MPLS LSP verification configuration
     
     Copyright (c) 2013-2017 by Cisco Systems, Inc.
     All rights reserved.";

  revision 2015-11-09 {
    description
      "IOS XR 6.0 revision.";
  }

  container mpls-oam {
    description
      "MPLS LSP verification configuration";
    container reply-mode {
      description
        "Echo request reply mode attributes";
      container control-channel {
        description
          "Configure control channel reply mode";
        leaf allow-reverse-lsp {
          type empty;
          description
            "Use Reverse LSP as the control channel";
        }
      }
    }
    leaf enable-oam {
      type empty;
      description
        "Enable/Disable MPLS OAM globally.Without
         creating this object the MPLS OAM feature will
         not be enabled. Deleting this object will stop
         the MPLS OAM feature.";
    }
    leaf disable-vendor-extension {
      type empty;
      description
        "Disable vendor extension";
    }
  }
}
