module Cisco-IOS-XR-sysadmin-ethsw-esdma-trunk {
  namespace "http://www.cisco.com/ns/yang/Cisco-IOS-XR-sysadmin-ethsw-esdma-trunk";
  prefix esdma_trunk;

  import tailf-common {
    prefix tailf;
  }
  import Cisco-IOS-XR-sysadmin-ethsw-esdma-types {
    prefix esdma_types;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains the YANG definitions
     for the Cisco IOS-XR SysAdmin
     'show controller switch trunk' command.
     
     Copyright(c) 2011-2017 by Cisco Systems, Inc.
     All rights reserved.";

  revision 2017-05-01 {
    description
      "Namespace change to comply with Cisco guidelines on namespace";
  }
  revision 2016-07-06 {
    description
      "Initial revision with content extracted from esdma_cli.yang.";
  }

  grouping switch-trunk-group {
    container trunk {
      tailf:callpoint "esdma_switch_trunk_summary";
      tailf:info "Display the switch trunk group information";
      list location {
        key "rack card switch-id";
        tailf:info "Location information for switch trunk group information";
        tailf:cli-full-command;
        tailf:cli-key-format "$(1)/$(2)/$(3)";
        tailf:cli-suppress-table;
        tailf:cli-show-template "$(trunk-member-port-iter|show)";
        leaf rack {
          type esdma_types:esdma-rack-num-enum;
          description
            "Rack to display the switch trunk group information for";
        }
        leaf card {
          type esdma_types:esdma-cpu;
          description
            "Card to display the switch trunk group information for";
        }
        leaf switch-id {
          type esdma_types:esdma-switch-type-enum;
          description
            "Switch type to display the switch trunk group information for";
        }
        leaf trunk-member-count {
          type uint32;
          description
            "Number of member ports in the trunk group";
          tailf:cli-suppress-show-path;
          tailf:cli-suppress-show-match;
        }
        leaf trunk-name {
          type string;
          description
            "Name of the trunk group";
          tailf:cli-suppress-show-path;
          tailf:cli-suppress-show-match;
        }
        list trunk-member-port-iter {
          key "trunk-member-port";
          tailf:cli-drop-node-name;
          tailf:cli-table-legend
            "$(../trunk-name) Port Membership Information
             
             Rack  Card  Switch
             ------------------
             $(../rack|ljust:4)  $(../card|ljust:4)  $(../switch-id|ljust:6)
            ";
          tailf:cli-enforce-table;
          tailf:cli-table-footer
            "
             Total number of trunk group member ports: $(../trunk-member-count)";
          leaf trunk-member-port {
            type uint32;
            description
              "Trunk Member Port";
            tailf:cli-suppress-show-path;
            tailf:cli-suppress-show-match;
            tailf:display-column-name "Member Port";
            tailf:cli-value-display-template "$(.==255?-:$(.))";
          }
          leaf trunk-member-status {
            type esdma_types:esdma-trunk-member-status;
            description
              "Trunk Member Status";
            tailf:cli-suppress-show-path;
            tailf:cli-suppress-show-match;
            tailf:display-column-name "Status";
          }
        }
      }
    }
  }
  tailf:id "http://cisco.com/panini/calvados/esdma/esdma_trunk";
}
