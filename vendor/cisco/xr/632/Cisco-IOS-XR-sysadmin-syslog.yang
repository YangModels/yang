module Cisco-IOS-XR-sysadmin-syslog {
  namespace "http://www.cisco.com/ns/yang/Cisco-IOS-XR-sysadmin-syslog";
  prefix syslog;

  import tailf-common {
    prefix tailf;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains a collection of YANG
     definitions for Cisco IOS-XR SysAdmin configuration.
     
     This module defines configuration for
     sysadmin syslog infrastructure.
     
     Copyright(c) 2010-2016 by Cisco Systems, Inc.
     All rights reserved.";

  revision 2017-05-09 {
    description
      "Namespace change to comply with Cisco guidelines";
  }
  revision 2016-09-16 {
    description
      "Added new type for show logging host";
  }

  typedef num-lines-type {
    type uint32;
    tailf:info "nlines;;Number of last lines to Display";
  }

  typedef dir-or-file-path-type {
    type string;
    tailf:info "path;;Host directory or file path";
  }

  grouping syslog-grp {
    container console {
      description
        "Syslog Infrastructure";
      tailf:info "Modify message logging facilities";
      choice disable_or_severity {
        mandatory false;
        case choice_emergency {
          leaf emergency {
            type empty;
            tailf:info "System is unusable                 (severity=0)";
          }
        }
        case choice_alert {
          leaf alert {
            type empty;
            tailf:info "Immediate action needed            (severity=1)";
          }
        }
        case choice_critical {
          leaf critical {
            type empty;
            tailf:info "Critical conditions                (severity=2)";
          }
        }
        case choice_error {
          leaf error {
            type empty;
            tailf:info "Error conditions                   (severity=3)";
          }
        }
        case choice_warning {
          leaf warning {
            type empty;
            tailf:info "Warning conditions       (severity=4) [default]";
          }
        }
        case choice_notice {
          leaf notice {
            type empty;
            tailf:info "Normal but significant conditions  (severity=5)";
          }
        }
        case choice_informational {
          leaf informational {
            type empty;
            tailf:info "Informational messages             (severity=6)";
          }
        }
        case choice_debug {
          leaf debug {
            type empty;
            tailf:info "Debugging messages                 (severity=7)";
          }
        }
        case choice_disable {
          leaf disable {
            type empty;
            tailf:info "Disable logging";
          }
        }
      }
    }
  }
  tailf:id "http://cisco.com/calvados/syslog";
}
