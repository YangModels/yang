module Cisco-IOS-XR-sysadmin-tacacs-test-tacacs {
  namespace "http://www.cisco.com/ns/yang/Cisco-IOS-XR-sysadmin-tacacs-test-tacacs";
  prefix test_tacacs;

  import tailf-common {
    prefix tailf;
  }
  import Cisco-IOS-XR-sysadmin-tacacs-tacacs-server {
    prefix tacacs-server;
  }

  organization
    "Cisco Systems Inc.";
  contact
    "aaa-ng-tacacs-dev@cisco.com";
  description
    "This clie part is for test commands for tacacs";

  revision 2017-05-10 {
    description
      "Namespace changed from test_tacacs to Cisco-IOS-XR-sysadmin-tacacs-test-tacacs";
  }
  revision 2015-07-07 {
    description
      "Initial revision";
  }

  augment "/tacacs-server:tacacs-server" {
    container test-authentication {
      presence "";
      config false;
      tailf:hidden "full";
      tailf:cli-incomplete-command;
      tailf:callpoint "test_tacacs_authentication";
      tailf:info "Test tacacs-server authentication";
      tailf:cli-show-template
        "
         Test command 
          Authentication through tacacs+ : $(authentication)
        ";
      leaf authentication {
        type string;
        mandatory false;
        description
          "Authentication";
        tailf:cli-suppress-show-path;
      }
    }
    container test-authorization {
      presence "";
      config false;
      tailf:hidden "full";
      tailf:cli-incomplete-command;
      tailf:callpoint "test_tacacs_authorization";
      tailf:info "Test tacacs-server authorization";
      tailf:cli-show-template
        "
         Test command 
          Authorization through tacacs+  : $(authorization)
        ";
      leaf authorization {
        type string;
        mandatory false;
        description
          "Authorization";
        tailf:cli-suppress-show-path;
      }
    }
    container test-accounting {
      presence "";
      config false;
      tailf:hidden "full";
      tailf:cli-incomplete-command;
      tailf:callpoint "test_tacacs_accounting";
      tailf:info "Test tacacs-server accounting";
      tailf:cli-show-template
        "
         Test command 
          accounting through tacacs+  : $(accounting)
        ";
      leaf accounting {
        type string;
        mandatory false;
        description
          "Accounting";
        tailf:cli-suppress-show-path;
      }
    }
  }
  tailf:id "http://www.cisco.com/calvados/test_tacacs";
}
