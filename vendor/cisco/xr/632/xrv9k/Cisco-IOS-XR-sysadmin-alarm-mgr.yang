module Cisco-IOS-XR-sysadmin-alarm-mgr {
  namespace "http://www.cisco.com/ns/yang/Cisco-IOS-XR-sysadmin-alarm-mgr";
  prefix alarms;

  import tailf-common {
    prefix tailf;
  }
  import ietf-yang-types {
    prefix yang;
  }
  import Cisco-IOS-XR-sysadmin-types {
    prefix calvados;
  }
  import Cisco-IOS-XR-sysadmin-show-trace {
    prefix show_trace;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains a collection of YANG
     definitions for Cisco IOS-XR SysAdmin configuration.
     
     Alarm management YANG model
     
     Copyright(c) 2011-2017 by Cisco Systems, Inc.
     All rights reserved.";

  revision 2017-04-12 {
    description
      "Changed the namespace and module name";
  }
  revision 2012-03-27 {
    description
      "Initial Revision";
  }

  typedef severity_td {
    type enumeration {
      enum "unknown" {
        value 0;
      }
      enum "not_reported" {
        value 1;
      }
      enum "not_alarmed" {
        value 2;
      }
      enum "minor" {
        value 3;
      }
      enum "major" {
        value 4;
      }
      enum "critical" {
        value 5;
      }
    }
    description
      "The severity enumeration type of an alarm ";
  }

  typedef status_td {
    type enumeration {
      enum "unknown" {
        value 0;
      }
      enum "set" {
        value 1;
      }
      enum "clear" {
        value 2;
      }
      enum "suppress" {
        value 3;
      }
    }
    description
      "The status enumeration type of an alarm ";
  }

  typedef group_td {
    type enumeration {
      enum "unknown" {
        value 0;
      }
      enum "environ" {
        value 1;
      }
      enum "ethernet" {
        value 2;
      }
      enum "fabric" {
        value 3;
      }
      enum "power" {
        value 4;
      }
      enum "software" {
        value 5;
      }
      enum "slice" {
        value 7;
      }
      enum "cpu" {
        value 8;
      }
      enum "controller" {
        value 9;
      }
      enum "sonet" {
        value 10;
      }
      enum "otn" {
        value 11;
      }
      enum "sdh_controller" {
        value 12;
      }
      enum "asic" {
        value 13;
      }
      enum "fpd_infra" {
        value 14;
      }
      enum "shelf" {
        value 15;
      }
      enum "mpa" {
        value 16;
      }
      enum "ots" {
        value 17;
      }
      enum "timing" {
        value 18;
      }
      enum "last" {
        value 19;
      }
    }
    description
      "The group enumeration type of an alarm ";
  }

  typedef agent_state_td {
    type enumeration {
      enum "start" {
        value 0;
      }
      enum "init" {
        value 1;
      }
      enum "connecting" {
        value 2;
      }
      enum "connected" {
        value 3;
      }
      enum "registered" {
        value 4;
      }
      enum "disconnected" {
        value 5;
      }
    }
  }

  typedef agent_type_td {
    type enumeration {
      enum "unknown" {
        value 0;
      }
      enum "producer" {
        value 1;
      }
      enum "consumer" {
        value 2;
      }
      enum "subscriber" {
        value 3;
      }
    }
  }

  typedef timestamp_td {
    type yang:date-and-time;
    description
      "The Alarm timestamp type for all times in alarm";
  }

  grouping alarmBasicFilters {
    leaf aid {
      type string;
      description
        "The AID for the current alarm";
      tailf:cli-suppress-show-path;
      tailf:cli-suppress-show-match;
      tailf:display-column-name "Alarm Id";
      tailf:info "Alarm identifier";
    }
    leaf tag {
      type string;
      description
        "The Fault Tag for the current alarm";
      tailf:cli-suppress-show-path;
      tailf:cli-suppress-show-match;
      tailf:display-column-name "Tag";
      tailf:info "Tag identifier";
    }
    leaf module {
      type string;
      description
        "The Module for the current alarm";
      tailf:cli-suppress-show-path;
      tailf:cli-suppress-show-match;
      tailf:display-column-name "Module";
      tailf:info "Module identifier";
    }
    leaf gen_location {
      type string;
      description
        "The location for the current alarm";
      tailf:cli-suppress-show-path;
      tailf:cli-suppress-show-match;
      tailf:display-column-name "location";
      tailf:info "Alarm location";
    }
    leaf eid {
      type string;
      description
        "The Object Id for the current alarm";
      tailf:cli-suppress-show-path;
      tailf:cli-suppress-show-match;
      tailf:display-column-name "Alarm Object Id";
      tailf:info "Alarm identifier";
    }
    leaf severity {
      type severity_td;
      description
        "The alarm severity.";
      tailf:display-column-name "severity";
      tailf:info "The current severity of the bi-state alarm";
    }
    leaf group {
      type group_td;
      description
        "The alarm grouping ";
      tailf:display-column-name "group";
      tailf:info "The group to which this alarm is assigned";
    }
    leaf description {
      type string;
      description
        "Alarm description";
      tailf:cli-suppress-show-path;
      tailf:cli-suppress-show-match;
      tailf:display-column-name "description";
      tailf:info "A brief description about the alarm.";
    }
    leaf set_time {
      type string;
      description
        "Alarm set time stamp";
      tailf:cli-suppress-show-path;
      tailf:cli-suppress-show-match;
      tailf:display-column-name "set time";
      tailf:info "Alarm set time.";
    }
  }

  grouping alarmBasicHistoryFilters {
    leaf clear_time {
      type string;
      description
        "Alarm clear time stamp";
      tailf:cli-suppress-show-path;
      tailf:cli-suppress-show-match;
      tailf:display-column-name "clear time";
      tailf:info "Alarm clear time.";
    }
  }

  grouping alarmBasicSuppressedFilters {
    leaf suppressed_time {
      type string;
      description
        "Alarm suppressed time stamp";
      tailf:cli-suppress-show-path;
      tailf:cli-suppress-show-match;
      tailf:display-column-name "suppressed time";
      tailf:info "The time at which the alarm is suppressed.";
    }
  }

  grouping alarmExtFilters {
    leaf state {
      type status_td;
      description
        "The current state of the bi-state alarm";
      tailf:display-column-name "bi-state";
      tailf:info "The current state of the bi-state alarm";
    }
    leaf reporting_agent_id {
      type uint32;
      description
        "The reporting agent id.";
      tailf:display-column-name "agent-id";
      tailf:info "The reporting agent id.";
    }
    leaf resynced {
      type uint32;
      description
        "The condition bit-flags of the alarm";
      tailf:display-column-name "resynced";
      tailf:info "The condition bit-flags of the alarm, 0-Resync";
    }
    leaf detail_desc {
      type string;
      description
        "Alarm detailed description";
      tailf:cli-suppress-show-path;
      tailf:cli-suppress-show-match;
      tailf:display-column-name "detailed_desc";
      tailf:info "Detailed description about the alarm.";
    }
  }

  grouping alarmFilters {
    description
      "Alarm attributes that can be used to filter.";
    uses alarmBasicFilters;
    uses alarmExtFilters;
    uses alarmBasicHistoryFilters;
  }

  grouping alarmDetailSuppressedFilters {
    description
      "Suppressed alarm detail attributes that can be used to filter.";
    uses alarmBasicFilters;
    uses alarmExtFilters;
    uses alarmBasicSuppressedFilters;
  }

  grouping alarmBriefFilters {
    description
      "Alarm brief attributes that can be used to filter.";
    uses alarmBasicFilters;
    uses alarmBasicHistoryFilters;
  }

  grouping alarmBriefActiveFilters {
    description
      "Alarm brief attributes that can be used to filter.";
    uses alarmBasicFilters;
  }

  grouping alarmBriefSuppressedFilters {
    description
      "Suppressed alarm brief attributes that can be used to filter.";
    uses alarmBasicFilters;
    uses alarmBasicSuppressedFilters;
  }

  grouping alarmStats {
    description
      "Alarm Statistics.";
    leaf attime {
      type string;
      description
        "Alarms statistics at specified time";
      tailf:cli-suppress-show-path;
      tailf:cli-suppress-show-match;
      tailf:display-column-name "time";
      tailf:info "Alarms statistics at specified time.";
    }
    leaf reported {
      type uint64;
      description
        "Total alarms reported into this service.";
      tailf:cli-suppress-show-path;
      tailf:cli-suppress-show-match;
      tailf:display-column-name "alarms reported";
      tailf:info "Alarms reported into this service.";
    }
    leaf dropped {
      type uint64;
      description
        "Alarms dropped due to some error or other.";
      tailf:cli-suppress-show-path;
      tailf:cli-suppress-show-match;
      tailf:display-column-name "alarms dropped";
      tailf:info "Alarms dropped due to some error or other.";
    }
    leaf bi_set {
      type uint64;
      description
        "Total active alarms current in this service.";
      tailf:cli-suppress-show-path;
      tailf:cli-suppress-show-match;
      tailf:display-column-name "alarms bi-state set";
      tailf:info "Alarms that are currently in the active state.";
    }
    leaf bi_clear {
      type uint64;
      description
        "Alarms that are currently in the cleared state.";
      tailf:cli-suppress-show-path;
      tailf:cli-suppress-show-match;
      tailf:display-column-name "alarms bi-state cleared";
      tailf:info "Alarms that are currently in the cleared state.";
    }
    leaf suppressed {
      type uint64;
      description
        "Alarms that are currently in the suppressed state.";
      tailf:cli-suppress-show-path;
      tailf:cli-suppress-show-match;
      tailf:display-column-name "suppressed alarm";
      tailf:info "Alarms that are currently in the suppressed state.";
    }
    leaf drop_inv_aid {
      type uint64;
      description
        "Alarms dropped due to invalid aid in the alarm report.";
      tailf:cli-suppress-show-path;
      tailf:cli-suppress-show-match;
      tailf:display-column-name "alarms dropped invalid aid";
      tailf:info "Alarms dropped due to invalid aid in the alarm report.";
    }
    leaf drop_no_mem {
      type uint64;
      description
        "Alarms dropped due to low memory condition.";
      tailf:cli-suppress-show-path;
      tailf:cli-suppress-show-match;
      tailf:display-column-name "alarms dropped no memory";
      tailf:info "Alarms dropped due to low memory condition.";
    }
    leaf drop_db_error {
      type uint64;
      description
        "Alarms dropped due to database internal error.";
      tailf:cli-suppress-show-path;
      tailf:cli-suppress-show-match;
      tailf:display-column-name "alarms dropped database error";
      tailf:info "Alarms dropped due to database internal error.";
    }
    leaf drop_clear_no_set {
      type uint64;
      description
        "Alarms dropped due to clear without a set.";
      tailf:cli-suppress-show-path;
      tailf:cli-suppress-show-match;
      tailf:display-column-name "alarms dropped clear without set";
      tailf:info "Alarms dropped due to clear without a set.";
    }
    leaf drop_dup {
      type uint64;
      description
        "Alarms dropped due to duplicate alarm report.";
      tailf:cli-suppress-show-path;
      tailf:cli-suppress-show-match;
      tailf:display-column-name "alarms dropped duplicate alarm";
      tailf:info "Alarms dropped due to duplicate alarm reported.";
    }
    leaf cache_hit {
      type uint64;
      description
        "Alarms present in the cached for show";
      tailf:cli-suppress-show-path;
      tailf:cli-suppress-show-match;
      tailf:display-column-name "show cache hit";
      tailf:info "Alarms present in the cached for show";
    }
    leaf cache_miss {
      type uint64;
      description
        "Alarms not present in the cached for show";
      tailf:cli-suppress-show-path;
      tailf:cli-suppress-show-match;
      tailf:display-column-name "show cache miss";
      tailf:info "Alarms missed in cache";
    }
  }

  grouping alarmClients {
    description
      "Alarm clients.";
    leaf agent_name {
      type string;
      description
        "Alarms client";
      tailf:display-column-name "agent name";
      tailf:info "Alarm client for this servce";
    }
    leaf agent_id {
      type uint32;
      description
        "Alarms agent id of the client";
      tailf:display-column-name "agent id";
      tailf:info "Alarms agent id of the client";
    }
    leaf agent_location {
      type calvados:location-id;
      description
        "The location of this client";
      tailf:display-column-name "agent location";
      tailf:info "The location of this client";
    }
    leaf agent_handle {
      type string;
      description
        "The client handle through which interface";
      tailf:display-column-name "CAPI agent handle";
      tailf:info "The client handle through which interface";
    }
    leaf agent_state {
      type agent_state_td;
      description
        "The current state of the client";
      tailf:display-column-name "agent connection state";
      tailf:info "The current state of the client";
    }
    leaf agent_type {
      type agent_type_td;
      description
        "The type of  the client";
      tailf:display-column-name "agent type";
      tailf:info "The type of the client";
    }
    leaf agent_filter_disp {
      type boolean;
      description
        "The current subscription status of the client";
      tailf:display-column-name "agent filter display";
      tailf:info "The current subscription status of the client";
    }
    leaf agent_subs_id {
      type uint32;
      description
        "The subscriber id of the client";
      tailf:display-column-name "agent filter id";
      tailf:info "The subscriber id of the client";
    }
    leaf agent_filter_state {
      type status_td;
      description
        "The filter used for alarm bi-state state";
      tailf:display-column-name "agent filter bi-state";
      tailf:info "The filter used for the alarm bi-state state";
    }
    leaf agent_filter_severity {
      type severity_td;
      description
        "The filter used for alarm severity";
      tailf:display-column-name "agent filter severity";
      tailf:info "The filter used for alarm severity";
    }
    leaf agent_filter_group {
      type group_td;
      description
        "The filter used for alarm group";
      tailf:display-column-name "agent filter group";
      tailf:info "The filter used for alarm group";
    }
    leaf agent_sdr_id {
      type uint32;
      description
        "agent alarm_sm register with sdr_id in SOMT mode";
      tailf:display-column-name "agent sdr id";
      tailf:info "sdr_id from agent registration data";
    }
    leaf agent_connect_count {
      type uint64;
      description
        "Number of times the agent connected to the alarm mgr";
      tailf:cli-suppress-show-path;
      tailf:cli-suppress-show-match;
      tailf:display-column-name "agent connect count";
      tailf:info "Number of times the agent connected to the alarm mgr";
    }
    leaf agent_connect_time {
      type string;
      description
        "Agent connect timestamp";
      tailf:cli-suppress-show-path;
      tailf:cli-suppress-show-match;
      tailf:display-column-name "agent last connect time";
      tailf:info "Agent connect timestamp.";
    }
    leaf agent_get_count {
      type uint64;
      description
        "Number of times the agent queried for alarms";
      tailf:cli-suppress-show-path;
      tailf:cli-suppress-show-match;
      tailf:display-column-name "agent get count";
      tailf:info "Number of times the agent queried for alarms";
    }
    leaf agent_subscribe_count {
      type uint64;
      description
        "Number of times the agent subscribed for alarms";
      tailf:cli-suppress-show-path;
      tailf:cli-suppress-show-match;
      tailf:display-column-name "agent subscribed count";
      tailf:info "Number of times the agent subscribed for alarms.";
    }
    leaf agent_report_count {
      type uint64;
      description
        "Number of times the agent reported alarms";
      tailf:cli-suppress-show-path;
      tailf:cli-suppress-show-match;
      tailf:display-column-name "agent report count";
      tailf:info "Number of times the agent reported alarms.";
    }
  }

  grouping scope_brief_shows {
    list active {
      key "aid eid";
      max-elements "1024";
      tailf:cli-full-command;
      tailf:cli-full-show-path;
      tailf:cli-no-key-completion;
      tailf:cli-no-match-completion;
      tailf:info "Show active alarms at this scope.";
      tailf:cli-show-template-legend
        "
         -------------------------------------------------------------------------------
         Active Alarms
         -------------------------------------------------------------------------------
         Location          Severity      Group           Set time            Description
         -------------------------------------------------------------------------------
        ";
      tailf:cli-show-template
        "$(.legend_shown != true ?
         -------------------------------------------------------------------------------
         Active Alarms
         
         -------------------------------------------------------------------------------
         Location          Severity      Group           Set time            Description
         -------------------------------------------------------------------------------
         )$(gen_location|ljust:17) $(severity|ljust:13) $(group|ljust:15) $(set_time|ljust:19) $(description)
        ";
      tailf:cli-show-template-enter "";
      tailf:cli-suppress-table;
      uses alarmBriefActiveFilters;
    }
    list history {
      key "aid eid";
      max-elements "1024";
      tailf:cli-full-command;
      tailf:cli-full-show-path;
      tailf:cli-no-key-completion;
      tailf:cli-no-match-completion;
      tailf:info "Show the history alarms at this scope.";
      tailf:cli-show-template-legend
        "
         -------------------------------------------------------------------------------
         History Alarms
         -------------------------------------------------------------------------------
         Location          Severity      Group           Set time            Description
                                                         Clear time                      
         -------------------------------------------------------------------------------
        ";
      tailf:cli-show-template
        "$(.legend_shown != true ?
         -------------------------------------------------------------------------------
         History Alarms
         -------------------------------------------------------------------------------
         Location          Severity      Group           Set time            Description
                                                         Clear time                      
         -----------------------------------------------------------------------
         )$(gen_location|ljust:17) $(severity|ljust:13) $(group|ljust:15) $(set_time|ljust:19) $(description)
                                                         $(clear_time|ljust:19)
        ";
      tailf:cli-show-template-enter "";
      tailf:cli-suppress-table;
      uses alarmBriefFilters;
    }
    list suppressed {
      key "aid eid";
      max-elements "1024";
      tailf:cli-full-command;
      tailf:cli-full-show-path;
      tailf:cli-no-key-completion;
      tailf:cli-no-match-completion;
      tailf:info "Show the suppressed alarms at this scope.";
      tailf:cli-show-template-legend
        "
         -------------------------------------------------------------------------------
         Suppressed Alarms
         -------------------------------------------------------------------------------
         Location          Severity      Group           Set time            Description
                                                         Suppressed time               
         -------------------------------------------------------------------------------
        ";
      tailf:cli-show-template
        "$(.legend_shown != true ?
         -------------------------------------------------------------------------------
         History Alarms
         -------------------------------------------------------------------------------
         Location          Severity      Group           Set time            Description
                                                         Suppressed time                      
         -----------------------------------------------------------------------
         )$(gen_location|ljust:17) $(severity|ljust:13) $(group|ljust:15) $(set_time|ljust:19) $(description)
                                                         $(suppressed_time|ljust:19)
        ";
      tailf:cli-show-template-enter "";
      tailf:cli-suppress-table;
      uses alarmBriefSuppressedFilters;
    }
  }

  grouping scope_detail_shows {
    list active {
      key "aid eid";
      max-elements "1024";
      tailf:cli-full-command;
      tailf:cli-full-show-path;
      tailf:cli-no-key-completion;
      tailf:cli-no-match-completion;
      tailf:info "Show the active alarms at this scope.";
      tailf:cli-show-template-legend
        "
         ------------------------------------------------------------
         Active Alarms
         ------------------------------------------------------------
        ";
      tailf:cli-show-template
        "$(.legend_shown != true ?
         ------------------------------------------------------------
         Active Alarms
         ------------------------------------------------------------
         )aid\\\\:          $(aid|ljust:60)
         tag\\\\:          $(tag|ljust:60)
         module\\\\:       $(module|ljust:60)
         location\\\\:     $(gen_location|ljust:60)
         eid\\\\:          $(eid|ljust:60)
         state\\\\:        $(state|ljust:60)
         severity\\\\:     $(severity|ljust:60)
         group\\\\:        $(group|ljust:60)
         agent\\\\:        $(reporting_agent_id|ljust:60)
         pending sync\\\\: $(resynced|ljust:60)
         set_time\\\\:     $(set_time|ljust:60)
         clear_time\\\\:   $(clear_time|ljust:60)
         description\\\\:  $(description|ljust:60)
         detail info\\\\:  $(detail_desc|ljust:60)
         
        ";
      tailf:cli-show-template-enter "";
      tailf:cli-suppress-table;
      uses alarmFilters;
    }
    list history {
      key "aid eid";
      max-elements "1024";
      tailf:cli-full-command;
      tailf:cli-full-show-path;
      tailf:cli-no-key-completion;
      tailf:cli-no-match-completion;
      tailf:info "Show the history alarms at this scope.";
      tailf:cli-show-template-legend
        "
         ------------------------------------------------------------
         History Alarms
         ------------------------------------------------------------
        ";
      tailf:cli-show-template
        "$(.legend_shown != true ?
         ------------------------------------------------------------
         History Alarms
         ------------------------------------------------------------
         )aid\\\\:         $(aid|ljust:60)
         tag\\\\:         $(tag|ljust:60)
         module\\\\:      $(module|ljust:60)
         location\\\\:    $(gen_location|ljust:60)
         eid\\\\:         $(eid|ljust:60)
         state\\\\:       $(state|ljust:60)
         severity\\\\:    $(severity|ljust:60)
         group\\\\:       $(group|ljust:60)
         agent\\\\:       $(reporting_agent_id|ljust:60)
         set_time\\\\:    $(set_time|ljust:60)
         clear_time\\\\:  $(clear_time|ljust:60)
         description\\\\: $(description|ljust:60)
         detail info\\\\: $(detail_desc|ljust:60)
         
        ";
      tailf:cli-show-template-enter "";
      tailf:cli-suppress-table;
      uses alarmFilters;
    }
    list stats {
      key "attime";
      max-elements "1024";
      tailf:cli-full-command;
      tailf:cli-full-show-path;
      tailf:cli-no-key-completion;
      tailf:cli-no-match-completion;
      tailf:info "Show the service statistics.";
      tailf:cli-show-template-legend
        "
         ------------------------------------------------------------
         Statistics
         ------------------------------------------------------------
        ";
      tailf:cli-show-template
        "$(.legend_shown != true ?
         ------------------------------------------------------------
         Statistics
         ------------------------------------------------------------
         )alarms reported\\\\:    $(reported|ljust:60)
         dropped\\\\:            $(dropped|ljust:60)
         bi-state set\\\\:       $(bi_set|ljust:60)
         bi-state cleared\\\\:   $(bi_clear|ljust:60)
         suppressed\\\\:         $(suppressed|ljust:60)
         dropped invalid aid\\\\:$(drop_inv_aid|ljust:60)
         drop no mem\\\\:        $(drop_no_mem|ljust:60)
         drop db error\\\\:      $(drop_db_error|hex:8)
         drop clear no set\\\\:  $(drop_clear_no_set|ljust:60)
         drop duplicate\\\\:     $(drop_dup|ljust:60)
         cache hit\\\\:          $(cache_hit|ljust:60)
         cache miss\\\\:         $(cache_miss|ljust:60)
         
        ";
      tailf:cli-show-template-enter "";
      tailf:cli-suppress-table;
      uses alarmStats;
    }
    list clients {
      key "agent_handle";
      max-elements "1024";
      tailf:cli-full-command;
      tailf:cli-full-show-path;
      tailf:cli-no-key-completion;
      tailf:cli-no-match-completion;
      tailf:info "Show the clients associated with the service.";
      tailf:cli-show-template-legend
        "
         ------------------------------------------------------------
         Clients
         ------------------------------------------------------------
        ";
      tailf:cli-show-template
        "$(.legend_shown != true ?
         ------------------------------------------------------------
         Clients
         ------------------------------------------------------------
         )agent name\\\\:              $(agent_name|ljust:60)
         agent id\\\\:                $(agent_id|ljust:60)
         agent location\\\\:          $(agent_location|ljust:60)
         agent handle\\\\:            $(agent_handle|ljust:60)
         agent state\\\\:             $(agent_state|ljust:60)
         agent type\\\\:              $(agent_type|ljust:60)
         agent filter display\\\\:    $(agent_filter_disp|ljust:60)
         agent subscriber id\\\\:     $(agent_subs_id|ljust:60)
         agent filter state\\\\:      $(agent_filter_state|ljust:60)
         agent filter severity\\\\:   $(agent_filter_severity|ljust:60)
         agent filter group\\\\:      $(agent_filter_group|ljust:60)
         $(agent_sdr_id != 65535 ?agent sdr id\\\\:            $(agent_sdr_id|ljust:60)
         )agent connect count\\\\:     $(agent_connect_count|ljust:60)
         agent connect time\\\\:      $(agent_connect_time|ljust:60)
         agent get count\\\\:         $(agent_get_count|ljust:60)
         agent subscribe count\\\\:   $(agent_subscribe_count|ljust:60)
         agent report count\\\\:      $(agent_report_count|ljust:60)
         
        ";
      tailf:cli-show-template-enter "";
      tailf:cli-suppress-table;
      uses alarmClients;
    }
    list suppressed {
      key "aid eid";
      max-elements "1024";
      tailf:cli-full-command;
      tailf:cli-full-show-path;
      tailf:cli-no-key-completion;
      tailf:cli-no-match-completion;
      tailf:info "Show the suppressed alarms at this scope.";
      tailf:cli-show-template-legend
        "
         ------------------------------------------------------------
         Suppressed Alarms
         ------------------------------------------------------------
        ";
      tailf:cli-show-template
        "$(.legend_shown != true ?
         ------------------------------------------------------------
         Suppressed Alarms
         ------------------------------------------------------------
         )aid\\\\:              $(aid|ljust:60)
         tag\\\\:              $(tag|ljust:60)
         module\\\\:           $(module|ljust:60)
         location\\\\:         $(gen_location|ljust:60)
         eid\\\\:              $(eid|ljust:60)
         state\\\\:            $(state|ljust:60)
         severity\\\\:         $(severity|ljust:60)
         group\\\\:            $(group|ljust:60)
         agent\\\\:            $(reporting_agent_id|ljust:60)
         pending sync\\\\:     $(resynced|ljust:60)
         set_time\\\\:         $(set_time|ljust:60)
         suppressed_time\\\\:  $(suppressed_time|ljust:60)
         description\\\\:      $(description|ljust:60)
         detail info\\\\:      $(detail_desc|ljust:60)
         
        ";
      tailf:cli-show-template-enter "";
      tailf:cli-suppress-table;
      uses alarmDetailSuppressedFilters;
    }
  }
  tailf:id "http://www.cisco.com/panini/calvados/alarm";

  container alarm_mgr {
    config false;
    description
      "Calvados alarms operational data model";
    tailf:alt-name "alarms";
    tailf:info "Show Alarms associated with calvados";
    tailf:cli-show-template "$(brief|show)";
    uses show_trace:traceable;
    container brief {
      description
        "A set of brief alarm commands";
      tailf:cli-incomplete-command;
      tailf:info "A set of brief alarm commands";
      tailf:cli-show-template "$(rack|show)";
      container card {
        description
          "Alarms reported at the local card as 
           specified by the location parameter";
        tailf:info "Show brief card scope alarms related data.";
        list location {
          key "locations";
          tailf:info "Specify a location for alarms.";
          tailf:cli-no-match-completion;
          tailf:cli-suppress-table;
          tailf:cli-incomplete-command;
          tailf:cli-show-template-enter "";
          leaf locations {
            type calvados:location-id;
            tailf:cli-drop-node-name;
            tailf:cli-incomplete-command;
          }
          tailf:callpoint "alarm_node_brief";
          uses scope_brief_shows;
        }
      }
      container rack {
        description
          "Alarms reported at the rack scope   
           specified by the rack-id";
        tailf:cli-incomplete-command;
        tailf:info "Show brief rack scope alarms related data.";
        tailf:cli-show-template "$(rack_locations|show)";
        list rack_locations {
          key "rackid";
          tailf:cli-drop-node-name;
          tailf:cli-no-match-completion;
          tailf:cli-suppress-table;
          tailf:cli-incomplete-command;
          tailf:cli-show-template-enter "";
          tailf:cli-show-template "$(active|show)";
          leaf rackid {
            type uint32;
            tailf:cli-drop-node-name;
            tailf:cli-incomplete-command;
            tailf:info "Specify a rack id for alarms.";
          }
          tailf:callpoint "alarm_rack_brief";
          uses scope_brief_shows;
        }
      }
      container system {
        description
          "Alarms reported at the system scope";
        tailf:callpoint "alarm_system_brief";
        tailf:cli-incomplete-command;
        tailf:info "Show brief system scope alarm related data.";
        uses scope_brief_shows;
      }
    }
    container detail {
      description
        "A set of detail alarm commands";
      tailf:cli-incomplete-command;
      tailf:cli-show-template "$(rack|show)";
      tailf:info "A set of detail alarm commands";
      container card {
        description
          "Alarms reported at the local card as 
           specified by the location parameter";
        tailf:info "Show detail card scope alarms related data.";
        list location {
          key "locations";
          tailf:info "Specify a card location for alarms.";
          tailf:cli-no-match-completion;
          tailf:cli-suppress-table;
          tailf:cli-incomplete-command;
          tailf:cli-show-template-enter "";
          leaf locations {
            type calvados:location-id;
            tailf:cli-drop-node-name;
            tailf:cli-incomplete-command;
          }
          tailf:callpoint "alarm_node_detail";
          uses scope_detail_shows;
        }
      }
      container rack {
        description
          "Alarms reported at the rack as 
           specified by the location parameter";
        tailf:cli-incomplete-command;
        tailf:info "Show detail rack scope alarms related data.";
        list rack_locations {
          key "rackid";
          tailf:cli-drop-node-name;
          tailf:cli-no-match-completion;
          tailf:cli-suppress-table;
          tailf:cli-incomplete-command;
          tailf:cli-show-template-enter "";
          leaf rackid {
            type uint32;
            tailf:cli-drop-node-name;
            tailf:cli-incomplete-command;
            tailf:info "Specify a rack id for rack scope alarms.";
          }
          tailf:callpoint "alarm_rack_detail";
          uses scope_detail_shows;
        }
      }
      container system {
        description
          "Alarms reported at the system as 
           specified by the location parameter";
        tailf:callpoint "alarm_system_detail";
        tailf:cli-incomplete-command;
        tailf:info "Show detail system scope alarms related data.";
        uses scope_detail_shows;
      }
    }
  }
}
