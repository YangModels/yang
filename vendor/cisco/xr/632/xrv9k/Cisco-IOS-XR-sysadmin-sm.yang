module Cisco-IOS-XR-sysadmin-sm {
  namespace "http://www.cisco.com/ns/yang/Cisco-IOS-XR-sysadmin-sm";
  prefix shelf_sm;

  import tailf-common {
    prefix tailf;
  }
  import ietf-yang-types {
    prefix ietf;
  }
  import ietf-inet-types {
    prefix inet;
  }
  import Cisco-IOS-XR-sysadmin-types {
    prefix calvados;
  }
  import Cisco-IOS-XR-sysadmin-show-trace {
    prefix show_trace;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains a collection of YANG
     definitions for Cisco IOS-XR SysAdmin configuration.
     
     This module holds Shelf Management configuration data.
     
     Copyright(c) 2011-2017 by Cisco Systems, Inc.
     All rights reserved.";

  revision 2017-04-12 {
    description
      "Changed namespace and module name";
  }
  revision 2016-10-12 {
    description
      "Unhide commands and configs. Moved to advanced-grp";
  }
  revision 2012-01-05 {
    description
      "show platform [detail] [location L] support";
  }
  revision 2011-11-08 {
    description
      "Initial revision";
  }

  grouping sm-oper-group {
    container oper {
      config false;
      tailf:cli-drop-node-name;
      tailf:callpoint "sm_oper_placeholder";
      uses ctrace-oper-group;
      uses platform-oper-group;
      uses chassis-oper-group;
      uses reload-rack-oper-group;
      uses reboot-history-oper-group;
      uses mgmt-interfaces-oper-group;
      uses reload-vm-oper-group;
      uses mac-pool-oper-group;
    }
  }

  grouping ctrace-oper-group {
    container shelf_mgr {
      tailf:info "Show Shelf Manager Information";
      tailf:cli-incomplete-show-path;
      uses show_trace:traceable;
    }
  }

  grouping platform-oper-group {
    container platform {
      config false;
      tailf:info "Show platform node information";
      tailf:cli-show-template "$(summary|show)";
      uses platform-summary-oper-group;
      uses platform-detail-oper-group;
      uses platform-slices-oper-group;
    }
  }

  grouping chassis-oper-group {
    container chassis {
      config false;
      tailf:info "Show chassis information";
      tailf:callpoint "chassis";
      tailf:cli-show-template "$(brief|show)";
      uses chassis-brief-oper-group;
    }
  }

  grouping reload-rack-oper-group {
    container reload {
      config false;
      tailf:cli-suppress-show-path;
      container rack {
        list racks {
          key "rack";
          tailf:callpoint "reload_loc";
          leaf rack {
            type string;
          }
        }
      }
    }
  }

  grouping reload-vm-oper-group {
    container reload_vm {
      config false;
      tailf:info "reload vm(s) on a node";
      tailf:callpoint "platform";
      tailf:cli-suppress-show-path;
      list location {
        key "location";
        tailf:info "Location of node to reload";
        leaf location {
          type string;
          tailf:info "Location of node to reload";
        }
      }
    }
  }

  grouping reboot-history-events-oper-group {
    list events {
      key "event_idx";
      tailf:cli-drop-node-name;
      tailf:cli-suppress-table;
      tailf:cli-suppress-show-path;
      tailf:cli-suppress-show-match;
      tailf:cli-show-template "$(event|show)";
      leaf event_idx {
        type uint32;
        tailf:alt-name "Event Index";
      }
      container event {
        tailf:cli-drop-node-name;
        leaf timestamp {
          type string;
          tailf:alt-name "Timestamp";
          tailf:cli-column-width "24";
        }
        leaf reason_code {
          type uint32;
          tailf:alt-name "Reason Code";
          tailf:cli-column-width "10";
        }
        leaf reason {
          type string;
          tailf:alt-name "Reason";
        }
        leaf src_loc {
          type string;
          tailf:alt-name "Src Location";
        }
        leaf src_name {
          type string;
          tailf:alt-name "Src Name";
        }
      }
    }
  }

  grouping reboot-history-card-oper-group {
    container card {
      tailf:info "Card reboot history";
      list location {
        key "location";
        tailf:info "Location of node to show; omit to show all locations";
        tailf:cli-suppress-table;
        tailf:cli-show-template-enter
          "
           Card Reboot History for $(location)
          ";
        leaf location {
          type calvados:location-id;
          tailf:info "Node location";
        }
        uses reboot-history-events-oper-group;
      }
    }
  }

  grouping reboot-history-admin-vm-oper-group {
    container admin-vm {
      tailf:info "Admin VM reboot history";
      list location {
        key "location";
        tailf:info "Location of node to show; omit to show all locations";
        tailf:cli-suppress-table;
        tailf:cli-show-template-enter
          "
           Admin VM Reboot History for $(location)
          ";
        leaf location {
          type calvados:location-id;
          tailf:info "Node location";
        }
        uses reboot-history-events-oper-group;
      }
    }
  }

  grouping reboot-history-reverse-oper-group {
    container reverse {
      tailf:info "Show reboot history in reverse order";
      tailf:display-status-name "Reboot history in reverse order";
      uses reboot-history-card-oper-group;
      uses reboot-history-admin-vm-oper-group;
    }
  }

  grouping reboot-history-oper-group {
    container reboot-history {
      config false;
      tailf:info "Show reboot history events";
      tailf:callpoint "platform";
      uses reboot-history-card-oper-group;
      uses reboot-history-admin-vm-oper-group;
      uses reboot-history-reverse-oper-group;
    }
  }

  grouping mgmt-interfaces-oper-group {
    list interface {
      key "ifname";
      tailf:info "Management Interfaces";
      tailf:callpoint "mgmt-interfaces";
      leaf ifname {
        type string;
      }
      tailf:cli-suppress-table;
      tailf:cli-show-template-enter "";
      tailf:cli-show-template "$(interface-data|show)";
      container interface-data {
        tailf:cli-drop-node-name;
        tailf:cli-show-template
          "$(../ifname)  Link encap\\\\: Ethernet$(intf_num == 0 ?  HWaddr $(mac)
             inet  addr\\\\: $(ipv4)
             $(port_status) $(flagstr)  MTU\\\\:$(mtu)  Metric\\\\:$(metric)
           :  $(port_status)
           )  RX packets\\\\:$(rx_pak|rjust:11) errors\\\\:$(rx_errors) dropped\\\\:$(rx_dropped) overruns\\\\:$(rx_overruns)   frame\\\\:$(rx_frame)
             TX packets\\\\:$(tx_pak|rjust:11) errors\\\\:$(tx_errors) dropped\\\\:$(tx_dropped) overruns\\\\:$(tx_overruns) carrier\\\\:$(tx_carrier)
                                    collisions\\\\:$(collisions) txqueuelen\\\\:$(tx_queuelen)
             RX bytes\\\\:$(rx_bytes|rjust:22)  TX bytes\\\\:$(tx_bytes|rjust:22)
           
          ";
        leaf mac {
          type ietf:mac-address;
          tailf:hidden "internal";
        }
        leaf ipv4 {
          type inet:ipv4-address;
          tailf:hidden "internal";
        }
        leaf flagstr {
          type string;
          tailf:hidden "internal";
        }
        leaf port_status {
          type string;
          tailf:hidden "internal";
        }
        leaf mtu {
          type uint32;
          tailf:hidden "internal";
        }
        leaf metric {
          type uint32;
          tailf:hidden "internal";
        }
        leaf rx_pak {
          type uint32;
          tailf:hidden "internal";
        }
        leaf rx_errors {
          type uint32;
          tailf:hidden "internal";
        }
        leaf rx_dropped {
          type uint32;
          tailf:hidden "internal";
        }
        leaf rx_overruns {
          type uint32;
          tailf:hidden "internal";
        }
        leaf rx_frame {
          type uint32;
          tailf:hidden "internal";
        }
        leaf tx_pak {
          type uint32;
          tailf:hidden "internal";
        }
        leaf tx_errors {
          type uint32;
          tailf:hidden "internal";
        }
        leaf tx_dropped {
          type uint32;
          tailf:hidden "internal";
        }
        leaf tx_overruns {
          type uint32;
          tailf:hidden "internal";
        }
        leaf tx_carrier {
          type uint32;
          tailf:hidden "internal";
        }
        leaf collisions {
          type uint32;
          tailf:hidden "internal";
        }
        leaf tx_queuelen {
          type uint32;
          tailf:hidden "internal";
        }
        leaf rx_bytes {
          type uint64;
          tailf:hidden "internal";
        }
        leaf tx_bytes {
          type uint64;
          tailf:hidden "internal";
        }
        leaf intf_num {
          type uint32;
          tailf:hidden "internal";
        }
      }
    }
  }

  grouping mac-pool-oper-group {
    container macpool {
      config false;
      tailf:info "Show virtual mac pool information.";
      tailf:callpoint "mac_pool";
      tailf:cli-show-template "$(brief|show)";
      uses mac-pool-brief-oper-group;
    }
  }

  grouping platform-summary-oper-group {
    container summary {
      tailf:cli-drop-node-name;
      tailf:callpoint "platform_summary";
      list location {
        key "location";
        tailf:info "Location of node to show; omit to show all locations";
        tailf:cli-full-command;
        tailf:cli-no-match-completion;
        tailf:cli-enforce-table;
        leaf location {
          type calvados:location-id;
          tailf:info "Node location";
          tailf:display-column-name "Location";
        }
        container summary-data {
          tailf:cli-drop-node-name;
          leaf card_type {
            type string;
            tailf:display-column-name "Card Type";
            tailf:cli-column-width "22";
            tailf:cli-suppress-show-path;
            tailf:cli-suppress-show-match;
          }
          leaf hw_state {
            type string;
            tailf:display-column-name "HW State";
            tailf:cli-column-width "12";
            tailf:cli-suppress-show-path;
            tailf:cli-suppress-show-match;
          }
          leaf sw_state {
            type string;
            tailf:display-column-name "SW State";
            tailf:cli-column-width "12";
            tailf:cli-suppress-show-path;
            tailf:cli-suppress-show-match;
          }
          leaf config_state {
            type string;
            tailf:display-column-name "Config State";
            tailf:cli-column-width "12";
            tailf:cli-suppress-show-path;
            tailf:cli-suppress-show-match;
          }
        }
      }
    }
  }

  grouping platform-detail-oper-group {
    container detail {
      tailf:info "Show details of node type and state";
      tailf:callpoint "platform_detail";
      list location {
        key "location";
        tailf:info "Location of node to show; omit to show all locations";
        tailf:cli-full-command;
        tailf:cli-no-match-completion;
        tailf:cli-show-template-enter
          "
           Platform Information for $(location)
          ";
        tailf:cli-show-template "$(detail-data|show)";
        leaf location {
          type calvados:location-id;
          tailf:info "Node location";
          tailf:alt-name "Module Location :";
        }
        container detail-data {
          tailf:cli-drop-node-name;
          leaf pid {
            type string;
            tailf:alt-name "PID :";
            tailf:cli-suppress-show-path;
            tailf:cli-suppress-show-match;
          }
          leaf description {
            type string;
            tailf:alt-name "Description :";
            tailf:cli-suppress-show-path;
            tailf:cli-suppress-show-match;
          }
          leaf vid_sn {
            type string;
            tailf:alt-name "VID/SN :";
            tailf:cli-suppress-show-path;
            tailf:cli-suppress-show-match;
          }
          leaf hw_state {
            type string;
            tailf:alt-name "HW Oper State :";
            tailf:cli-suppress-show-path;
            tailf:cli-suppress-show-match;
          }
          leaf sw_state {
            type string;
            tailf:alt-name "SW Oper State :";
            tailf:cli-suppress-show-path;
            tailf:cli-suppress-show-match;
          }
          leaf config_wordy {
            type string;
            tailf:alt-name "Configuration :";
            tailf:cli-suppress-show-path;
            tailf:cli-suppress-show-match;
          }
          leaf hw_ver {
            type string;
            tailf:alt-name "HW Version :";
            tailf:cli-suppress-show-path;
            tailf:cli-suppress-show-match;
          }
          leaf last_event {
            type string;
            tailf:alt-name "Last Event :";
            tailf:cli-suppress-show-path;
            tailf:cli-suppress-show-match;
          }
          leaf last_ev_reason_str {
            type string;
            tailf:alt-name "Last Event Reason :";
            tailf:cli-suppress-show-path;
            tailf:cli-suppress-show-match;
          }
        }
      }
    }
  }

  grouping platform-slices-oper-group {
    container slices {
      tailf:info "Show summary of node forwarding slices";
      tailf:callpoint "platform_slices";
      list location {
        key "location";
        tailf:info "Location of node to show; omit to show all locations";
        tailf:cli-full-command;
        tailf:cli-no-match-completion;
        leaf location {
          type calvados:location-id;
          tailf:info "Node location";
          tailf:display-column-name "Location";
        }
        list slice_values {
          key "slice_idx";
          tailf:cli-drop-node-name;
          tailf:cli-suppress-show-path;
          tailf:cli-suppress-show-match;
          tailf:cli-show-template "$(slice|show)";
          leaf slice_idx {
            type uint32;
            tailf:display-column-name "";
            tailf:cli-value-display-template "";
          }
          container slice {
            tailf:cli-drop-node-name;
            leaf slice_num {
              type uint32;
              tailf:display-column-name "Slice Num";
              tailf:cli-column-width "10";
            }
            leaf admin_state {
              type string;
              tailf:display-column-name "Admin State";
              tailf:cli-column-width "13";
            }
            leaf oper_state {
              type string;
              tailf:display-column-name "Oper State";
              tailf:cli-column-width "13";
            }
          }
        }
      }
    }
  }

  grouping chassis-brief-oper-group {
    container brief {
      tailf:cli-drop-node-name;
      list chassis_serial {
        key "serial_number";
        tailf:info "Rack serial number of node to show; omit to show all racks";
        tailf:cli-drop-node-name;
        tailf:cli-full-command;
        tailf:cli-no-match-completion;
        tailf:cli-enforce-table;
        leaf serial_number {
          type string;
          tailf:info "Rack serial number";
          tailf:cli-column-width "12";
          tailf:display-column-name "Serial Num";
        }
        container brief-data {
          tailf:cli-drop-node-name;
          leaf racknum {
            type string;
            tailf:display-column-name "Rack Num";
            tailf:cli-column-width "10";
            tailf:cli-suppress-show-path;
            tailf:cli-suppress-show-match;
          }
          leaf rack_type {
            type string;
            tailf:display-column-name "Rack Type";
            tailf:cli-column-width "10";
            tailf:cli-suppress-show-path;
            tailf:cli-suppress-show-match;
          }
          leaf rack_state {
            type string;
            tailf:display-column-name "Rack State";
            tailf:cli-column-width "10";
            tailf:cli-suppress-show-path;
            tailf:cli-suppress-show-match;
          }
          leaf data_plane {
            type string;
            tailf:display-column-name "Data Plane";
            tailf:cli-column-width "10";
            tailf:cli-suppress-show-path;
            tailf:cli-suppress-show-match;
          }
          leaf ctrl_plane {
            type string;
            tailf:display-column-name "Ctrl Plane";
            tailf:cli-column-width "10";
            tailf:cli-suppress-show-path;
            tailf:cli-suppress-show-match;
          }
        }
      }
    }
  }

  grouping mac-pool-brief-oper-group {
    container brief {
      tailf:cli-drop-node-name;
      list rack {
        key "serial_number";
        tailf:info "Show virtual mac info on specific rack; omit to show all racks";
        tailf:cli-drop-node-name;
        tailf:cli-full-command;
        tailf:cli-no-match-completion;
        tailf:cli-enforce-table;
        leaf serial_number {
          type string;
          tailf:info "Rack serial number";
          tailf:cli-column-width "12";
          tailf:display-column-name "Rack Serial";
        }
        container brief-data {
          tailf:cli-drop-node-name;
          leaf racknum {
            type string;
            tailf:display-column-name "Rack Num";
            tailf:cli-column-width "8";
            tailf:cli-suppress-show-path;
            tailf:cli-suppress-show-match;
          }
          leaf mac_base {
            type ietf:mac-address;
            tailf:display-column-name "Mac Base";
            tailf:info "Base mac address from the rack";
            tailf:cli-column-width "17";
            tailf:cli-suppress-show-path;
            tailf:cli-suppress-show-match;
          }
          leaf mac_count {
            type uint32;
            tailf:display-column-name "Mac Count";
            tailf:info "Total mac count on this rack backplane";
            tailf:cli-column-width "10";
            tailf:cli-suppress-show-path;
            tailf:cli-suppress-show-match;
          }
          leaf is_selected {
            type boolean;
            tailf:display-column-name "Selected";
            tailf:cli-column-width "10";
            tailf:cli-suppress-show-path;
            tailf:cli-suppress-show-match;
          }
          leaf allocated_count {
            type uint32;
            tailf:display-column-name "Allocated";
            tailf:info "Allocated mac address count";
            tailf:cli-column-width "10";
            tailf:cli-suppress-show-path;
            tailf:cli-suppress-show-match;
          }
        }
      }
    }
  }

  grouping sm-config-group {
    container config {
      config true;
      tailf:cli-drop-node-name;
      uses chassis-config-group;
      uses mgmt-interfaces-config-group;
      uses virtual-macaddr-config-group;
    }
  }

  grouping chassis-config-group {
    container chassis {
      tailf:info "Configure Chassis Serial Number";
      list serial {
        key "serial";
        unique "rack";
        leaf serial {
          type string;
          mandatory true;
          tailf:info "Chassis Serial Number String";
        }
        leaf rack {
          type string {
            pattern "[fF][0-7]|[0-9]|[1][0-5]|[2][4][0-7]";
            tailf:info
              "Configurable range:
                   LINE RACK   : 0-15
                   FABRIC RACK : F0-F7";
          }
          mandatory true;
          tailf:info "Chassis Rack Number";
        }
      }
    }
  }

  grouping mgmt-interfaces-config-group {
    container interface {
      tailf:info "Configure Interface";
      container MgmtEth {
        tailf:info "Configure Management Ethernet Interface";
        list locport {
          key "rack slot intf port";
          tailf:cli-drop-node-name;
          tailf:cli-key-format "$(1)/$(2)/$(3)/$(4)";
          leaf rack {
            type string {
              pattern "[fF][0-7]|[0-9]|[1][0-5]";
              tailf:info "Location rack";
            }
            tailf:info "Location/InterfaceNum/Port";
          }
          leaf slot {
            type string {
              pattern "[Rr][Pp][0-1]|[Rr][Ss][Pp][0-1]|[Ss][Cc][0-1]";
              tailf:info "(RP or SC) Location slot";
            }
            tailf:info "Slot";
          }
          leaf intf {
            type uint32 {
              range "0";
              tailf:info "Interface Number, Admin(0)";
            }
            tailf:info "Interface Number";
            tailf:cli-suppress-range;
          }
          leaf port {
            type uint32 {
              range "0";
              tailf:info "Port Number, currently (0)";
            }
            tailf:info "Port Number";
            tailf:cli-suppress-range;
          }
          container ipv4 {
            tailf:info "IPv4 parameters";
            leaf address {
              type string {
                pattern "(([0-9]|[1-9][0-9]|1[0-9][0-9]|2[0-4][0-9]|25[0-5])\\.){3}([0-9]|[1-9][0-9]|1[0-9][0-9]|2[0-4][0-9]|25[0-5])(( (([0-9]|[1-9][0-9]|1[0-9][0-9]|2[0-4][0-9]|25[0-5])\\.){3}([0-9]|[1-9][0-9]|1[0-9][0-9]|2[0-4][0-9]|25[0-5]))|(/([0-9]+)))";
                tailf:info "IPv4 address and netmask: A.B.C.D/E or A.B.C.D E.F.G.H";
              }
              tailf:info "IPv4 address and netmask: A.B.C.D/E or A.B.C.D E.F.G.H";
              tailf:cli-multi-value {
                tailf:cli-max-words "2";
              }
            }
          }
          leaf shutdown {
            type empty;
            tailf:info "Shut the interface down";
          }
          leaf mtu {
            type uint32 {
              range "48..9000";
            }
            tailf:info "MTU for interface";
          }
          leaf default-gw {
            type inet:ipv4-address;
            tailf:info "Default Gateway address: A.B.C.D";
          }
          container arp {
            tailf:info "Configure static ARP entry";
            list ip {
              key "ip";
              leaf ip {
                type inet:ipv4-address;
                mandatory true;
                tailf:info "IPv4 parameters";
              }
              leaf mac {
                type ietf:mac-address;
                mandatory true;
                tailf:info "Mac address";
              }
            }
          }
        }
      }
    }
    container domain {
      tailf:info "Domain Name System (DNS) information";
      list name {
        key "name";
        tailf:info "Domain name to search";
        leaf name {
          type string;
          tailf:info "domain name string";
        }
      }
      list name-server {
        key "name-server";
        tailf:info "Domain name server";
        leaf name-server {
          type inet:ipv4-address;
          tailf:info "domain name server address: A.B.C.D";
        }
      }
    }
  }

  grouping virtual-macaddr-config-group {
    container virtual-macaddr-range {
      tailf:hidden "advanced-grp";
      tailf:info "Configure range of mac addresses for virtual interfaces";
      leaf base {
        type ietf:mac-address;
        tailf:info "Base mac address of range for virtual interfaces";
      }
      leaf count {
        type uint32 {
          range "1..65535";
        }
        tailf:info "Count of contiguous mac addresses";
      }
    }
  }

  grouping sm-action-group {
    container actions {
      config false;
      tailf:cli-drop-node-name;
      uses reload-action-group;
    }
  }

  grouping reload-action-group {
    tailf:action "reload" {
      tailf:info "Reload a node";
      tailf:actionpoint "reload";
      input {
        choice reload_input {
          mandatory true;
          case target_rack {
            leaf rack {
              type leafref {
                path "/oper/reload/rack/racks/rack";
              }
              mandatory false;
              tailf:info "Reload a rack";
            }
          }
          case target_vm {
            container location_list {
              tailf:cli-drop-node-name;
              leaf location {
                type leafref {
                  path "/oper/reload_vm/location/location";
                }
                mandatory false;
                tailf:info "Location of node to reload";
              }
              choice reload_target {
                mandatory false;
                case target_admin {
                  leaf admin {
                    type empty;
                    mandatory false;
                    tailf:info "Reload only the admin virtual machine";
                  }
                }
                case target_all {
                  leaf all {
                    type empty;
                    mandatory false;
                    tailf:info "Reload all the virtual machines";
                  }
                }
              }
            }
          }
        }
      }
      output {
        leaf result {
          type string;
          mandatory true;
        }
      }
    }
  }
  tailf:id "http://www.cisco.com/panini/calvados/shelf_sm";

  uses sm-oper-group;
  uses sm-config-group;
  uses sm-action-group;
}
