module Cisco-IOS-XR-ping-act {
  namespace "http://cisco.com/ns/yang/Cisco-IOS-XR-ping-act";
  prefix ping-act;

  import Cisco-IOS-XR-types {
    prefix xr;
  }
  include Cisco-IOS-XR-ipv4-ping-act;
  include Cisco-IOS-XR-ipv6-ping-act;

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ping action package configuration.
     
     Copyright (c) 2016 by Cisco Systems, Inc.
     All rights reserved.";

  revision 2016-09-28 {
    description
      "IOS XR 6.2.1 revision.";
  }

  rpc ping {
    description
      "Send echo messages";
    input {
      container destination {
        uses PING-OPTIONS;
        uses IPV4-SPECIFIC-OPTIONS;
        uses IPV6-SPECIFIC-OPTIONS;
      }
      list ipv4 {
        key "destination";
        uses IPV4-PING-INPUT;
      }
      container ipv6 {
        uses IPV6-PING-INPUT;
      }
    }
    output {
      container ping-response {
        list ipv4 {
          key "destination";
          uses IPV4-PING-OUTPUT;
        }
        container ipv6 {
          uses IPV6-PING-OUTPUT;
        }
      }
    }
  }
}
