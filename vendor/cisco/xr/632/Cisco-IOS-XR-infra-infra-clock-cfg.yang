module Cisco-IOS-XR-infra-infra-clock-cfg {
  namespace "http://cisco.com/ns/yang/Cisco-IOS-XR-infra-infra-clock-cfg";
  prefix infra-infra-clock-cfg;

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR infra-infra-clock package configuration.
     
     This module contains definitions
     for the following management objects:
       clock: Configure time-of-day clock
     
     Copyright (c) 2013-2017 by Cisco Systems, Inc.
     All rights reserved.";

  revision 2015-11-09 {
    description
      "IOS XR 6.0 revision.";
  }

  typedef Clock-month {
    type enumeration {
      enum "january" {
        value 0;
        description
          "January";
      }
      enum "february" {
        value 1;
        description
          "February";
      }
      enum "march" {
        value 2;
        description
          "March";
      }
      enum "april" {
        value 3;
        description
          "April";
      }
      enum "may" {
        value 4;
        description
          "May";
      }
      enum "june" {
        value 5;
        description
          "June";
      }
      enum "july" {
        value 6;
        description
          "July";
      }
      enum "august" {
        value 7;
        description
          "August";
      }
      enum "september" {
        value 8;
        description
          "September";
      }
      enum "october" {
        value 9;
        description
          "October";
      }
      enum "november" {
        value 10;
        description
          "November";
      }
      enum "december" {
        value 11;
        description
          "December";
      }
    }
    description
      "Clock month";
  }

  typedef Clock-summer-time-mode {
    type enumeration {
      enum "recurring" {
        value 0;
        description
          "Recurring summer time";
      }
      enum "date" {
        value 1;
        description
          "Absolute summer time";
      }
    }
    description
      "Clock summer time mode";
  }

  container clock {
    description
      "Configure time-of-day clock";
    container summer-time {
      presence "Indicates a summer-time node is configured.";
      description
        "Configure summer (daylight savings) time";
      leaf time-zone-name {
        type string;
        mandatory true;
        description
          "Name of time zone in summer";
      }
      leaf mode {
        type Clock-summer-time-mode;
        mandatory true;
        description
          "Summer time mode";
      }
      leaf start-week-number-or-start-date {
        type uint32 {
          range "1..31";
        }
        description
          " If Mode is set to 'Recurring' specify Week
           number of the Month to start (first and last
           strings are not allowed as they are in CLI) ,
           if Mode is set to 'Date' specify Date to start ";
      }
      leaf start-weekday-or-start-year {
        type uint32 {
          range "0..2035";
        }
        description
          " If Mode is set to 'Recurring' specify Weekday
           to start , if Mode is set to 'Date' specify
           Year to start ";
      }
      leaf start-month {
        type Clock-month;
        description
          " Month to start ";
      }
      leaf start-hour {
        type uint32 {
          range "0..23";
        }
        description
          "Hour to start ";
      }
      leaf start-minute {
        type uint32 {
          range "0..59";
        }
        description
          "Minute to start ";
      }
      leaf end-week-number-or-end-date {
        type uint32 {
          range "1..31";
        }
        description
          "If Mode is set to 'Recurring' specify Week
           number of the Month to end (first and last
           strings are not allowed as they are in CLI), if
           Mode is set to 'Date' specify Date to End";
      }
      leaf end-weekday-or-end-year {
        type uint32 {
          range "0..2035";
        }
        description
          "If Mode is set to 'Recurring' specify Weekday
           to end , if Mode is set to 'Date' specify Year
           to end";
      }
      leaf end-month {
        type Clock-month;
        description
          " Month to end ";
      }
      leaf end-hour {
        type uint32 {
          range "0..23";
        }
        description
          "Hour to end ";
      }
      leaf end-minute {
        type uint32 {
          range "0..59";
        }
        description
          "Minute to end ";
      }
      leaf offset {
        type uint32 {
          range "1..1440";
        }
        units "minute";
        description
          "Offset to add in minutes ";
      }
    }
    container time-zone {
      presence "Indicates a time-zone node is configured.";
      description
        "Configure time zone";
      leaf time-zone-name {
        type string;
        mandatory true;
        description
          "Name of time zone";
      }
      leaf hour-offset {
        type int32 {
          range "-23..23";
        }
        units "hour";
        mandatory true;
        description
          "Hours offset from UTC";
      }
      leaf minute-offset {
        type uint32 {
          range "0..59";
        }
        units "minute";
        default "0";
        description
          "Minutes offset from UTC";
      }
    }
  }
}
