module cpak_driver_types {
  namespace "http://www.cisco.com/panini/calvados/slice_control/cpak/types";
  prefix cpak_driver_type;

  organization "Cisco Systems, Inc.";

  contact
    "Cisco Systems, Inc.
     Customer Service

     Postal: 170 West Tasman Drive
     San Jose, CA 95134

     Tel: +1 800 553-NETS

     E-mail: cs-yang@cisco.com";

  description 
    "This module contains definitions
     for the Calvados model objects.

    Copyright (c) 2012-2017 by Cisco Systems, Inc.
     All rights reserved.";

  revision "2015-08-30" {
    description "Initial version.";
  }


  typedef cpak_id_type {
    type string {
      pattern "all|[0-3]";
    }
  }
}
