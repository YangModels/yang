module Cisco-IOS-XR-asr9k-sc-envmon-oper {
  namespace "http://cisco.com/ns/yang/Cisco-IOS-XR-asr9k-sc-envmon-oper";
  prefix asr9k-sc-envmon-oper;

  import Cisco-IOS-XR-types {
    prefix xr;
  }
  include Cisco-IOS-XR-asr9k-sc-envmon-oper-sub1 {
    revision-date 2017-01-19;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR asr9k-sc-envmon package operational data.
     
     This module contains definitions
     for the following management objects:
       environmental-monitoring-cli: Environmental Monitoring
         Operational data space
       environmental-monitoring: environmental monitoring
     
     Copyright (c) 2013-2017 by Cisco Systems, Inc.
     All rights reserved.";

  revision 2017-01-19 {
    description
      "IOS-XR 6.2.1 revision.";
  }
  revision 2015-11-09 {
    description
      "IOS XR 6.0 revision.";
  }

  container environmental-monitoring-cli {
    config false;
    description
      "Environmental Monitoring Operational data space";
    container rack-clis {
      description
        "Table of racks";
      list rack-cli {
        key "rack";
        description
          "Number";
        container slot-clis {
          description
            "Table of slots";
          list slot-cli {
            key "slot";
            description
              "Name";
            container module-clis {
              description
                "Table of modules";
              list module-cli {
                key "module";
                description
                  "Name";
                container sensor-type-clis {
                  description
                    "Table of sensor types";
                  list sensor-type-cli {
                    key "type";
                    description
                      "Type of sensor";
                    container sensor-name-clis {
                      description
                        "Table of sensors";
                      list sensor-name-cli {
                        key "name";
                        description
                          "Name of sensor";
                        container value-detailed-cli {
                          description
                            "Detailed sensor information including
                             the sensor value";
                          uses ENVMON-SENSOR-INFO;
                        }
                        container threshold-clis {
                          description
                            "The threshold information";
                          list threshold-cli {
                            key "type";
                            description
                              "Types of thresholds";
                            container value-detailed-cli {
                              description
                                "Detailed sensor threshold
                                 information";
                              uses ENVMON-THRESHOLD-INFO;
                            }
                            leaf trap-cli {
                              type boolean;
                              description
                                "Threshold trap enable flag
                                 true-ENABLE, false-DISABLE";
                            }
                            leaf value-brief-cli {
                              type xr:Hex-integer;
                              description
                                "Threshold value for the sensor";
                            }
                            leaf type {
                              type xr:Cisco-ios-xr-string;
                              description
                                "Threshold type";
                            }
                          }
                        }
                        leaf value-brief-cli {
                          type xr:Hex-integer;
                          description
                            "The sensor value";
                        }
                        leaf name {
                          type xr:Cisco-ios-xr-string;
                          description
                            "Sensor name";
                        }
                      }
                    }
                    leaf type {
                      type xr:Cisco-ios-xr-string;
                      description
                        "Sensor type";
                    }
                  }
                }
                container power-cli {
                  description
                    "Module Power Draw";
                  container power-bag-cli {
                    description
                      "Detailed power bag information";
                    uses ENVMON-POWER-INFO;
                  }
                }
                leaf module {
                  type xr:Cisco-ios-xr-string;
                  description
                    "Module name";
                }
              }
            }
            leaf slot {
              type xr:Cisco-ios-xr-string;
              description
                "Slot name";
            }
          }
        }
        leaf rack {
          type int32;
          description
            "Rack number";
        }
      }
    }
  }
  container environmental-monitoring {
    config false;
    description
      "environmental monitoring";
    container racks {
      description
        "Table of racks";
      list rack {
        key "rack";
        description
          "Number";
        container slots {
          description
            "Table of slots";
          list slot {
            key "slot";
            description
              "Name";
            container modules {
              description
                "Table of modules";
              list module {
                key "module";
                description
                  "Name";
                container power {
                  description
                    "Module Power Draw";
                  container power-bag {
                    description
                      "Detailed power bag information";
                    uses ENVMON-POWER-INFO;
                  }
                }
                container sensor-types {
                  description
                    "Table of sensor types";
                  list sensor-type {
                    key "type";
                    description
                      "Type of sensor";
                    container sensor-names {
                      description
                        "Table of sensors";
                      list sensor-name {
                        key "name";
                        description
                          "Name of sensor";
                        container thresholds {
                          description
                            "The threshold information";
                          list threshold {
                            key "type";
                            description
                              "Types of thresholds";
                            container value-detailed {
                              description
                                "Detailed sensor threshold
                                 information";
                              uses ENVMON-THRESHOLD-INFO;
                            }
                            leaf trap {
                              type boolean;
                              description
                                "Threshold trap enable flag
                                 true-ENABLE, false-DISABLE";
                            }
                            leaf value-brief {
                              type xr:Hex-integer;
                              description
                                "Threshold value for the sensor";
                            }
                            leaf type {
                              type xr:Cisco-ios-xr-string;
                              description
                                "Threshold type";
                            }
                          }
                        }
                        container value-detailed {
                          description
                            "Detailed sensor information including
                             the sensor value";
                          uses ENVMON-SENSOR-INFO;
                        }
                        leaf value-brief {
                          type xr:Hex-integer;
                          description
                            "The sensor value";
                        }
                        leaf name {
                          type xr:Cisco-ios-xr-string;
                          description
                            "Sensor name";
                        }
                      }
                    }
                    leaf type {
                      type xr:Cisco-ios-xr-string;
                      description
                        "Sensor type";
                    }
                  }
                }
                leaf module {
                  type xr:Cisco-ios-xr-string;
                  description
                    "Module name";
                }
              }
            }
            leaf slot {
              type xr:Cisco-ios-xr-string;
              description
                "Slot name";
            }
          }
        }
        leaf rack {
          type int32;
          description
            "Rack number";
        }
      }
    }
  }
}
