module Cisco-IOS-XR-sysadmin-sm-hw-mod {
  namespace "http://www.cisco.com/ns/yang/Cisco-IOS-XR-sysadmin-sm-hw-mod";
  prefix shelf_sm_hw_mod;

  import tailf-common {
    prefix tailf;
  }
  import Cisco-IOS-XR-sysadmin-types {
    prefix calvados;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains a collection of YANG
     definitions for Cisco IOS-XR SysAdmin configuration.
     
     This module holds Shelf Management HW module data.
     
     Copyright(c) 2012-2017 by Cisco Systems, Inc.
     All rights reserved.";

  revision 2017-04-12 {
    description
      "Changed namespace and module name";
  }
  revision 2012-10-24 {
    description
      "Initial revision of the partition from sm.yang";
  }

  grouping hw-module-config-group {
    uses hw-module-shutdown-config-group;
    uses hw-module-reset-auto-disable-config-group;
    uses hw-module-offline-config-group;
  }

  grouping hw-module-shutdown-config-group {
    container shutdown {
      tailf:info "Shut down a hardware module";
      tailf:validate "shut_loc_validate" {
        tailf:dependency ".";
      }
      list location {
        key "location";
        tailf:info "Location of hardware module";
        leaf location {
          type calvados:location-id;
          mandatory true;
          tailf:info "location to (keep) shut down";
        }
      }
    }
  }

  grouping hw-module-reset-auto-disable-config-group {
    container reset {
      tailf:info "Do not auto-reset a hardware module on fault";
      tailf:validate "rad_loc_validate" {
        tailf:dependency ".";
      }
      container auto {
        tailf:info "Do not auto-reset a hardware module on fault";
        container disable {
          tailf:info "Do not auto-reset a hardware module on fault";
          list location {
            key "location";
            tailf:info "Location of hardware module";
            leaf location {
              type calvados:location-id;
              mandatory true;
              tailf:info "Location to disable auto reset recovery";
            }
          }
        }
      }
    }
  }

  grouping hw-module-offline-config-group {
    container offline {
      tailf:hidden "full";
      tailf:info "Keep a hardware module off line for diagnostics";
      list location {
        key "location";
        tailf:info "Location of hardware module";
        leaf location {
          type calvados:location-id;
          mandatory true;
          tailf:info "Location to (keep) off line";
        }
      }
    }
  }

  grouping hw-module-action-group {
    uses hw-module-reload-action-group;
    uses hw-module-bootmedia-action-group;
    uses hw-module-shutdown-action-group;
    uses hw-module-offline-action-group;
    uses hw-module-online-action-group;
  }

  grouping hw-module-bootmedia-action-group {
    container cbootmedia {
      config false;
      tailf:display-when "contains(../../location,'RP') or contains(../../location,'RSP') or contains(../../location,'SC') or contains(../../location, 'all') or re-match(../../location, '[0-9].*/[0-9].*')";
      tailf:callpoint "hwmodule_bootmedia";
      tailf:cli-drop-node-name;
      list bootmedia {
        key "bootmedium";
        config false;
        tailf:info "Select boot media to load image from";
        leaf bootmedium {
          type string;
        }
        tailf:action "reload" {
          tailf:display-when "contains(../../bootmedia,'usb') or contains(../../bootmedia,'network') or contains(../../bootmedia,'recovery-partition')";
          tailf:info "Reload a hardware module";
          tailf:actionpoint "hwmodule_reload_1";
          output {
            leaf result {
              type string;
              mandatory true;
            }
          }
        }
      }
    }
  }

  grouping hw-module-reload-action-group {
    tailf:action "reload" {
      tailf:info "Reload a hardware module";
      tailf:actionpoint "hwmodule_reload";
      input {
        leaf force {
          type empty;
          mandatory false;
          tailf:info "Do not wait for an orderly shutdown";
        }
        leaf noprompt {
          type empty;
          mandatory false;
          tailf:info "Do not prompt user for confirmation";
        }
      }
      output {
        leaf result {
          type string;
          mandatory true;
        }
      }
    }
  }

  grouping hw-module-shutdown-action-group {
    tailf:action "shutdown" {
      tailf:info "Shut down a hardware module";
      tailf:actionpoint "hwmodule_shutdown";
      input {
        choice shutdown_polarity {
          mandatory false;
          case shutdown {
            leaf force {
              type empty;
              mandatory false;
              tailf:info "Do not wait for an orderly shutdown";
            }
          }
          case powerup {
            leaf disable {
              type empty;
              mandatory false;
              tailf:hidden "full";
              tailf:info "Bring the module back up";
            }
          }
        }
      }
      output {
        leaf result {
          type string;
          mandatory true;
        }
      }
    }
  }

  grouping hw-module-offline-action-group {
    tailf:action "offline" {
      tailf:info "Take a hardware module offline for diagnostics";
      tailf:actionpoint "hwmodule_offline";
      output {
        leaf result {
          type string;
          mandatory true;
        }
      }
    }
  }

  grouping hw-module-online-action-group {
    tailf:action "online" {
      tailf:info "Take a hardware module online for normal operation";
      tailf:actionpoint "hwmodule_online";
      output {
        leaf result {
          type string;
          mandatory true;
        }
      }
    }
  }
  tailf:id "http://www.cisco.com/panini/calvados/shelf_sm_hw_mod";
}
