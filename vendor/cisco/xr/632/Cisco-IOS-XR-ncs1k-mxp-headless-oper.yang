module Cisco-IOS-XR-ncs1k-mxp-headless-oper {
  namespace "http://cisco.com/ns/yang/Cisco-IOS-XR-ncs1k-mxp-headless-oper";
  prefix ncs1k-mxp-headless-oper;

  import Cisco-IOS-XR-types {
    prefix xr;
  }
  include Cisco-IOS-XR-ncs1k-mxp-headless-oper-sub1 {
    revision-date 2017-03-30;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ncs1k-mxp-headless package operational data.
     
     This module contains definitions
     for the following management objects:
       headless-func-data: Information related to headless
         functionality
     
     Copyright (c) 2013-2017 by Cisco Systems, Inc.
     All rights reserved.";

  revision 2017-03-30 {
    description
      "PRBS stats added";
  }
  revision 2015-11-09 {
    description
      "IOS XR 6.0 revision.";
  }

  container headless-func-data {
    config false;
    description
      "Information related to headless functionality";
    container otn-port-names {
      description
        "OTN Statistics collected during last headless
         operation";
      list otn-port-name {
        key "name";
        description
          "port Name";
        leaf name {
          type xr:Interface-name;
          description
            "Port name";
        }
        uses MXP-HEADLESS-OTN-CNT-INFO;
      }
    }
    container ethernet-port-names {
      description
        "Ethernet Statistics collected during last
         headless operation";
      list ethernet-port-name {
        key "name";
        description
          "Port Name";
        leaf name {
          type xr:Interface-name;
          description
            "Port name";
        }
        uses MXP-HEADLESS-ETHER-PRIM-INFO;
      }
    }
  }
}
