submodule Cisco-IOS-XR-mpls-te-oper-sub1 {
  belongs-to Cisco-IOS-XR-mpls-te-oper {
    prefix Cisco-IOS-XR-mpls-te-oper;
  }

  import ietf-inet-types {
    prefix inet;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR mpls-te package operational data.
     
     Copyright (c) 2013-2017 by Cisco Systems, Inc.
     All rights reserved.";

  revision 2017-05-01 {
    description
      "Fixing backward compatibility error in module.";
  }
  revision 2015-11-09 {
    description
      "IOS XR 6.0 revision.";
  }

  typedef Mpls-tp-tunnel-switchover-trig {
    type enumeration {
      enum "none" {
        description
          "No Trigger";
      }
      enum "bfd" {
        description
          "Trigger is BFD";
      }
      enum "local-lockout" {
        description
          "Trigger is local lockout";
      }
      enum "remote-lockout" {
        description
          "Trigger is remote lockout";
      }
      enum "ais" {
        description
          "Trigger is AIS";
      }
      enum "ldi" {
        description
          "Trigger is LDI";
      }
      enum "lkr" {
        description
          "Trigger is LKR";
      }
      enum "link-down" {
        description
          "Trigger is due to link down event";
      }
    }
    description
      "Transport profile protection switchover triggers";
  }

  typedef Mpls-tp-tunnel-active-lsp {
    type enumeration {
      enum "working" {
        description
          "Working LSP";
      }
      enum "protect" {
        description
          "Protect LSP";
      }
      enum "none" {
        description
          "Neither working nor protection LSP is active";
      }
    }
    description
      "Transport profile tunnel active LSP";
  }

  typedef Mpls-tp-lsp-bfd-state {
    type enumeration {
      enum "down" {
        description
          "BFD down";
      }
      enum "up" {
        description
          "BFD up";
      }
    }
    description
      "Transport profile LSP BFD states";
  }

  typedef Mpls-tp-lsp-oam-state {
    type enumeration {
      enum "none" {
        description
          "No fault";
      }
      enum "ldi" {
        description
          "LDI";
      }
      enum "lkr" {
        description
          "LKR";
      }
      enum "ais" {
        description
          "AIS";
      }
    }
    description
      "Transport profile LSP OAM states";
  }

  typedef Mpls-tp-lsp-state {
    type enumeration {
      enum "down" {
        description
          "Down";
      }
      enum "up" {
        description
          "Up";
      }
      enum "active" {
        description
          "Up (active)";
      }
      enum "unknown" {
        description
          "Unknown";
      }
    }
    description
      "Transport profile LSP states";
  }

  typedef Mpls-tp-tunnel-state {
    type enumeration {
      enum "admin-down" {
        description
          "Tunnel is administratively down";
      }
      enum "admin-up" {
        description
          "Tunnel is administratively up";
      }
      enum "oper-up" {
        description
          "Tunnel is operationally up";
      }
      enum "oper-down" {
        description
          "Tunnel is operationally down";
      }
    }
    description
      "Transport profile tunnel states";
  }

  grouping MPLS-TE-TP-GLOBAL-INFO {
    description
      "Transport profile global information";
    container oam-protection-triggers {
      description
        "OAM Protection Triggers";
      uses MPLS-TE-TP-OAM-PROT-TRIGGER;
    }
    leaf node-id {
      type inet:ipv4-address;
      description
        "Node ID";
    }
    leaf global-id {
      type uint32;
      description
        "Global ID";
    }
    leaf oam-refresh {
      type uint32;
      units "second";
      description
        "OAM refresh interval in seconds";
    }
    leaf bfd-interval {
      type uint32;
      description
        "BFD interval";
    }
    leaf bfd-interval-in-micro-sec {
      type boolean;
      description
        "Is global BFD interval in micro sec";
    }
    leaf bfd-interval-standby {
      type uint32;
      description
        "BFD interval for standby LSPs";
    }
    leaf bfd-interval-standby-in-micro-sec {
      type boolean;
      description
        "Is global BFD interval for standby LSPs in micro
         sec";
    }
    leaf bfd-multiplier {
      type uint32;
      description
        "BFD multiplier";
    }
    leaf bfd-multiplier-standby {
      type uint32;
      description
        "BFD multiplier for standby LSPs";
    }
    leaf wait-to-restore-interval {
      type uint32;
      units "second";
      description
        "Wait to restore interval for working LSP in
         seconds";
    }
    leaf alarm-suppression {
      type boolean;
      description
        "Tunnel/LSP alarm suppression";
    }
    leaf soak-time {
      type uint32;
      units "second";
      description
        "Tunnel/LSP alarm soak time in seconds";
    }
  }

  grouping MPLS-TE-TP-OAM-PROT-TRIGGER {
    description
      "Transport profile tunnel OAM protection triggers";
    leaf ais {
      type boolean;
      description
        "Trigger due to AIS";
    }
    leaf ldi {
      type boolean;
      description
        "Trigger due to LDI";
    }
    leaf lkr {
      type boolean;
      description
        "Trigger due to LKR";
    }
  }

  grouping MPLS-TE-TP-DETAIL-TUNNEL-LSP-INFO {
    description
      "Transport profile LSP end-point detail
       information";
    container brief-information {
      description
        "Brief LSP information";
      uses MPLS-TE-TP-TUNNEL-LSP-INFO;
    }
    leaf oam-refresh-interval {
      type uint32;
      description
        "OAM refresh interval";
    }
    leaf tp-out-label {
      type uint32;
      description
        "Outgoing label";
    }
    leaf link-id {
      type uint32;
      description
        "Transport Profile Link Identifier";
    }
    leaf out-interface-name {
      type string;
      description
        "Outgoing interface name";
    }
    leaf out-next-hop {
      type inet:ipv4-address;
      description
        "Outgoing next hop in IPv4 address format";
    }
    leaf in-label {
      type uint32;
      description
        "Incoming label";
    }
    leaf reserved-bandwidth {
      type uint32;
      units "kbit/s";
      description
        "Reserved Bandwidth in Kbps";
    }
  }

  grouping MPLS-TE-TP-TUNNEL-LSP-INFO {
    description
      "Transport profile LSP end-point information";
    leaf lsp-id {
      type uint32;
      description
        "LSP identifier";
    }
    leaf state {
      type Mpls-tp-lsp-state;
      description
        "LSP state";
    }
    leaf lock-out {
      type boolean;
      description
        "Lock out";
    }
    leaf rx-oam-state {
      type Mpls-tp-lsp-oam-state;
      description
        "Received fault OAM state";
    }
    leaf tx-oam-state {
      type Mpls-tp-lsp-oam-state;
      description
        "Transmitted fault OAM state";
    }
    leaf bfd-state {
      type Mpls-tp-lsp-bfd-state;
      description
        "BFD state";
    }
  }

  grouping MPLS-TE-TP-TUNNEL-INFO {
    description
      "Transport profile tunnel Information";
    container working-lsp {
      description
        "Working LSP information";
      uses MPLS-TE-TP-TUNNEL-LSP-INFO;
    }
    container protect-lsp {
      description
        "Protect LSP information";
      uses MPLS-TE-TP-TUNNEL-LSP-INFO;
    }
    leaf tunnel-name {
      type string;
      description
        "Transport profile tunnel name";
    }
    leaf source-tunnel-id {
      type uint32;
      description
        "Source tunnel identifier";
    }
    leaf source-node-id {
      type inet:ipv4-address;
      description
        "Source node ID";
    }
    leaf source-global-id {
      type uint32;
      description
        "Source global ID";
    }
    leaf destination-node-id {
      type inet:ipv4-address;
      description
        "Destination node ID";
    }
    leaf destination-global-id {
      type uint32;
      description
        "Destination global ID";
    }
    leaf remote-tunnel-id {
      type uint32;
      description
        "Remote tunnel identifier";
    }
    leaf admin-status {
      type Mpls-tp-tunnel-state;
      description
        "Tunnel admin status";
    }
    leaf operation-status {
      type Mpls-tp-tunnel-state;
      description
        "Tunnel operational status";
    }
    leaf active-lsp {
      type Mpls-tp-tunnel-active-lsp;
      description
        "Active LSP";
    }
  }

  grouping MPLS-TE-TP-DETAIL-TUNNEL-INFO {
    description
      "Transport profile detail tunnel information";
    container tunnel {
      description
        "Brief tunnel information";
      uses MPLS-TE-TP-TUNNEL-INFO;
    }
    container working-lsp {
      description
        "Working LSP information";
      uses MPLS-TE-TP-DETAIL-TUNNEL-LSP-INFO;
    }
    container protect-lsp {
      description
        "Protect LSP information";
      uses MPLS-TE-TP-DETAIL-TUNNEL-LSP-INFO;
    }
    container oam-protection-triggers {
      description
        "OAM Protection Triggers";
      uses MPLS-TE-TP-OAM-PROT-TRIGGER;
    }
    leaf req-bandwidth {
      type uint32;
      units "kbit/s";
      description
        "Requested tunnel bandwidth in Kbps";
    }
    leaf oam-interval {
      type uint32;
      description
        "OAM Interval";
    }
    leaf bfd-interval-active {
      type uint32;
      description
        "BFD interval for active LSP";
    }
    leaf bfd-interval-active-in-micro-sec {
      type boolean;
      description
        "Is BFD interval for active LSP in micro sec";
    }
    leaf bfd-multiplier-active {
      type uint32;
      description
        "BFD multiplier for active LSP";
    }
    leaf bfd-interval-standby {
      type uint32;
      description
        "BFD interval for standby LSP";
    }
    leaf bfd-interval-standby-in-micro-sec {
      type boolean;
      description
        "Is BFD interval for standby LSP in micro sec";
    }
    leaf bfd-multiplier-standby {
      type uint32;
      description
        "BFD multiplier for standby LSP";
    }
    leaf tunnel-up-time {
      type uint32;
      units "second";
      description
        "Time in seconds since tunnel went up";
    }
    leaf switchover-trig {
      type Mpls-tp-tunnel-switchover-trig;
      description
        "Switchover trigger";
    }
    leaf switch-over-time {
      type uint32;
      description
        "The time at which last switchover was triggered";
    }
  }

  grouping MPLS-TE-TP-TUNNEL-SUMMARY {
    description
      "Transport profile tunnel summary";
    leaf up-working-ls-ps {
      type uint32;
      description
        "Number of working LSPs that are in up state";
    }
    leaf active-working-ls-ps {
      type uint32;
      description
        "Number of working LSPs that are active";
    }
    leaf down-working-ls-ps {
      type uint32;
      description
        "Number of Working LSPs that are in down state";
    }
    leaf locked-working-ls-ps {
      type uint32;
      description
        "Number of working LSPs that are locked out";
    }
    leaf up-protect-ls-ps {
      type uint32;
      description
        "Number of protect LSPs that are in up state";
    }
    leaf active-protect-ls-ps {
      type uint32;
      description
        "Number of protect LSPs that are active";
    }
    leaf down-protect-ls-ps {
      type uint32;
      description
        "Number of protect LSPs that are in down state";
    }
    leaf locked-protect-ls-ps {
      type uint32;
      description
        "Number of protect LSPs that are locked out";
    }
    leaf up-tunnels {
      type uint32;
      description
        "Number of tunnels that are in up state";
    }
    leaf down-tunnels {
      type uint32;
      description
        "Number of tunnels that are in down state";
    }
    leaf admin-down-tunnels {
      type uint32;
      description
        "Number of tunnels that are administratively down";
    }
    leaf complete-fec-working-ls-ps {
      type uint32;
      description
        "Number of working LSPs with complete FEC";
    }
    leaf complete-fec-protect-ls-ps {
      type uint32;
      description
        "Number of protect LSPs with complete FEC";
    }
    leaf bfd-session-working-ls-ps {
      type uint32;
      description
        "Number of working LSPs with BFD session";
    }
    leaf bfd-session-protect-ls-ps {
      type uint32;
      description
        "Number of protect LSPs with BFD session";
    }
  }
}
