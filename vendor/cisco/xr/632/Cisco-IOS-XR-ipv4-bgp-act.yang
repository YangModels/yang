module Cisco-IOS-XR-ipv4-bgp-act {
  namespace "http://cisco.com/ns/yang/Cisco-IOS-XR-ipv4-bgp-act";
  prefix bgp-act;

  import Cisco-IOS-XR-types {
    prefix csc;
  }
  import ietf-inet-types {
    prefix inet;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR action package configuration.
     
     Copyright (c) 2016-2017 by Cisco Systems, Inc.
     All rights reserved.";

  revision 2016-10-12 {
    description
      "IOS XR 6.2.1 revision.";
  }

  typedef update-group-id {
    type string {
      pattern "(([0-9]|1[0-5])\\.\\d+)";
    }
  }

  typedef refresh-sub-group-id {
    type string {
      pattern "(([0-9]|1[0-5])\\.\\d+)(:\\d+)";
    }
  }

  typedef ip-netmask {
    type inet:ip-address;
  }

  typedef ipv4-netmask {
    type inet:ipv4-address;
  }

  typedef ipv6-netmask {
    type inet:ipv6-address;
  }

  typedef two-byte {
    type uint16 {
      range "1..65535";
    }
  }

  typedef as-number {
    type union {
      type two-byte-as;
      type four-byte-as;
    }
    description
      "AS number";
  }

  typedef two-byte-as {
    type uint16 {
      range "1..65535";
    }
  }

  typedef four-byte-as {
    type union {
      type as-four-byte;
      type as-plain;
    }
  }

  typedef as-four-byte {
    type string {
      pattern "(\\d+\\.\\d+)";
    }
  }

  typedef as-plain {
    type uint32 {
      range "65536..4294967295";
    }
  }

  typedef rd {
    type union {
      type rd-four-byte-as;
      type rd-two-byte-as;
      type rd-plain-as;
      type rd-ipv4-address;
    }
    description
      "Route distinguisher";
  }

  typedef rd-four-byte-as {
    type string {
      pattern "(\\d+\\.\\d+:\\d+)";
    }
  }

  typedef rd-two-byte-as {
    type string {
      pattern "(\\d+:\\d+)";
    }
  }

  typedef rd-plain-as {
    type string {
      pattern "(\\d+:\\d+)";
    }
  }

  typedef rd-ipv4-address {
    type string {
      pattern "(([0-9]|[1-9][0-9]|1[0-9][0-9]|2[0-4][0-9]|25[0-5])\\.){3}([0-9]|[1-9][0-9]|1[0-9][0-9]|2[0-4][0-9]|25[0-5])(:\\d+)";
    }
  }

  typedef afi-safi-type {
    type enumeration {
      enum "all-all" {
        description
          "Both unicast and multicast address family modifiers
           of ipv4 and ipv6 address family";
      }
      enum "all-evpn";
      enum "all-flowspec";
      enum "all-labeled-unicast";
      enum "all-mdt";
      enum "all-mspw";
      enum "all-multicast";
      enum "all-mvpn";
      enum "all-rt-filter";
      enum "all-sr-policy";
      enum "all-tunnel";
      enum "all-unicast";
      enum "all-vpls";
      enum "all-vpws";
      enum "ipv4-all" {
        description
          "Both unicast and multicast address family modifiers";
      }
      enum "ipv4-flowspec";
      enum "ipv4-labeled-unicast";
      enum "ipv4-mdt";
      enum "ipv4-multicast";
      enum "ipv4-mvpn";
      enum "ipv4-rt-filter";
      enum "ipv4-sr-policy";
      enum "ipv4-tunnel";
      enum "ipv4-unicast";
      enum "ipv6-all" {
        description
          "Both unicast and multicast address family modifiers";
      }
      enum "ipv6-flowspec";
      enum "ipv6-labeled-unicast";
      enum "ipv6-multicast";
      enum "ipv6-mvpn";
      enum "ipv6-sr-policy";
      enum "ipv6-unicast";
      enum "l2vpn-evpn";
      enum "l2vpn-mspw";
      enum "l2vpn-vpls";
      enum "l2vpn-vpws";
      enum "link-state";
      enum "vpnv4-flowspec";
      enum "vpnv4-multicast";
      enum "vpnv4-unicast";
      enum "vpnv6-flowspec";
      enum "vpnv6-multicast";
      enum "vpnv6-unicast";
    }
  }

  typedef afi {
    type enumeration {
      enum "all" {
        description
          "Both ipv4 and ipv6 address families";
      }
      enum "ipv4";
      enum "ipv6";
      enum "l2vpn";
      enum "link-state";
      enum "vpnv4";
      enum "vpnv6";
    }
  }

  typedef safi {
    type union {
      type ipv4-safi;
      type ipv6-safi;
      type l2vpn-safi;
      type link-state-safi;
      type vpnv4-safi;
      type vpnv6-safi;
    }
  }

  typedef ipv4-safi {
    type enumeration {
      enum "all" {
        description
          "Both unicast and multicast address family modifiers";
      }
      enum "flowspec";
      enum "labeled-unicast";
      enum "mdt";
      enum "multicast";
      enum "mvpn";
      enum "rt-filter";
      enum "sr-policy";
      enum "tunnel";
      enum "unicast";
    }
  }

  typedef ipv6-safi {
    type enumeration {
      enum "all" {
        description
          "Both unicast and multicast address family modifiers";
      }
      enum "flowspec";
      enum "labeled-unicast";
      enum "multicast";
      enum "mvpn";
      enum "sr-policy";
      enum "unicast";
    }
  }

  typedef l2vpn-safi {
    type enumeration {
      enum "evpn";
      enum "mspw";
      enum "vpls";
      enum "vpws";
    }
  }

  typedef link-state-safi {
    type enumeration {
      enum "link-state";
    }
  }

  typedef vpnv4-safi {
    type enumeration {
      enum "flowspec";
      enum "multicast";
      enum "unicast";
    }
  }

  typedef vpnv6-safi {
    type enumeration {
      enum "flowspec";
      enum "multicast";
      enum "unicast";
    }
  }

  typedef instance-name {
    type union {
      type enumeration {
        enum "all";
      }
      type string;
    }
  }

  typedef vrf-name {
    type union {
      type enumeration {
        enum "all";
      }
      type string;
    }
  }

  rpc clear-bgp-all-graceful {
    description
      "Clear all peers and all routes from the BGP table.
       Clear with a hard reset and a graceful restart.
      ";
    csc:xr-task "bgp";
    csc:cli-command "clear bgp * graceful";
  }
  rpc clear-bgp-all {
    description
      "Clear all peers and all routes from the BGP table.\n";
    csc:xr-task "bgp";
    csc:cli-command "clear bgp *";
  }
  rpc clear-bgp-ip-addr-graceful {
    description
      "BGP neighbor address to clear.
       Clear with a hard reset and a graceful restart.
      ";
    input {
      leaf ip-addr {
        type inet:ip-address;
        mandatory true;
        description
          "BGP neighbor address to clear";
      }
    }
    csc:xr-task "bgp";
    csc:cli-command "clear bgp <ip-addr> graceful";
  }
  rpc clear-bgp-ip-addr-long-lived-stale {
    description
      "BGP neighbor address to clear.
       Clear long-lived-stale routes.
      ";
    input {
      leaf ip-addr {
        type inet:ip-address;
        mandatory true;
        description
          "BGP neighbor address to clear";
      }
    }
    csc:xr-task "bgp";
    csc:cli-command "clear bgp <ip-addr> long-lived-stale";
  }
  rpc clear-bgp-ip-addr {
    description
      "BGP neighbor address to clear.\n";
    input {
      leaf ip-addr {
        type inet:ip-address;
        mandatory true;
        description
          "BGP neighbor address to clear";
      }
    }
    csc:xr-task "bgp";
    csc:cli-command "clear bgp <ip-addr>";
  }
  rpc clear-bgp-afi-safi-all-soft-in-prefix-filter {
    description
      "Clear all peers and all routes from the BGP table.
       Soft reconfig.
       Soft reconfig inbound update.
       Push out prefix ORF and do inbound soft reconfig.
      ";
    input {
      leaf afi-safi-name {
        type afi-safi-type;
        mandatory true;
        description
          "AFI and SAFI";
      }
    }
    csc:xr-task "bgp";
    csc:cli-command "clear bgp <afi-safi-name> * soft in prefix-filter";
  }
  rpc clear-bgp-afi-safi-all-soft-in {
    description
      "Clear all peers and all routes from the BGP table.
       Soft reconfig.
       Soft reconfig inbound update.
      ";
    input {
      leaf afi-safi-name {
        type afi-safi-type;
        mandatory true;
        description
          "AFI and SAFI";
      }
    }
    csc:xr-task "bgp";
    csc:cli-command "clear bgp <afi-safi-name> * soft in";
  }
  rpc clear-bgp-afi-safi-all-soft-out {
    description
      "Clear all peers and all routes from the BGP table.
       Soft reconfig.
       Soft reconfig outbound update.
      ";
    input {
      leaf afi-safi-name {
        type afi-safi-type;
        mandatory true;
        description
          "AFI and SAFI";
      }
    }
    csc:xr-task "bgp";
    csc:cli-command "clear bgp <afi-safi-name> * soft out";
  }
  rpc clear-bgp-afi-safi-all-soft {
    description
      "Clear all peers and all routes from the BGP table.
       Soft reconfig.
      ";
    input {
      leaf afi-safi-name {
        type afi-safi-type;
        mandatory true;
        description
          "AFI and SAFI";
      }
    }
    csc:xr-task "bgp";
    csc:cli-command "clear bgp <afi-safi-name> * soft";
  }
  rpc clear-bgp-afi-safi-ip-addr-long-lived-stale {
    description
      "Clear long-lived-stale routes.\n";
    input {
      leaf afi-safi-name {
        type afi-safi-type;
        mandatory true;
        description
          "AFI and SAFI";
      }
      leaf ip-addr {
        type inet:ip-address;
        mandatory true;
        description
          "BGP neighbor address to clear";
      }
    }
    csc:xr-task "bgp";
    csc:cli-command "clear bgp <afi-safi-name> <ip-addr> long-lived-stale";
  }
  rpc clear-bgp-afi-safi-ip-addr-soft-in-prefix-filter {
    description
      "Soft reconfig.
       Soft reconfig inbound update.
       Push out prefix ORF and do inbound soft reconfig.
      ";
    input {
      leaf afi-safi-name {
        type afi-safi-type;
        mandatory true;
        description
          "AFI and SAFI";
      }
      leaf ip-addr {
        type inet:ip-address;
        mandatory true;
        description
          "BGP neighbor address to clear";
      }
    }
    csc:xr-task "bgp";
    csc:cli-command "clear bgp <afi-safi-name> <ip-addr> soft in prefix-filter";
  }
  rpc clear-bgp-afi-safi-ip-addr-soft-in {
    description
      "Soft reconfig.
       Soft reconfig inbound update.
      ";
    input {
      leaf afi-safi-name {
        type afi-safi-type;
        mandatory true;
        description
          "AFI and SAFI";
      }
      leaf ip-addr {
        type inet:ip-address;
        mandatory true;
        description
          "BGP neighbor address to clear";
      }
    }
    csc:xr-task "bgp";
    csc:cli-command "clear bgp <afi-safi-name> <ip-addr> soft in";
  }
  rpc clear-bgp-afi-safi-ip-addr-soft-out {
    description
      "Soft reconfig.
       Soft reconfig outbound update.
      ";
    input {
      leaf afi-safi-name {
        type afi-safi-type;
        mandatory true;
        description
          "AFI and SAFI";
      }
      leaf ip-addr {
        type inet:ip-address;
        mandatory true;
        description
          "BGP neighbor address to clear";
      }
    }
    csc:xr-task "bgp";
    csc:cli-command "clear bgp <afi-safi-name> <ip-addr> soft out";
  }
  rpc clear-bgp-afi-safi-ip-addr-soft {
    description
      "Soft reconfig.\n";
    input {
      leaf afi-safi-name {
        type afi-safi-type;
        mandatory true;
        description
          "AFI and SAFI";
      }
      leaf ip-addr {
        type inet:ip-address;
        mandatory true;
        description
          "BGP neighbor address to clear";
      }
    }
    csc:xr-task "bgp";
    csc:cli-command "clear bgp <afi-safi-name> <ip-addr> soft";
  }
  rpc clear-bgp-afi-safi-as-soft-in-prefix-filter {
    description
      "Clear peers in a specific AS.
       Soft reconfig.
       Soft reconfig inbound update.
       Push out prefix ORF and do inbound soft reconfig.
      ";
    input {
      leaf afi-safi-name {
        type afi-safi-type;
        mandatory true;
        description
          "AFI and SAFI";
      }
      leaf as-number {
        type as-number;
        mandatory true;
        description
          "AS number";
      }
    }
    csc:xr-task "bgp";
    csc:cli-command "clear bgp <afi-safi-name> as <as-number> soft in prefix-filter";
  }
  rpc clear-bgp-afi-safi-as-soft-in {
    description
      "Clear peers in a specific AS.
       Soft reconfig.
       Soft reconfig inbound update.
      ";
    input {
      leaf afi-safi-name {
        type afi-safi-type;
        mandatory true;
        description
          "AFI and SAFI";
      }
      leaf as-number {
        type as-number;
        mandatory true;
        description
          "AS number";
      }
    }
    csc:xr-task "bgp";
    csc:cli-command "clear bgp <afi-safi-name> as <as-number> soft in";
  }
  rpc clear-bgp-afi-safi-as-soft-out {
    description
      "Clear peers in a specific AS.
       Soft reconfig.
       Soft reconfig outbound update.
      ";
    input {
      leaf afi-safi-name {
        type afi-safi-type;
        mandatory true;
        description
          "AFI and SAFI";
      }
      leaf as-number {
        type as-number;
        mandatory true;
        description
          "AS number";
      }
    }
    csc:xr-task "bgp";
    csc:cli-command "clear bgp <afi-safi-name> as <as-number> soft out";
  }
  rpc clear-bgp-afi-safi-as-soft {
    description
      "Clear peers in a specific AS.
       Soft reconfig.
      ";
    input {
      leaf afi-safi-name {
        type afi-safi-type;
        mandatory true;
        description
          "AFI and SAFI";
      }
      leaf as-number {
        type as-number;
        mandatory true;
        description
          "AS number";
      }
    }
    csc:xr-task "bgp";
    csc:cli-command "clear bgp <afi-safi-name> as <as-number> soft";
  }
  rpc clear-bgp-afi-safi-dampening-ip-prefix {
    description
      "Clear route flap dampening information.\n";
    input {
      leaf afi-safi-name {
        type afi-safi-type;
        mandatory true;
        description
          "AFI and SAFI";
      }
      leaf ip-prefix {
        type inet:ip-prefix;
        mandatory true;
        description
          "Network and mask or masklength to clear dampening information";
      }
    }
    csc:xr-task "bgp";
    csc:cli-command "clear bgp <afi-safi-name> dampening <ip-prefix>";
  }
  rpc clear-bgp-afi-safi-dampening {
    description
      "Clear route flap dampening information.\n";
    input {
      leaf afi-safi-name {
        type afi-safi-type;
        mandatory true;
        description
          "AFI and SAFI";
      }
    }
    csc:xr-task "bgp";
    csc:cli-command "clear bgp <afi-safi-name> dampening";
  }
  rpc clear-bgp-afi-safi-external-soft-in-prefix-filter {
    description
      "Clear all external peers.
       Soft reconfig.
       Soft reconfig inbound update.
       Push out prefix ORF and do inbound soft reconfig.
      ";
    input {
      leaf afi-safi-name {
        type afi-safi-type;
        mandatory true;
        description
          "AFI and SAFI";
      }
    }
    csc:xr-task "bgp";
    csc:cli-command "clear bgp <afi-safi-name> external soft in prefix-filter";
  }
  rpc clear-bgp-afi-safi-external-soft-in {
    description
      "Clear all external peers.
       Soft reconfig.
       Soft reconfig inbound update.
      ";
    input {
      leaf afi-safi-name {
        type afi-safi-type;
        mandatory true;
        description
          "AFI and SAFI";
      }
    }
    csc:xr-task "bgp";
    csc:cli-command "clear bgp <afi-safi-name> external soft in";
  }
  rpc clear-bgp-afi-safi-external-soft-out {
    description
      "Clear all external peers.
       Soft reconfig.
       Soft reconfig outbound update.
      ";
    input {
      leaf afi-safi-name {
        type afi-safi-type;
        mandatory true;
        description
          "AFI and SAFI";
      }
    }
    csc:xr-task "bgp";
    csc:cli-command "clear bgp <afi-safi-name> external soft out";
  }
  rpc clear-bgp-afi-safi-external-soft {
    description
      "Clear all external peers.
       Soft reconfig.
      ";
    input {
      leaf afi-safi-name {
        type afi-safi-type;
        mandatory true;
        description
          "AFI and SAFI";
      }
    }
    csc:xr-task "bgp";
    csc:cli-command "clear bgp <afi-safi-name> external soft";
  }
  rpc clear-bgp-afi-safi-flap-statistics-ip-addr-ipv4-mask {
    description
      "Clear flap statistics.\n";
    input {
      leaf afi-safi-name {
        type afi-safi-type;
        mandatory true;
        description
          "AFI and SAFI";
      }
      leaf ip-addr {
        type inet:ip-address;
        mandatory true;
        description
          "BGP neighbor address to clear";
      }
      leaf ipv4-mask {
        type ipv4-netmask;
        mandatory true;
        description
          "Network and mask or masklength to clear flap statistics";
      }
    }
    csc:xr-task "bgp";
    csc:cli-command "clear bgp <afi-safi-name> flap-statistics <ip-addr> <ipv4-mask>";
  }
  rpc clear-bgp-afi-safi-flap-statistics-ip-addr {
    description
      "Clear flap statistics.\n";
    input {
      leaf afi-safi-name {
        type afi-safi-type;
        mandatory true;
        description
          "AFI and SAFI";
      }
      leaf ip-addr {
        type inet:ip-address;
        mandatory true;
        description
          "BGP neighbor address to clear";
      }
    }
    csc:xr-task "bgp";
    csc:cli-command "clear bgp <afi-safi-name> flap-statistics <ip-addr>";
  }
  rpc clear-bgp-afi-safi-flap-statistics-ip-prefix {
    description
      "Clear flap statistics.\n";
    input {
      leaf afi-safi-name {
        type afi-safi-type;
        mandatory true;
        description
          "AFI and SAFI";
      }
      leaf ip-prefix {
        type inet:ip-prefix;
        mandatory true;
        description
          "Network and mask or masklength to clear flap statistics";
      }
    }
    csc:xr-task "bgp";
    csc:cli-command "clear bgp <afi-safi-name> flap-statistics <ip-prefix>";
  }
  rpc clear-bgp-afi-safi-flap-statistics-regexp {
    description
      "Clear flap statistics.
       Clear flap statistics for routes matching the regular expression.
      ";
    input {
      leaf afi-safi-name {
        type afi-safi-type;
        mandatory true;
        description
          "AFI and SAFI";
      }
      leaf regexp-pattern {
        type string;
        mandatory true;
        description
          "A regular expression to match the BGP AS paths.  Use 'ctrl-v ?' to enter '?'";
      }
    }
    csc:xr-task "bgp";
    csc:cli-command "clear bgp <afi-safi-name> flap-statistics regexp <regexp-pattern>";
  }
  rpc clear-bgp-afi-safi-flap-statistics-route-policy {
    description
      "Clear flap statistics.
       Clear flap statistics for routes matching the route policy.
      ";
    input {
      leaf afi-safi-name {
        type afi-safi-type;
        mandatory true;
        description
          "AFI and SAFI";
      }
      leaf route-policy-name {
        type string;
        mandatory true;
        description
          "Route Policy name";
      }
    }
    csc:xr-task "bgp";
    csc:cli-command "clear bgp <afi-safi-name> flap-statistics route-policy <route-policy-name>";
  }
  rpc clear-bgp-afi-safi-flap-statistics {
    description
      "Clear flap statistics.\n";
    input {
      leaf afi-safi-name {
        type afi-safi-type;
        mandatory true;
        description
          "AFI and SAFI";
      }
    }
    csc:xr-task "bgp";
    csc:cli-command "clear bgp <afi-safi-name> flap-statistics";
  }
  rpc clear-bgp-afi-safi-nexthop-performance-statistics {
    description
      "Clear nexthop.
       Performance statistics information related to processing.
      ";
    input {
      leaf afi-safi-name {
        type afi-safi-type;
        mandatory true;
        description
          "AFI and SAFI";
      }
    }
    csc:xr-task "bgp";
    csc:cli-command "clear bgp <afi-safi-name> nexthop performance-statistics";
  }
  rpc clear-bgp-afi-safi-nexthop-registration-ip-addr {
    description
      "Clear nexthop.
       Registration with RIB and reregister.
      ";
    input {
      leaf afi-safi-name {
        type afi-safi-type;
        mandatory true;
        description
          "AFI and SAFI";
      }
      leaf ip-addr {
        type inet:ip-address;
        mandatory true;
        description
          "Nexthop address";
      }
    }
    csc:xr-task "bgp";
    csc:cli-command "clear bgp <afi-safi-name> nexthop registration <ip-addr>";
  }
  rpc clear-bgp-afi-safi-self-originated {
    description
      "Clear redistributed, network and aggregate routes originated here.\n";
    input {
      leaf afi-safi-name {
        type afi-safi-type;
        mandatory true;
        description
          "AFI and SAFI";
      }
    }
    csc:xr-task "bgp";
    csc:cli-command "clear bgp <afi-safi-name> self-originated";
  }
  rpc clear-bgp-afi-safi-shutdown {
    description
      "Clear all peers which were shut down due to low memory.\n";
    input {
      leaf afi-safi-name {
        type afi-safi-type;
        mandatory true;
        description
          "AFI and SAFI";
      }
    }
    csc:xr-task "bgp";
    csc:cli-command "clear bgp <afi-safi-name> shutdown";
  }
  rpc clear-bgp-afi-safi-update-outq-address-family-update-parent {
    description
      "Clear Update information (Do NOT execute without cisco support)(cisco-support).
       Clear Update generation OutQ counters (Do NOT execute without cisco support)(cisco-support).
       Address-family.
       Update parents' OutQ counters too.
      ";
    input {
      leaf afi-safi-name {
        type afi-safi-type;
        mandatory true;
        description
          "AFI and SAFI";
      }
    }
    csc:xr-task "bgp";
    csc:cli-command "clear bgp <afi-safi-name> update outq address-family update-parent";
  }
  rpc clear-bgp-afi-safi-update-outq-address-family {
    description
      "Clear Update information (Do NOT execute without cisco support)(cisco-support).
       Clear Update generation OutQ counters (Do NOT execute without cisco support)(cisco-support).
       Address-family.
      ";
    input {
      leaf afi-safi-name {
        type afi-safi-type;
        mandatory true;
        description
          "AFI and SAFI";
      }
    }
    csc:xr-task "bgp";
    csc:cli-command "clear bgp <afi-safi-name> update outq address-family";
  }
  rpc clear-bgp-afi-safi-update-outq-neighbor-ip-addr-refresh-update-parent {
    description
      "Clear Update information (Do NOT execute without cisco support)(cisco-support).
       Clear Update generation OutQ counters (Do NOT execute without cisco support)(cisco-support).
       Neighbor.
       Refresh OutQ.
       Update parents' OutQ counters too.
      ";
    input {
      leaf afi-safi-name {
        type afi-safi-type;
        mandatory true;
        description
          "AFI and SAFI";
      }
      leaf ip-addr {
        type inet:ip-address;
        mandatory true;
        description
          "Neighbor address";
      }
    }
    csc:xr-task "bgp";
    csc:cli-command "clear bgp <afi-safi-name> update outq neighbor <ip-addr> refresh update-parent";
  }
  rpc clear-bgp-afi-safi-update-outq-neighbor-ip-addr-refresh {
    description
      "Clear Update information (Do NOT execute without cisco support)(cisco-support).
       Clear Update generation OutQ counters (Do NOT execute without cisco support)(cisco-support).
       Neighbor.
       Refresh OutQ.
      ";
    input {
      leaf afi-safi-name {
        type afi-safi-type;
        mandatory true;
        description
          "AFI and SAFI";
      }
      leaf ip-addr {
        type inet:ip-address;
        mandatory true;
        description
          "Neighbor address";
      }
    }
    csc:xr-task "bgp";
    csc:cli-command "clear bgp <afi-safi-name> update outq neighbor <ip-addr> refresh";
  }
  rpc clear-bgp-afi-safi-update-outq-neighbor-ip-addr-update-parent {
    description
      "Clear Update information (Do NOT execute without cisco support)(cisco-support).
       Clear Update generation OutQ counters (Do NOT execute without cisco support)(cisco-support).
       Neighbor.
       Update parents' OutQ counters too.
      ";
    input {
      leaf afi-safi-name {
        type afi-safi-type;
        mandatory true;
        description
          "AFI and SAFI";
      }
      leaf ip-addr {
        type inet:ip-address;
        mandatory true;
        description
          "Neighbor address";
      }
    }
    csc:xr-task "bgp";
    csc:cli-command "clear bgp <afi-safi-name> update outq neighbor <ip-addr> update-parent";
  }
  rpc clear-bgp-afi-safi-update-outq-neighbor-ip-addr {
    description
      "Clear Update information (Do NOT execute without cisco support)(cisco-support).
       Clear Update generation OutQ counters (Do NOT execute without cisco support)(cisco-support).
       Neighbor.
      ";
    input {
      leaf afi-safi-name {
        type afi-safi-type;
        mandatory true;
        description
          "AFI and SAFI";
      }
      leaf ip-addr {
        type inet:ip-address;
        mandatory true;
        description
          "Neighbor address";
      }
    }
    csc:xr-task "bgp";
    csc:cli-command "clear bgp <afi-safi-name> update outq neighbor <ip-addr>";
  }
  rpc clear-bgp-afi-safi-update-outq-update-group-sub-group-update-parent {
    description
      "Clear Update information (Do NOT execute without cisco support)(cisco-support).
       Clear Update generation OutQ counters (Do NOT execute without cisco support)(cisco-support).
       Update-group.
       Sub-group.
       Update parents' OutQ counters too.
      ";
    input {
      leaf afi-safi-name {
        type afi-safi-type;
        mandatory true;
        description
          "AFI and SAFI";
      }
      leaf update-group {
        type update-group-id;
        mandatory true;
        description
          "Update-group process ID <x.y>";
      }
      leaf sub-group {
        type update-group-id;
        mandatory true;
        description
          "Sub-group process ID <x.y>";
      }
    }
    csc:xr-task "bgp";
    csc:cli-command "clear bgp <afi-safi-name> update outq update-group <update-group> sub-group <sub-group> update-parent";
  }
  rpc clear-bgp-afi-safi-update-outq-update-group-sub-group {
    description
      "Clear Update information (Do NOT execute without cisco support)(cisco-support).
       Clear Update generation OutQ counters (Do NOT execute without cisco support)(cisco-support).
       Update-group.
       Sub-group.
      ";
    input {
      leaf afi-safi-name {
        type afi-safi-type;
        mandatory true;
        description
          "AFI and SAFI";
      }
      leaf update-group {
        type update-group-id;
        mandatory true;
        description
          "Update-group process ID <x.y>";
      }
      leaf sub-group {
        type update-group-id;
        mandatory true;
        description
          "Sub-group process ID <x.y>";
      }
    }
    csc:xr-task "bgp";
    csc:cli-command "clear bgp <afi-safi-name> update outq update-group <update-group> sub-group <sub-group>";
  }
  rpc clear-bgp-afi-safi-update-outq-update-group-sub-group-refresh-sub-group-update-parent {
    description
      "Clear Update information (Do NOT execute without cisco support)(cisco-support).
       Clear Update generation OutQ counters (Do NOT execute without cisco support)(cisco-support).
       Update-group.
       Sub-group.
       Update parents' OutQ counters too.
      ";
    input {
      leaf afi-safi-name {
        type afi-safi-type;
        mandatory true;
        description
          "AFI and SAFI";
      }
      leaf update-group {
        type update-group-id;
        mandatory true;
        description
          "Update-group process ID <x.y>";
      }
      leaf refresh-sub-group {
        type refresh-sub-group-id;
        mandatory true;
        description
          "Refresh Sub-group process ID <x.y:z>";
      }
    }
    csc:xr-task "bgp";
    csc:cli-command "clear bgp <afi-safi-name> update outq update-group <update-group> sub-group <refresh-sub-group> update-parent";
  }
  rpc clear-bgp-afi-safi-update-outq-update-group-sub-group-refresh-sub-group {
    description
      "Clear Update information (Do NOT execute without cisco support)(cisco-support).
       Clear Update generation OutQ counters (Do NOT execute without cisco support)(cisco-support).
       Update-group.
       Sub-group.
      ";
    input {
      leaf afi-safi-name {
        type afi-safi-type;
        mandatory true;
        description
          "AFI and SAFI";
      }
      leaf update-group {
        type update-group-id;
        mandatory true;
        description
          "Update-group process ID <x.y>";
      }
      leaf refresh-sub-group {
        type refresh-sub-group-id;
        mandatory true;
        description
          "Refresh Sub-group process ID <x.y:z>";
      }
    }
    csc:xr-task "bgp";
    csc:cli-command "clear bgp <afi-safi-name> update outq update-group <update-group> sub-group <refresh-sub-group>";
  }
  rpc clear-bgp-afi-safi-update-outq-update-group-update-parent {
    description
      "Clear Update information (Do NOT execute without cisco support)(cisco-support).
       Clear Update generation OutQ counters (Do NOT execute without cisco support)(cisco-support).
       Update-group.
       Update parents' OutQ counters too.
      ";
    input {
      leaf afi-safi-name {
        type afi-safi-type;
        mandatory true;
        description
          "AFI and SAFI";
      }
      leaf update-group {
        type update-group-id;
        mandatory true;
        description
          "Update-group process ID <x.y>";
      }
    }
    csc:xr-task "bgp";
    csc:cli-command "clear bgp <afi-safi-name> update outq update-group <update-group> update-parent";
  }
  rpc clear-bgp-afi-safi-update-outq-update-group {
    description
      "Clear Update information (Do NOT execute without cisco support)(cisco-support).
       Clear Update generation OutQ counters (Do NOT execute without cisco support)(cisco-support).
       Update-group.
      ";
    input {
      leaf afi-safi-name {
        type afi-safi-type;
        mandatory true;
        description
          "AFI and SAFI";
      }
      leaf update-group {
        type update-group-id;
        mandatory true;
        description
          "Update-group process ID <x.y>";
      }
    }
    csc:xr-task "bgp";
    csc:cli-command "clear bgp <afi-safi-name> update outq update-group <update-group>";
  }
  rpc clear-bgp-as-graceful {
    description
      "Clear peers in a specific AS.
       Clear with a hard reset and a graceful restart.
      ";
    input {
      leaf as-number {
        type as-number;
        mandatory true;
        description
          "AS number";
      }
    }
    csc:xr-task "bgp";
    csc:cli-command "clear bgp as <as-number> graceful";
  }
  rpc clear-bgp-as {
    description
      "Clear peers in a specific AS.\n";
    input {
      leaf as-number {
        type as-number;
        mandatory true;
        description
          "AS number";
      }
    }
    csc:xr-task "bgp";
    csc:cli-command "clear bgp as <as-number>";
  }
  rpc clear-bgp-bestpath-ip-addr-ip-netmask {
    description
      "re-run BGP bestpath selection.\n";
    input {
      leaf ip-addr {
        type inet:ip-address;
        mandatory true;
        description
          "Network";
      }
      leaf ip-netmask {
        type ip-netmask;
        mandatory true;
        description
          "Mask";
      }
    }
    csc:xr-task "bgp";
    csc:cli-command "clear bgp bestpath <ip-addr> <ip-netmask>";
  }
  rpc clear-bgp-bestpath-ip-addr {
    description
      "re-run BGP bestpath selection.\n";
    input {
      leaf ip-addr {
        type inet:ip-address;
        mandatory true;
        description
          "Network";
      }
    }
    csc:xr-task "bgp";
    csc:cli-command "clear bgp bestpath <ip-addr>";
  }
  rpc clear-bgp-bestpath-ip-prefix {
    description
      "re-run BGP bestpath selection.\n";
    input {
      leaf ip-prefix {
        type inet:ip-prefix;
        mandatory true;
        description
          "Network and masklength";
      }
    }
    csc:xr-task "bgp";
    csc:cli-command "clear bgp bestpath <ip-prefix>";
  }
  rpc clear-bgp-bestpath-afi-safi-ip-addr-ip-netmask {
    description
      "re-run BGP bestpath selection.\n";
    input {
      leaf afi-safi-name {
        type afi-safi-type;
        mandatory true;
        description
          "AFI and SAFI";
      }
      leaf ip-addr {
        type inet:ip-address;
        mandatory true;
        description
          "Network";
      }
      leaf ip-netmask {
        type ip-netmask;
        mandatory true;
        description
          "Mask";
      }
    }
    csc:xr-task "bgp";
    csc:cli-command "clear bgp bestpath <afi-safi-name> <ip-addr> <ip-netmask>";
  }
  rpc clear-bgp-bestpath-afi-safi-ip-addr {
    description
      "re-run BGP bestpath selection.\n";
    input {
      leaf afi-safi-name {
        type afi-safi-type;
        mandatory true;
        description
          "AFI and SAFI";
      }
      leaf ip-addr {
        type inet:ip-address;
        mandatory true;
        description
          "Network";
      }
    }
    csc:xr-task "bgp";
    csc:cli-command "clear bgp bestpath <afi-safi-name> <ip-addr>";
  }
  rpc clear-bgp-bestpath-afi-safi-ip-prefix {
    description
      "re-run BGP bestpath selection.\n";
    input {
      leaf afi-safi-name {
        type afi-safi-type;
        mandatory true;
        description
          "AFI and SAFI";
      }
      leaf ip-prefix {
        type inet:ip-prefix;
        mandatory true;
        description
          "Network and masklength";
      }
    }
    csc:xr-task "bgp";
    csc:cli-command "clear bgp bestpath <afi-safi-name> <ip-prefix>";
  }
  rpc clear-bgp-bestpath-afi-safi-bridge-domain-ip-addr-ip-netmask {
    description
      "re-run BGP bestpath selection.
       Display routes for a specified Bridge Domain.
      ";
    input {
      leaf afi-safi-name {
        type afi-safi-type;
        mandatory true;
        description
          "AFI and SAFI";
      }
      leaf bridge-domain-name {
        type string;
        mandatory true;
        description
          "Bridge Domain";
      }
      leaf ip-addr {
        type inet:ip-address;
        mandatory true;
        description
          "Network";
      }
      leaf ip-netmask {
        type ip-netmask;
        mandatory true;
        description
          "Mask";
      }
    }
    csc:xr-task "bgp";
    csc:cli-command "clear bgp bestpath <afi-safi-name> bridge-domain <bridge-domain-name> <ip-addr> <ip-netmask>";
  }
  rpc clear-bgp-bestpath-afi-safi-bridge-domain-ip-addr {
    description
      "re-run BGP bestpath selection.
       Display routes for a specified Bridge Domain.
      ";
    input {
      leaf afi-safi-name {
        type afi-safi-type;
        mandatory true;
        description
          "AFI and SAFI";
      }
      leaf bridge-domain-name {
        type string;
        mandatory true;
        description
          "Bridge Domain";
      }
      leaf ip-addr {
        type inet:ip-address;
        mandatory true;
        description
          "Network";
      }
    }
    csc:xr-task "bgp";
    csc:cli-command "clear bgp bestpath <afi-safi-name> bridge-domain <bridge-domain-name> <ip-addr>";
  }
  rpc clear-bgp-bestpath-afi-safi-bridge-domain-ip-prefix {
    description
      "re-run BGP bestpath selection.
       Display routes for a specified Bridge Domain.
      ";
    input {
      leaf afi-safi-name {
        type afi-safi-type;
        mandatory true;
        description
          "AFI and SAFI";
      }
      leaf bridge-domain-name {
        type string;
        mandatory true;
        description
          "Bridge Domain";
      }
      leaf ip-prefix {
        type inet:ip-prefix;
        mandatory true;
        description
          "Network and masklength";
      }
    }
    csc:xr-task "bgp";
    csc:cli-command "clear bgp bestpath <afi-safi-name> bridge-domain <bridge-domain-name> <ip-prefix>";
  }
  rpc clear-bgp-bestpath-afi-safi-rd-ip-addr-ip-netmask {
    description
      "re-run BGP bestpath selection.
       Display routes with a specific route distinguisher.
      ";
    input {
      leaf afi-safi-name {
        type afi-safi-type;
        mandatory true;
        description
          "AFI and SAFI";
      }
      leaf rd {
        type rd;
        mandatory true;
        description
          "Route distinguisher";
      }
      leaf ip-addr {
        type inet:ip-address;
        mandatory true;
        description
          "Network";
      }
      leaf ip-netmask {
        type ip-netmask;
        mandatory true;
        description
          "Mask";
      }
    }
    csc:xr-task "bgp";
    csc:cli-command "clear bgp bestpath <afi-safi-name> rd <rd> <ip-addr> <ip-netmask>";
  }
  rpc clear-bgp-bestpath-afi-safi-rd-ip-addr {
    description
      "re-run BGP bestpath selection.
       Display routes with a specific route distinguisher.
      ";
    input {
      leaf afi-safi-name {
        type afi-safi-type;
        mandatory true;
        description
          "AFI and SAFI";
      }
      leaf rd {
        type rd;
        mandatory true;
        description
          "Route distinguisher";
      }
      leaf ip-addr {
        type inet:ip-address;
        mandatory true;
        description
          "Network";
      }
    }
    csc:xr-task "bgp";
    csc:cli-command "clear bgp bestpath <afi-safi-name> rd <rd> <ip-addr>";
  }
  rpc clear-bgp-bestpath-afi-safi-rd-ip-prefix {
    description
      "re-run BGP bestpath selection.
       Display routes with a specific route distinguisher.
      ";
    input {
      leaf afi-safi-name {
        type afi-safi-type;
        mandatory true;
        description
          "AFI and SAFI";
      }
      leaf rd {
        type rd;
        mandatory true;
        description
          "Route distinguisher";
      }
      leaf ip-prefix {
        type inet:ip-prefix;
        mandatory true;
        description
          "Network and masklength";
      }
    }
    csc:xr-task "bgp";
    csc:cli-command "clear bgp bestpath <afi-safi-name> rd <rd> <ip-prefix>";
  }
  rpc clear-bgp-bestpath-afi-safi-ipv4-addr-ipv4-mask {
    description
      "re-run BGP bestpath selection.\n";
    input {
      leaf afi-safi-name {
        type afi-safi-type;
        mandatory true;
        description
          "AFI and SAFI";
      }
      leaf ipv4-addr {
        type inet:ipv4-address;
        mandatory true;
        description
          "IPv4 network";
      }
      leaf ipv4-mask {
        type ipv4-netmask;
        mandatory true;
        description
          "IPv4 mask";
      }
    }
    csc:xr-task "bgp";
    csc:cli-command "clear bgp bestpath <afi-safi-name> <ipv4-addr> <ipv4-mask>";
  }
  rpc clear-bgp-bestpath-afi-safi-ipv4-addr {
    description
      "re-run BGP bestpath selection.\n";
    input {
      leaf afi-safi-name {
        type afi-safi-type;
        mandatory true;
        description
          "AFI and SAFI";
      }
      leaf ipv4-addr {
        type inet:ipv4-address;
        mandatory true;
        description
          "IPv4 network";
      }
    }
    csc:xr-task "bgp";
    csc:cli-command "clear bgp bestpath <afi-safi-name> <ipv4-addr>";
  }
  rpc clear-bgp-bestpath-afi-safi-ipv4-prefix {
    description
      "re-run BGP bestpath selection.\n";
    input {
      leaf afi-safi-name {
        type afi-safi-type;
        mandatory true;
        description
          "AFI and SAFI";
      }
      leaf ipv4-prefix {
        type inet:ipv4-prefix;
        mandatory true;
        description
          "IPv4 network and masklength";
      }
    }
    csc:xr-task "bgp";
    csc:cli-command "clear bgp bestpath <afi-safi-name> <ipv4-prefix>";
  }
  rpc clear-bgp-bestpath-afi-safi-rd-ipv4-addr {
    description
      "re-run BGP bestpath selection.
       Display routes with a specific route distinguisher.
      ";
    input {
      leaf afi-safi-name {
        type afi-safi-type;
        mandatory true;
        description
          "AFI and SAFI";
      }
      leaf rd {
        type rd;
        mandatory true;
        description
          "Route distinguisher";
      }
      leaf ipv4-addr {
        type inet:ipv4-address;
        mandatory true;
        description
          "IPv4 MDT network";
      }
    }
    csc:xr-task "bgp";
    csc:cli-command "clear bgp bestpath <afi-safi-name> rd <rd> <ipv4-addr>";
  }
  rpc clear-bgp-bestpath-afi-safi-vrf-ipv4-addr {
    description
      "re-run BGP bestpath selection.
       Display routes for a specified VRF.
      ";
    input {
      leaf afi-safi-name {
        type afi-safi-type;
        mandatory true;
        description
          "AFI and SAFI";
      }
      leaf vrf-name {
        type string;
        mandatory true;
        description
          "VRF name";
      }
      leaf ipv4-addr {
        type inet:ipv4-address;
        mandatory true;
        description
          "IPv4 MDT network";
      }
    }
    csc:xr-task "bgp";
    csc:cli-command "clear bgp bestpath <afi-safi-name> vrf <vrf-name> <ipv4-addr>";
  }
  rpc clear-bgp-bestpath-afi-safi-network {
    description
      "re-run BGP bestpath selection.\n";
    input {
      leaf afi-safi-name {
        type afi-safi-type;
        mandatory true;
        description
          "AFI and SAFI";
      }
      leaf network {
        type string;
        mandatory true;
        description
          "Address family modifier specific network";
      }
    }
    csc:xr-task "bgp";
    csc:cli-command "clear bgp bestpath <afi-safi-name> <network>";
  }
  rpc clear-bgp-bestpath-afi-safi-rd-network {
    description
      "re-run BGP bestpath selection.
       Display routes with a specific route distinguisher.
      ";
    input {
      leaf afi-safi-name {
        type afi-safi-type;
        mandatory true;
        description
          "AFI and SAFI";
      }
      leaf rd {
        type rd;
        mandatory true;
        description
          "Route distinguisher";
      }
      leaf network {
        type string;
        mandatory true;
        description
          "Address family modifier specific network";
      }
    }
    csc:xr-task "bgp";
    csc:cli-command "clear bgp bestpath <afi-safi-name> rd <rd> <network>";
  }
  rpc clear-bgp-bestpath-afi-safi-vrf-network {
    description
      "re-run BGP bestpath selection.
       Display routes for a specified VRF.
      ";
    input {
      leaf afi-safi-name {
        type afi-safi-type;
        mandatory true;
        description
          "AFI and SAFI";
      }
      leaf vrf-name {
        type string;
        mandatory true;
        description
          "VRF name";
      }
      leaf network {
        type string;
        mandatory true;
        description
          "Address family modifier specific network";
      }
    }
    csc:xr-task "bgp";
    csc:cli-command "clear bgp bestpath <afi-safi-name> vrf <vrf-name> <network>";
  }
  rpc clear-bgp-bestpath-afi-safi-rt-constraint-network {
    description
      "re-run BGP bestpath selection.\n";
    input {
      leaf afi-safi-name {
        type afi-safi-type;
        mandatory true;
        description
          "AFI and SAFI";
      }
      leaf rt-constraint-network {
        type string;
        mandatory true;
        description
          "RT-Constraint network";
      }
    }
    csc:xr-task "bgp";
    csc:cli-command "clear bgp bestpath <afi-safi-name> <rt-constraint-network>";
  }
  rpc clear-bgp-bestpath-afi-safi-ipv4-tunnel-network {
    description
      "re-run BGP bestpath selection.\n";
    input {
      leaf afi-safi-name {
        type afi-safi-type;
        mandatory true;
        description
          "AFI and SAFI";
      }
      leaf ipv4-tunnel-network {
        type string;
        mandatory true;
        description
          "IPv4 Tunnel network <Tunnel-ID>:<IPv4 Address>";
      }
    }
    csc:xr-task "bgp";
    csc:cli-command "clear bgp bestpath <afi-safi-name> <ipv4-tunnel-network>";
  }
  rpc clear-bgp-bestpath-afi-safi-ipv6-addr-ipv6-netmask {
    description
      "re-run BGP bestpath selection.\n";
    input {
      leaf afi-safi-name {
        type afi-safi-type;
        mandatory true;
        description
          "AFI and SAFI";
      }
      leaf ipv6-addr {
        type inet:ipv6-address;
        mandatory true;
        description
          "IPv6 network";
      }
      leaf ipv6-netmask {
        type ipv6-netmask;
        mandatory true;
        description
          "IPv6 mask";
      }
    }
    csc:xr-task "bgp";
    csc:cli-command "clear bgp bestpath <afi-safi-name> <ipv6-addr> <ipv6-netmask>";
  }
  rpc clear-bgp-bestpath-afi-safi-ipv6-addr {
    description
      "re-run BGP bestpath selection.\n";
    input {
      leaf afi-safi-name {
        type afi-safi-type;
        mandatory true;
        description
          "AFI and SAFI";
      }
      leaf ipv6-addr {
        type inet:ipv6-address;
        mandatory true;
        description
          "IPv6 network";
      }
    }
    csc:xr-task "bgp";
    csc:cli-command "clear bgp bestpath <afi-safi-name> <ipv6-addr>";
  }
  rpc clear-bgp-bestpath-afi-safi-ipv6-prefix {
    description
      "re-run BGP bestpath selection.\n";
    input {
      leaf afi-safi-name {
        type afi-safi-type;
        mandatory true;
        description
          "AFI and SAFI";
      }
      leaf ipv6-prefix {
        type inet:ipv6-prefix;
        mandatory true;
        description
          "IPv6 network and masklength";
      }
    }
    csc:xr-task "bgp";
    csc:cli-command "clear bgp bestpath <afi-safi-name> <ipv6-prefix>";
  }
  rpc clear-bgp-bestpath-afi-safi-rd {
    description
      "re-run BGP bestpath selection.
       Display routes with a specific route distinguisher.
      ";
    input {
      leaf afi-safi-name {
        type afi-safi-type;
        mandatory true;
        description
          "AFI and SAFI";
      }
      leaf rd {
        type rd;
        mandatory true;
        description
          "Route distinguisher";
      }
    }
    csc:xr-task "bgp";
    csc:cli-command "clear bgp bestpath <afi-safi-name> rd <rd>";
  }
  rpc clear-bgp-bestpath-afi-safi-vrf {
    description
      "re-run BGP bestpath selection.
       Display routes for a specified VRF.
      ";
    input {
      leaf afi-safi-name {
        type afi-safi-type;
        mandatory true;
        description
          "AFI and SAFI";
      }
      leaf vrf-name {
        type string;
        mandatory true;
        description
          "VRF name";
      }
    }
    csc:xr-task "bgp";
    csc:cli-command "clear bgp bestpath <afi-safi-name> vrf <vrf-name>";
  }
  rpc clear-bgp-bestpath-afi-safi {
    description
      "re-run BGP bestpath selection.\n";
    input {
      leaf afi-safi-name {
        type afi-safi-type;
        mandatory true;
        description
          "AFI and SAFI";
      }
    }
    csc:xr-task "bgp";
    csc:cli-command "clear bgp bestpath <afi-safi-name>";
  }
  rpc clear-bgp-bestpath-afi-safi-sr-policy-prefix {
    description
      "re-run BGP bestpath selection.\n";
    input {
      leaf afi-safi-name {
        type afi-safi-type;
        mandatory true;
        description
          "AFI and SAFI";
      }
      leaf sr-policy-prefix {
        type string;
        mandatory true;
        description
          "SR Policy prefix";
      }
    }
    csc:xr-task "bgp";
    csc:cli-command "clear bgp bestpath <afi-safi-name> <sr-policy-prefix>";
  }
  rpc clear-bgp-bestpath-afi-safi-bridge-domain-ipv4-prefix {
    description
      "re-run BGP bestpath selection.
       Display routes for a specified Bridge Domain.
      ";
    input {
      leaf afi-safi-name {
        type afi-safi-type;
        mandatory true;
        description
          "AFI and SAFI";
      }
      leaf bridge-domain-name {
        type string;
        mandatory true;
        description
          "Bridge Domain";
      }
      leaf ipv4-prefix {
        type inet:ipv4-prefix;
        mandatory true;
        description
          "L2VPN EVPN Prefix";
      }
    }
    csc:xr-task "bgp";
    csc:cli-command "clear bgp bestpath <afi-safi-name> bridge-domain <bridge-domain-name> <ipv4-prefix>";
  }
  rpc clear-bgp-bestpath-afi-safi-rd-ipv4-prefix {
    description
      "re-run BGP bestpath selection.
       Display routes with a specific route distinguisher.
      ";
    input {
      leaf afi-safi-name {
        type afi-safi-type;
        mandatory true;
        description
          "AFI and SAFI";
      }
      leaf rd {
        type rd;
        mandatory true;
        description
          "Route distinguisher";
      }
      leaf ipv4-prefix {
        type inet:ipv4-prefix;
        mandatory true;
        description
          "L2VPN EVPN Prefix";
      }
    }
    csc:xr-task "bgp";
    csc:cli-command "clear bgp bestpath <afi-safi-name> rd <rd> <ipv4-prefix>";
  }
  rpc clear-bgp-bestpath-afi-safi-mp2mp-ipv4-prefix {
    description
      "re-run BGP bestpath selection.
       Display routes for a specified Xconnect group:MP2MP.
      ";
    input {
      leaf afi-safi-name {
        type afi-safi-type;
        mandatory true;
        description
          "AFI and SAFI";
      }
      leaf mp2mp {
        type string;
        mandatory true;
        description
          "Xconnect Group:mp2mp";
      }
      leaf ipv4-prefix {
        type inet:ipv4-prefix;
        mandatory true;
        description
          "L2VPN VPWS Prefix";
      }
    }
    csc:xr-task "bgp";
    csc:cli-command "clear bgp bestpath <afi-safi-name> mp2mp <mp2mp> <ipv4-prefix>";
  }
  rpc clear-bgp-bestpath-afi-safi-vrf-ipv4-prefix {
    description
      "re-run BGP bestpath selection.
       Display routes for a specified VRF.
      ";
    input {
      leaf afi-safi-name {
        type afi-safi-type;
        mandatory true;
        description
          "AFI and SAFI";
      }
      leaf vrf-name {
        type string;
        mandatory true;
        description
          "VRF name";
      }
      leaf ipv4-prefix {
        type inet:ipv4-prefix;
        mandatory true;
        description
          "VPN Fspec Prefix";
      }
    }
    csc:xr-task "bgp";
    csc:cli-command "clear bgp bestpath <afi-safi-name> vrf <vrf-name> <ipv4-prefix>";
  }
  rpc clear-bgp-bestpath-afi-safi-rd-ipv4-addr-ipv4-mask {
    description
      "re-run BGP bestpath selection.
       Display routes with a specific route distinguisher.
      ";
    input {
      leaf afi-safi-name {
        type afi-safi-type;
        mandatory true;
        description
          "AFI and SAFI";
      }
      leaf rd {
        type rd;
        mandatory true;
        description
          "Route distinguisher";
      }
      leaf ipv4-addr {
        type inet:ipv4-address;
        mandatory true;
        description
          "IPv4 network";
      }
      leaf ipv4-mask {
        type ipv4-netmask;
        mandatory true;
        description
          "IPv4 mask";
      }
    }
    csc:xr-task "bgp";
    csc:cli-command "clear bgp bestpath <afi-safi-name> rd <rd> <ipv4-addr> <ipv4-mask>";
  }
  rpc clear-bgp-bestpath-afi-safi-vrf-ipv4-addr-ipv4-mask {
    description
      "re-run BGP bestpath selection.
       Display routes for a specified VRF.
      ";
    input {
      leaf afi-safi-name {
        type afi-safi-type;
        mandatory true;
        description
          "AFI and SAFI";
      }
      leaf vrf-name {
        type string;
        mandatory true;
        description
          "VRF name";
      }
      leaf ipv4-addr {
        type inet:ipv4-address;
        mandatory true;
        description
          "IPv4 network";
      }
      leaf ipv4-mask {
        type ipv4-netmask;
        mandatory true;
        description
          "IPv4 mask";
      }
    }
    csc:xr-task "bgp";
    csc:cli-command "clear bgp bestpath <afi-safi-name> vrf <vrf-name> <ipv4-addr> <ipv4-mask>";
  }
  rpc clear-bgp-bestpath-afi-safi-rd-ipv6-addr-ipv6-netmask {
    description
      "re-run BGP bestpath selection.
       Display routes with a specific route distinguisher.
      ";
    input {
      leaf afi-safi-name {
        type afi-safi-type;
        mandatory true;
        description
          "AFI and SAFI";
      }
      leaf rd {
        type rd;
        mandatory true;
        description
          "Route distinguisher";
      }
      leaf ipv6-addr {
        type inet:ipv6-address;
        mandatory true;
        description
          "IPv6 network";
      }
      leaf ipv6-netmask {
        type ipv6-netmask;
        mandatory true;
        description
          "IPv6 mask";
      }
    }
    csc:xr-task "bgp";
    csc:cli-command "clear bgp bestpath <afi-safi-name> rd <rd> <ipv6-addr> <ipv6-netmask>";
  }
  rpc clear-bgp-bestpath-afi-safi-rd-ipv6-addr {
    description
      "re-run BGP bestpath selection.
       Display routes with a specific route distinguisher.
      ";
    input {
      leaf afi-safi-name {
        type afi-safi-type;
        mandatory true;
        description
          "AFI and SAFI";
      }
      leaf rd {
        type rd;
        mandatory true;
        description
          "Route distinguisher";
      }
      leaf ipv6-addr {
        type inet:ipv6-address;
        mandatory true;
        description
          "IPv6 network";
      }
    }
    csc:xr-task "bgp";
    csc:cli-command "clear bgp bestpath <afi-safi-name> rd <rd> <ipv6-addr>";
  }
  rpc clear-bgp-bestpath-afi-safi-rd-ipv6-prefix {
    description
      "re-run BGP bestpath selection.
       Display routes with a specific route distinguisher.
      ";
    input {
      leaf afi-safi-name {
        type afi-safi-type;
        mandatory true;
        description
          "AFI and SAFI";
      }
      leaf rd {
        type rd;
        mandatory true;
        description
          "Route distinguisher";
      }
      leaf ipv6-prefix {
        type inet:ipv6-prefix;
        mandatory true;
        description
          "IPv6 network and masklength";
      }
    }
    csc:xr-task "bgp";
    csc:cli-command "clear bgp bestpath <afi-safi-name> rd <rd> <ipv6-prefix>";
  }
  rpc clear-bgp-bestpath-afi-safi-vrf-ipv6-addr-ipv6-netmask {
    description
      "re-run BGP bestpath selection.
       Display routes for a specified VRF.
      ";
    input {
      leaf afi-safi-name {
        type afi-safi-type;
        mandatory true;
        description
          "AFI and SAFI";
      }
      leaf vrf-name {
        type string;
        mandatory true;
        description
          "VRF name";
      }
      leaf ipv6-addr {
        type inet:ipv6-address;
        mandatory true;
        description
          "IPv6 network";
      }
      leaf ipv6-netmask {
        type ipv6-netmask;
        mandatory true;
        description
          "IPv6 mask";
      }
    }
    csc:xr-task "bgp";
    csc:cli-command "clear bgp bestpath <afi-safi-name> vrf <vrf-name> <ipv6-addr> <ipv6-netmask>";
  }
  rpc clear-bgp-bestpath-afi-safi-vrf-ipv6-addr {
    description
      "re-run BGP bestpath selection.
       Display routes for a specified VRF.
      ";
    input {
      leaf afi-safi-name {
        type afi-safi-type;
        mandatory true;
        description
          "AFI and SAFI";
      }
      leaf vrf-name {
        type string;
        mandatory true;
        description
          "VRF name";
      }
      leaf ipv6-addr {
        type inet:ipv6-address;
        mandatory true;
        description
          "IPv6 network";
      }
    }
    csc:xr-task "bgp";
    csc:cli-command "clear bgp bestpath <afi-safi-name> vrf <vrf-name> <ipv6-addr>";
  }
  rpc clear-bgp-bestpath-afi-safi-vrf-ipv6-prefix {
    description
      "re-run BGP bestpath selection.
       Display routes for a specified VRF.
      ";
    input {
      leaf afi-safi-name {
        type afi-safi-type;
        mandatory true;
        description
          "AFI and SAFI";
      }
      leaf vrf-name {
        type string;
        mandatory true;
        description
          "VRF name";
      }
      leaf ipv6-prefix {
        type inet:ipv6-prefix;
        mandatory true;
        description
          "IPv6 network and masklength";
      }
    }
    csc:xr-task "bgp";
    csc:cli-command "clear bgp bestpath <afi-safi-name> vrf <vrf-name> <ipv6-prefix>";
  }
  rpc clear-bgp-bestpath-vrf-ip-addr-ip-netmask {
    description
      "re-run BGP bestpath selection.
       Specify a VRF.
      ";
    input {
      leaf vrf-all {
        type vrf-name;
        mandatory true;
        description
          "VRF name or all";
      }
      leaf ip-addr {
        type inet:ip-address;
        mandatory true;
        description
          "Network";
      }
      leaf ip-netmask {
        type ip-netmask;
        mandatory true;
        description
          "Mask";
      }
    }
    csc:xr-task "bgp";
    csc:cli-command "clear bgp bestpath vrf <vrf-all> <ip-addr> <ip-netmask>";
  }
  rpc clear-bgp-bestpath-vrf-ip-addr {
    description
      "re-run BGP bestpath selection.
       Specify a VRF.
      ";
    input {
      leaf vrf-all {
        type vrf-name;
        mandatory true;
        description
          "VRF name or all";
      }
      leaf ip-addr {
        type inet:ip-address;
        mandatory true;
        description
          "Network";
      }
    }
    csc:xr-task "bgp";
    csc:cli-command "clear bgp bestpath vrf <vrf-all> <ip-addr>";
  }
  rpc clear-bgp-bestpath-vrf-ip-prefix {
    description
      "re-run BGP bestpath selection.
       Specify a VRF.
      ";
    input {
      leaf vrf-all {
        type vrf-name;
        mandatory true;
        description
          "VRF name or all";
      }
      leaf ip-prefix {
        type inet:ip-prefix;
        mandatory true;
        description
          "Network and masklength";
      }
    }
    csc:xr-task "bgp";
    csc:cli-command "clear bgp bestpath vrf <vrf-all> <ip-prefix>";
  }
  rpc clear-bgp-bestpath-vrf-afi-safi-ipv4-prefix {
    description
      "re-run BGP bestpath selection.
       Specify a VRF.
      ";
    input {
      leaf vrf-all {
        type vrf-name;
        mandatory true;
        description
          "VRF name or all";
      }
      leaf afi-safi-name {
        type afi-safi-type;
        mandatory true;
        description
          "AFI and SAFI";
      }
      leaf ipv4-prefix {
        type inet:ipv4-prefix;
        mandatory true;
        description
          "Fspec IPv4 Prefix";
      }
    }
    csc:xr-task "bgp";
    csc:cli-command "clear bgp bestpath vrf <vrf-all> <afi-safi-name> <ipv4-prefix>";
  }
  rpc clear-bgp-bestpath-vrf-afi-safi-ipv4-addr-ipv4-mask {
    description
      "re-run BGP bestpath selection.
       Specify a VRF.
      ";
    input {
      leaf vrf-all {
        type vrf-name;
        mandatory true;
        description
          "VRF name or all";
      }
      leaf afi-safi-name {
        type afi-safi-type;
        mandatory true;
        description
          "AFI and SAFI";
      }
      leaf ipv4-addr {
        type inet:ipv4-address;
        mandatory true;
        description
          "IPv4 network";
      }
      leaf ipv4-mask {
        type ipv4-netmask;
        mandatory true;
        description
          "IPv4 mask";
      }
    }
    csc:xr-task "bgp";
    csc:cli-command "clear bgp bestpath vrf <vrf-all> <afi-safi-name> <ipv4-addr> <ipv4-mask>";
  }
  rpc clear-bgp-bestpath-vrf-afi-safi-ipv4-addr {
    description
      "re-run BGP bestpath selection.
       Specify a VRF.
      ";
    input {
      leaf vrf-all {
        type vrf-name;
        mandatory true;
        description
          "VRF name or all";
      }
      leaf afi-safi-name {
        type afi-safi-type;
        mandatory true;
        description
          "AFI and SAFI";
      }
      leaf ipv4-addr {
        type inet:ipv4-address;
        mandatory true;
        description
          "IPv4 network";
      }
    }
    csc:xr-task "bgp";
    csc:cli-command "clear bgp bestpath vrf <vrf-all> <afi-safi-name> <ipv4-addr>";
  }
  rpc clear-bgp-bestpath-vrf-afi-safi-network {
    description
      "re-run BGP bestpath selection.
       Specify a VRF.
      ";
    input {
      leaf vrf-all {
        type vrf-name;
        mandatory true;
        description
          "VRF name or all";
      }
      leaf afi-safi-name {
        type afi-safi-type;
        mandatory true;
        description
          "AFI and SAFI";
      }
      leaf network {
        type string;
        mandatory true;
        description
          "Address family modifier specific network";
      }
    }
    csc:xr-task "bgp";
    csc:cli-command "clear bgp bestpath vrf <vrf-all> <afi-safi-name> <network>";
  }
  rpc clear-bgp-bestpath-vrf-afi-safi-rd-network {
    description
      "re-run BGP bestpath selection.
       Specify a VRF.
       Display routes with a specific route distinguisher.
      ";
    input {
      leaf vrf-all {
        type vrf-name;
        mandatory true;
        description
          "VRF name or all";
      }
      leaf afi-safi-name {
        type afi-safi-type;
        mandatory true;
        description
          "AFI and SAFI";
      }
      leaf rd {
        type rd;
        mandatory true;
        description
          "Route distinguisher";
      }
      leaf network {
        type string;
        mandatory true;
        description
          "Address family modifier specific network";
      }
    }
    csc:xr-task "bgp";
    csc:cli-command "clear bgp bestpath vrf <vrf-all> <afi-safi-name> rd <rd> <network>";
  }
  rpc clear-bgp-bestpath-vrf-afi-safi-vrf-network {
    description
      "re-run BGP bestpath selection.
       Specify a VRF.
       Display routes for a specified VRF.
      ";
    input {
      leaf vrf-all {
        type vrf-name;
        mandatory true;
        description
          "VRF name or all";
      }
      leaf afi-safi-name {
        type afi-safi-type;
        mandatory true;
        description
          "AFI and SAFI";
      }
      leaf vrf-name {
        type string;
        mandatory true;
        description
          "VRF name";
      }
      leaf network {
        type string;
        mandatory true;
        description
          "Address family modifier specific network";
      }
    }
    csc:xr-task "bgp";
    csc:cli-command "clear bgp bestpath vrf <vrf-all> <afi-safi-name> vrf <vrf-name> <network>";
  }
  rpc clear-bgp-bestpath-vrf-afi-safi-ipv6-addr-ipv6-netmask {
    description
      "re-run BGP bestpath selection.
       Specify a VRF.
      ";
    input {
      leaf vrf-all {
        type vrf-name;
        mandatory true;
        description
          "VRF name or all";
      }
      leaf afi-safi-name {
        type afi-safi-type;
        mandatory true;
        description
          "AFI and SAFI";
      }
      leaf ipv6-addr {
        type inet:ipv6-address;
        mandatory true;
        description
          "IPv6 network";
      }
      leaf ipv6-netmask {
        type ipv6-netmask;
        mandatory true;
        description
          "IPv6 mask";
      }
    }
    csc:xr-task "bgp";
    csc:cli-command "clear bgp bestpath vrf <vrf-all> <afi-safi-name> <ipv6-addr> <ipv6-netmask>";
  }
  rpc clear-bgp-bestpath-vrf-afi-safi-ipv6-addr {
    description
      "re-run BGP bestpath selection.
       Specify a VRF.
      ";
    input {
      leaf vrf-all {
        type vrf-name;
        mandatory true;
        description
          "VRF name or all";
      }
      leaf afi-safi-name {
        type afi-safi-type;
        mandatory true;
        description
          "AFI and SAFI";
      }
      leaf ipv6-addr {
        type inet:ipv6-address;
        mandatory true;
        description
          "IPv6 network";
      }
    }
    csc:xr-task "bgp";
    csc:cli-command "clear bgp bestpath vrf <vrf-all> <afi-safi-name> <ipv6-addr>";
  }
  rpc clear-bgp-bestpath-vrf-afi-safi-ipv6-prefix {
    description
      "re-run BGP bestpath selection.
       Specify a VRF.
      ";
    input {
      leaf vrf-all {
        type vrf-name;
        mandatory true;
        description
          "VRF name or all";
      }
      leaf afi-safi-name {
        type afi-safi-type;
        mandatory true;
        description
          "AFI and SAFI";
      }
      leaf ipv6-prefix {
        type inet:ipv6-prefix;
        mandatory true;
        description
          "IPv6 network and masklength";
      }
    }
    csc:xr-task "bgp";
    csc:cli-command "clear bgp bestpath vrf <vrf-all> <afi-safi-name> <ipv6-prefix>";
  }
  rpc clear-bgp-bestpath-vrf-afi-safi-rd {
    description
      "re-run BGP bestpath selection.
       Specify a VRF.
       Display routes with a specific route distinguisher.
      ";
    input {
      leaf vrf-all {
        type vrf-name;
        mandatory true;
        description
          "VRF name or all";
      }
      leaf afi-safi-name {
        type afi-safi-type;
        mandatory true;
        description
          "AFI and SAFI";
      }
      leaf rd {
        type rd;
        mandatory true;
        description
          "Route distinguisher";
      }
    }
    csc:xr-task "bgp";
    csc:cli-command "clear bgp bestpath vrf <vrf-all> <afi-safi-name> rd <rd>";
  }
  rpc clear-bgp-bestpath-vrf-afi-safi-vrf {
    description
      "re-run BGP bestpath selection.
       Specify a VRF.
       Display routes for a specified VRF.
      ";
    input {
      leaf vrf-all {
        type vrf-name;
        mandatory true;
        description
          "VRF name or all";
      }
      leaf afi-safi-name {
        type afi-safi-type;
        mandatory true;
        description
          "AFI and SAFI";
      }
      leaf vrf-name {
        type string;
        mandatory true;
        description
          "VRF name";
      }
    }
    csc:xr-task "bgp";
    csc:cli-command "clear bgp bestpath vrf <vrf-all> <afi-safi-name> vrf <vrf-name>";
  }
  rpc clear-bgp-bestpath-vrf-afi-safi {
    description
      "re-run BGP bestpath selection.
       Specify a VRF.
      ";
    input {
      leaf vrf-all {
        type vrf-name;
        mandatory true;
        description
          "VRF name or all";
      }
      leaf afi-safi-name {
        type afi-safi-type;
        mandatory true;
        description
          "AFI and SAFI";
      }
    }
    csc:xr-task "bgp";
    csc:cli-command "clear bgp bestpath vrf <vrf-all> <afi-safi-name>";
  }
  rpc clear-bgp-external-graceful {
    description
      "Clear all external peers.
       Clear with a hard reset and a graceful restart.
      ";
    csc:xr-task "bgp";
    csc:cli-command "clear bgp external graceful";
  }
  rpc clear-bgp-external {
    description
      "Clear all external peers.\n";
    csc:xr-task "bgp";
    csc:cli-command "clear bgp external";
  }
  rpc clear-bgp-instance-all-graceful {
    description
      "Choose a particular BGP instance.
       Clear all peers and all routes from the BGP table.
       Clear with a hard reset and a graceful restart.
      ";
    input {
      leaf instance-name {
        type instance-name;
        mandatory true;
        description
          "instance name or all";
      }
    }
    csc:xr-task "bgp";
    csc:cli-command "clear bgp instance <instance-name> * graceful";
  }
  rpc clear-bgp-instance-all {
    description
      "Choose a particular BGP instance.
       Clear all peers and all routes from the BGP table.
      ";
    input {
      leaf instance-name {
        type instance-name;
        mandatory true;
        description
          "instance name or all";
      }
    }
    csc:xr-task "bgp";
    csc:cli-command "clear bgp instance <instance-name> *";
  }
  rpc clear-bgp-instance-ip-addr-graceful {
    description
      "Choose a particular BGP instance.
       Clear with a hard reset and a graceful restart.
      ";
    input {
      leaf instance-name {
        type instance-name;
        mandatory true;
        description
          "instance name or all";
      }
      leaf ip-addr {
        type inet:ip-address;
        mandatory true;
        description
          "BGP neighbor address to clear";
      }
    }
    csc:xr-task "bgp";
    csc:cli-command "clear bgp instance <instance-name> <ip-addr> graceful";
  }
  rpc clear-bgp-instance-ip-addr-long-lived-stale {
    description
      "Choose a particular BGP instance.
       Clear long-lived-stale routes.
      ";
    input {
      leaf instance-name {
        type instance-name;
        mandatory true;
        description
          "instance name or all";
      }
      leaf ip-addr {
        type inet:ip-address;
        mandatory true;
        description
          "BGP neighbor address to clear";
      }
    }
    csc:xr-task "bgp";
    csc:cli-command "clear bgp instance <instance-name> <ip-addr> long-lived-stale";
  }
  rpc clear-bgp-instance-ip-addr {
    description
      "Choose a particular BGP instance.\n";
    input {
      leaf instance-name {
        type instance-name;
        mandatory true;
        description
          "instance name or all";
      }
      leaf ip-addr {
        type inet:ip-address;
        mandatory true;
        description
          "BGP neighbor address to clear";
      }
    }
    csc:xr-task "bgp";
    csc:cli-command "clear bgp instance <instance-name> <ip-addr>";
  }
  rpc clear-bgp-instance-afi-safi-all-soft-in-prefix-filter {
    description
      "Choose a particular BGP instance.
       Clear all peers and all routes from the BGP table.
       Soft reconfig.
       Soft reconfig inbound update.
       Push out prefix ORF and do inbound soft reconfig.
      ";
    input {
      leaf instance-name {
        type instance-name;
        mandatory true;
        description
          "instance name or all";
      }
      leaf afi-safi-name {
        type afi-safi-type;
        mandatory true;
        description
          "AFI and SAFI";
      }
    }
    csc:xr-task "bgp";
    csc:cli-command "clear bgp instance <instance-name> <afi-safi-name> * soft in prefix-filter";
  }
  rpc clear-bgp-instance-afi-safi-all-soft-in {
    description
      "Choose a particular BGP instance.
       Clear all peers and all routes from the BGP table.
       Soft reconfig.
       Soft reconfig inbound update.
      ";
    input {
      leaf instance-name {
        type instance-name;
        mandatory true;
        description
          "instance name or all";
      }
      leaf afi-safi-name {
        type afi-safi-type;
        mandatory true;
        description
          "AFI and SAFI";
      }
    }
    csc:xr-task "bgp";
    csc:cli-command "clear bgp instance <instance-name> <afi-safi-name> * soft in";
  }
  rpc clear-bgp-instance-afi-safi-all-soft-out {
    description
      "Choose a particular BGP instance.
       Clear all peers and all routes from the BGP table.
       Soft reconfig.
       Soft reconfig outbound update.
      ";
    input {
      leaf instance-name {
        type instance-name;
        mandatory true;
        description
          "instance name or all";
      }
      leaf afi-safi-name {
        type afi-safi-type;
        mandatory true;
        description
          "AFI and SAFI";
      }
    }
    csc:xr-task "bgp";
    csc:cli-command "clear bgp instance <instance-name> <afi-safi-name> * soft out";
  }
  rpc clear-bgp-instance-afi-safi-all-soft {
    description
      "Choose a particular BGP instance.
       Clear all peers and all routes from the BGP table.
       Soft reconfig.
      ";
    input {
      leaf instance-name {
        type instance-name;
        mandatory true;
        description
          "instance name or all";
      }
      leaf afi-safi-name {
        type afi-safi-type;
        mandatory true;
        description
          "AFI and SAFI";
      }
    }
    csc:xr-task "bgp";
    csc:cli-command "clear bgp instance <instance-name> <afi-safi-name> * soft";
  }
  rpc clear-bgp-instance-afi-safi-ip-addr-long-lived-stale {
    description
      "Choose a particular BGP instance.
       Clear long-lived-stale routes.
      ";
    input {
      leaf instance-name {
        type instance-name;
        mandatory true;
        description
          "instance name or all";
      }
      leaf afi-safi-name {
        type afi-safi-type;
        mandatory true;
        description
          "AFI and SAFI";
      }
      leaf ip-addr {
        type inet:ip-address;
        mandatory true;
        description
          "BGP neighbor address to clear";
      }
    }
    csc:xr-task "bgp";
    csc:cli-command "clear bgp instance <instance-name> <afi-safi-name> <ip-addr> long-lived-stale";
  }
  rpc clear-bgp-instance-afi-safi-ip-addr-soft-in-prefix-filter {
    description
      "Choose a particular BGP instance.
       Soft reconfig.
       Soft reconfig inbound update.
       Push out prefix ORF and do inbound soft reconfig.
      ";
    input {
      leaf instance-name {
        type instance-name;
        mandatory true;
        description
          "instance name or all";
      }
      leaf afi-safi-name {
        type afi-safi-type;
        mandatory true;
        description
          "AFI and SAFI";
      }
      leaf ip-addr {
        type inet:ip-address;
        mandatory true;
        description
          "BGP neighbor address to clear";
      }
    }
    csc:xr-task "bgp";
    csc:cli-command "clear bgp instance <instance-name> <afi-safi-name> <ip-addr> soft in prefix-filter";
  }
  rpc clear-bgp-instance-afi-safi-ip-addr-soft-in {
    description
      "Choose a particular BGP instance.
       Soft reconfig.
       Soft reconfig inbound update.
      ";
    input {
      leaf instance-name {
        type instance-name;
        mandatory true;
        description
          "instance name or all";
      }
      leaf afi-safi-name {
        type afi-safi-type;
        mandatory true;
        description
          "AFI and SAFI";
      }
      leaf ip-addr {
        type inet:ip-address;
        mandatory true;
        description
          "BGP neighbor address to clear";
      }
    }
    csc:xr-task "bgp";
    csc:cli-command "clear bgp instance <instance-name> <afi-safi-name> <ip-addr> soft in";
  }
  rpc clear-bgp-instance-afi-safi-ip-addr-soft-out {
    description
      "Choose a particular BGP instance.
       Soft reconfig.
       Soft reconfig outbound update.
      ";
    input {
      leaf instance-name {
        type instance-name;
        mandatory true;
        description
          "instance name or all";
      }
      leaf afi-safi-name {
        type afi-safi-type;
        mandatory true;
        description
          "AFI and SAFI";
      }
      leaf ip-addr {
        type inet:ip-address;
        mandatory true;
        description
          "BGP neighbor address to clear";
      }
    }
    csc:xr-task "bgp";
    csc:cli-command "clear bgp instance <instance-name> <afi-safi-name> <ip-addr> soft out";
  }
  rpc clear-bgp-instance-afi-safi-ip-addr-soft {
    description
      "Choose a particular BGP instance.
       Soft reconfig.
      ";
    input {
      leaf instance-name {
        type instance-name;
        mandatory true;
        description
          "instance name or all";
      }
      leaf afi-safi-name {
        type afi-safi-type;
        mandatory true;
        description
          "AFI and SAFI";
      }
      leaf ip-addr {
        type inet:ip-address;
        mandatory true;
        description
          "BGP neighbor address to clear";
      }
    }
    csc:xr-task "bgp";
    csc:cli-command "clear bgp instance <instance-name> <afi-safi-name> <ip-addr> soft";
  }
  rpc clear-bgp-instance-afi-safi-as-soft-in-prefix-filter {
    description
      "Choose a particular BGP instance.
       Clear peers in a specific AS.
       Soft reconfig.
       Soft reconfig inbound update.
       Push out prefix ORF and do inbound soft reconfig.
      ";
    input {
      leaf instance-name {
        type instance-name;
        mandatory true;
        description
          "instance name or all";
      }
      leaf afi-safi-name {
        type afi-safi-type;
        mandatory true;
        description
          "AFI and SAFI";
      }
      leaf as-number {
        type as-number;
        mandatory true;
        description
          "AS number";
      }
    }
    csc:xr-task "bgp";
    csc:cli-command "clear bgp instance <instance-name> <afi-safi-name> as <as-number> soft in prefix-filter";
  }
  rpc clear-bgp-instance-afi-safi-as-soft-in {
    description
      "Choose a particular BGP instance.
       Clear peers in a specific AS.
       Soft reconfig.
       Soft reconfig inbound update.
      ";
    input {
      leaf instance-name {
        type instance-name;
        mandatory true;
        description
          "instance name or all";
      }
      leaf afi-safi-name {
        type afi-safi-type;
        mandatory true;
        description
          "AFI and SAFI";
      }
      leaf as-number {
        type as-number;
        mandatory true;
        description
          "AS number";
      }
    }
    csc:xr-task "bgp";
    csc:cli-command "clear bgp instance <instance-name> <afi-safi-name> as <as-number> soft in";
  }
  rpc clear-bgp-instance-afi-safi-as-soft-out {
    description
      "Choose a particular BGP instance.
       Clear peers in a specific AS.
       Soft reconfig.
       Soft reconfig outbound update.
      ";
    input {
      leaf instance-name {
        type instance-name;
        mandatory true;
        description
          "instance name or all";
      }
      leaf afi-safi-name {
        type afi-safi-type;
        mandatory true;
        description
          "AFI and SAFI";
      }
      leaf as-number {
        type as-number;
        mandatory true;
        description
          "AS number";
      }
    }
    csc:xr-task "bgp";
    csc:cli-command "clear bgp instance <instance-name> <afi-safi-name> as <as-number> soft out";
  }
  rpc clear-bgp-instance-afi-safi-as-soft {
    description
      "Choose a particular BGP instance.
       Clear peers in a specific AS.
       Soft reconfig.
      ";
    input {
      leaf instance-name {
        type instance-name;
        mandatory true;
        description
          "instance name or all";
      }
      leaf afi-safi-name {
        type afi-safi-type;
        mandatory true;
        description
          "AFI and SAFI";
      }
      leaf as-number {
        type as-number;
        mandatory true;
        description
          "AS number";
      }
    }
    csc:xr-task "bgp";
    csc:cli-command "clear bgp instance <instance-name> <afi-safi-name> as <as-number> soft";
  }
  rpc clear-bgp-instance-afi-safi-dampening-ip-prefix {
    description
      "Choose a particular BGP instance.
       Clear route flap dampening information.
      ";
    input {
      leaf instance-name {
        type instance-name;
        mandatory true;
        description
          "instance name or all";
      }
      leaf afi-safi-name {
        type afi-safi-type;
        mandatory true;
        description
          "AFI and SAFI";
      }
      leaf ip-prefix {
        type inet:ip-prefix;
        mandatory true;
        description
          "Network and mask or masklength to clear dampening information";
      }
    }
    csc:xr-task "bgp";
    csc:cli-command "clear bgp instance <instance-name> <afi-safi-name> dampening <ip-prefix>";
  }
  rpc clear-bgp-instance-afi-safi-dampening {
    description
      "Choose a particular BGP instance.
       Clear route flap dampening information.
      ";
    input {
      leaf instance-name {
        type instance-name;
        mandatory true;
        description
          "instance name or all";
      }
      leaf afi-safi-name {
        type afi-safi-type;
        mandatory true;
        description
          "AFI and SAFI";
      }
    }
    csc:xr-task "bgp";
    csc:cli-command "clear bgp instance <instance-name> <afi-safi-name> dampening";
  }
  rpc clear-bgp-instance-afi-safi-external-soft-in-prefix-filter {
    description
      "Choose a particular BGP instance.
       Clear all external peers.
       Soft reconfig.
       Soft reconfig inbound update.
       Push out prefix ORF and do inbound soft reconfig.
      ";
    input {
      leaf instance-name {
        type instance-name;
        mandatory true;
        description
          "instance name or all";
      }
      leaf afi-safi-name {
        type afi-safi-type;
        mandatory true;
        description
          "AFI and SAFI";
      }
    }
    csc:xr-task "bgp";
    csc:cli-command "clear bgp instance <instance-name> <afi-safi-name> external soft in prefix-filter";
  }
  rpc clear-bgp-instance-afi-safi-external-soft-in {
    description
      "Choose a particular BGP instance.
       Clear all external peers.
       Soft reconfig.
       Soft reconfig inbound update.
      ";
    input {
      leaf instance-name {
        type instance-name;
        mandatory true;
        description
          "instance name or all";
      }
      leaf afi-safi-name {
        type afi-safi-type;
        mandatory true;
        description
          "AFI and SAFI";
      }
    }
    csc:xr-task "bgp";
    csc:cli-command "clear bgp instance <instance-name> <afi-safi-name> external soft in";
  }
  rpc clear-bgp-instance-afi-safi-external-soft-out {
    description
      "Choose a particular BGP instance.
       Clear all external peers.
       Soft reconfig.
       Soft reconfig outbound update.
      ";
    input {
      leaf instance-name {
        type instance-name;
        mandatory true;
        description
          "instance name or all";
      }
      leaf afi-safi-name {
        type afi-safi-type;
        mandatory true;
        description
          "AFI and SAFI";
      }
    }
    csc:xr-task "bgp";
    csc:cli-command "clear bgp instance <instance-name> <afi-safi-name> external soft out";
  }
  rpc clear-bgp-instance-afi-safi-external-soft {
    description
      "Choose a particular BGP instance.
       Clear all external peers.
       Soft reconfig.
      ";
    input {
      leaf instance-name {
        type instance-name;
        mandatory true;
        description
          "instance name or all";
      }
      leaf afi-safi-name {
        type afi-safi-type;
        mandatory true;
        description
          "AFI and SAFI";
      }
    }
    csc:xr-task "bgp";
    csc:cli-command "clear bgp instance <instance-name> <afi-safi-name> external soft";
  }
  rpc clear-bgp-instance-afi-safi-flap-statistics-ip-addr-ipv4-mask {
    description
      "Choose a particular BGP instance.
       Clear flap statistics.
      ";
    input {
      leaf instance-name {
        type instance-name;
        mandatory true;
        description
          "instance name or all";
      }
      leaf afi-safi-name {
        type afi-safi-type;
        mandatory true;
        description
          "AFI and SAFI";
      }
      leaf ip-addr {
        type inet:ip-address;
        mandatory true;
        description
          "BGP neighbor address to clear";
      }
      leaf ipv4-mask {
        type ipv4-netmask;
        mandatory true;
        description
          "Network and mask or masklength to clear flap statistics";
      }
    }
    csc:xr-task "bgp";
    csc:cli-command "clear bgp instance <instance-name> <afi-safi-name> flap-statistics <ip-addr> <ipv4-mask>";
  }
  rpc clear-bgp-instance-afi-safi-flap-statistics-ip-addr {
    description
      "Choose a particular BGP instance.
       Clear flap statistics.
      ";
    input {
      leaf instance-name {
        type instance-name;
        mandatory true;
        description
          "instance name or all";
      }
      leaf afi-safi-name {
        type afi-safi-type;
        mandatory true;
        description
          "AFI and SAFI";
      }
      leaf ip-addr {
        type inet:ip-address;
        mandatory true;
        description
          "BGP neighbor address to clear";
      }
    }
    csc:xr-task "bgp";
    csc:cli-command "clear bgp instance <instance-name> <afi-safi-name> flap-statistics <ip-addr>";
  }
  rpc clear-bgp-instance-afi-safi-flap-statistics-ip-prefix {
    description
      "Choose a particular BGP instance.
       Clear flap statistics.
      ";
    input {
      leaf instance-name {
        type instance-name;
        mandatory true;
        description
          "instance name or all";
      }
      leaf afi-safi-name {
        type afi-safi-type;
        mandatory true;
        description
          "AFI and SAFI";
      }
      leaf ip-prefix {
        type inet:ip-prefix;
        mandatory true;
        description
          "Network and mask or masklength to clear flap statistics";
      }
    }
    csc:xr-task "bgp";
    csc:cli-command "clear bgp instance <instance-name> <afi-safi-name> flap-statistics <ip-prefix>";
  }
  rpc clear-bgp-instance-afi-safi-flap-statistics-regexp {
    description
      "Choose a particular BGP instance.
       Clear flap statistics.
       Clear flap statistics for routes matching the regular expression.
      ";
    input {
      leaf instance-name {
        type instance-name;
        mandatory true;
        description
          "instance name or all";
      }
      leaf afi-safi-name {
        type afi-safi-type;
        mandatory true;
        description
          "AFI and SAFI";
      }
      leaf regexp-pattern {
        type string;
        mandatory true;
        description
          "A regular expression to match the BGP AS paths.  Use 'ctrl-v ?' to enter '?'";
      }
    }
    csc:xr-task "bgp";
    csc:cli-command "clear bgp instance <instance-name> <afi-safi-name> flap-statistics regexp <regexp-pattern>";
  }
  rpc clear-bgp-instance-afi-safi-flap-statistics-route-policy {
    description
      "Choose a particular BGP instance.
       Clear flap statistics.
       Clear flap statistics for routes matching the route policy.
      ";
    input {
      leaf instance-name {
        type instance-name;
        mandatory true;
        description
          "instance name or all";
      }
      leaf afi-safi-name {
        type afi-safi-type;
        mandatory true;
        description
          "AFI and SAFI";
      }
      leaf route-policy-name {
        type string;
        mandatory true;
        description
          "Route Policy name";
      }
    }
    csc:xr-task "bgp";
    csc:cli-command "clear bgp instance <instance-name> <afi-safi-name> flap-statistics route-policy <route-policy-name>";
  }
  rpc clear-bgp-instance-afi-safi-flap-statistics {
    description
      "Choose a particular BGP instance.
       Clear flap statistics.
      ";
    input {
      leaf instance-name {
        type instance-name;
        mandatory true;
        description
          "instance name or all";
      }
      leaf afi-safi-name {
        type afi-safi-type;
        mandatory true;
        description
          "AFI and SAFI";
      }
    }
    csc:xr-task "bgp";
    csc:cli-command "clear bgp instance <instance-name> <afi-safi-name> flap-statistics";
  }
  rpc clear-bgp-instance-afi-safi-nexthop-performance-statistics {
    description
      "Choose a particular BGP instance.
       Clear nexthop.
       Performance statistics information related to processing.
      ";
    input {
      leaf instance-name {
        type instance-name;
        mandatory true;
        description
          "instance name or all";
      }
      leaf afi-safi-name {
        type afi-safi-type;
        mandatory true;
        description
          "AFI and SAFI";
      }
    }
    csc:xr-task "bgp";
    csc:cli-command "clear bgp instance <instance-name> <afi-safi-name> nexthop performance-statistics";
  }
  rpc clear-bgp-instance-afi-safi-nexthop-registration-ip-addr {
    description
      "Choose a particular BGP instance.
       Clear nexthop.
       Registration with RIB and reregister.
      ";
    input {
      leaf instance-name {
        type instance-name;
        mandatory true;
        description
          "instance name or all";
      }
      leaf afi-safi-name {
        type afi-safi-type;
        mandatory true;
        description
          "AFI and SAFI";
      }
      leaf ip-addr {
        type inet:ip-address;
        mandatory true;
        description
          "Nexthop address";
      }
    }
    csc:xr-task "bgp";
    csc:cli-command "clear bgp instance <instance-name> <afi-safi-name> nexthop registration <ip-addr>";
  }
  rpc clear-bgp-instance-afi-safi-self-originated {
    description
      "Choose a particular BGP instance.
       Clear redistributed, network and aggregate routes originated here.
      ";
    input {
      leaf instance-name {
        type instance-name;
        mandatory true;
        description
          "instance name or all";
      }
      leaf afi-safi-name {
        type afi-safi-type;
        mandatory true;
        description
          "AFI and SAFI";
      }
    }
    csc:xr-task "bgp";
    csc:cli-command "clear bgp instance <instance-name> <afi-safi-name> self-originated";
  }
  rpc clear-bgp-instance-afi-safi-shutdown {
    description
      "Choose a particular BGP instance.
       Clear all peers which were shut down due to low memory.
      ";
    input {
      leaf instance-name {
        type instance-name;
        mandatory true;
        description
          "instance name or all";
      }
      leaf afi-safi-name {
        type afi-safi-type;
        mandatory true;
        description
          "AFI and SAFI";
      }
    }
    csc:xr-task "bgp";
    csc:cli-command "clear bgp instance <instance-name> <afi-safi-name> shutdown";
  }
  rpc clear-bgp-instance-afi-safi-update-outq-address-family-update-parent {
    description
      "Choose a particular BGP instance.
       Clear Update information (Do NOT execute without cisco support)(cisco-support).
       Clear Update generation OutQ counters (Do NOT execute without cisco support)(cisco-support).
       Address-family.
       Update parents' OutQ counters too.
      ";
    input {
      leaf instance-name {
        type instance-name;
        mandatory true;
        description
          "instance name or all";
      }
      leaf afi-safi-name {
        type afi-safi-type;
        mandatory true;
        description
          "AFI and SAFI";
      }
    }
    csc:xr-task "bgp";
    csc:cli-command "clear bgp instance <instance-name> <afi-safi-name> update outq address-family update-parent";
  }
  rpc clear-bgp-instance-afi-safi-update-outq-address-family {
    description
      "Choose a particular BGP instance.
       Clear Update information (Do NOT execute without cisco support)(cisco-support).
       Clear Update generation OutQ counters (Do NOT execute without cisco support)(cisco-support).
       Address-family.
      ";
    input {
      leaf instance-name {
        type instance-name;
        mandatory true;
        description
          "instance name or all";
      }
      leaf afi-safi-name {
        type afi-safi-type;
        mandatory true;
        description
          "AFI and SAFI";
      }
    }
    csc:xr-task "bgp";
    csc:cli-command "clear bgp instance <instance-name> <afi-safi-name> update outq address-family";
  }
  rpc clear-bgp-instance-afi-safi-update-outq-neighbor-ip-addr-refresh-update-parent {
    description
      "Choose a particular BGP instance.
       Clear Update information (Do NOT execute without cisco support)(cisco-support).
       Clear Update generation OutQ counters (Do NOT execute without cisco support)(cisco-support).
       Neighbor.
       Refresh OutQ.
       Update parents' OutQ counters too.
      ";
    input {
      leaf instance-name {
        type instance-name;
        mandatory true;
        description
          "instance name or all";
      }
      leaf afi-safi-name {
        type afi-safi-type;
        mandatory true;
        description
          "AFI and SAFI";
      }
      leaf ip-addr {
        type inet:ip-address;
        mandatory true;
        description
          "Neighbor address";
      }
    }
    csc:xr-task "bgp";
    csc:cli-command "clear bgp instance <instance-name> <afi-safi-name> update outq neighbor <ip-addr> refresh update-parent";
  }
  rpc clear-bgp-instance-afi-safi-update-outq-neighbor-ip-addr-refresh {
    description
      "Choose a particular BGP instance.
       Clear Update information (Do NOT execute without cisco support)(cisco-support).
       Clear Update generation OutQ counters (Do NOT execute without cisco support)(cisco-support).
       Neighbor.
       Refresh OutQ.
      ";
    input {
      leaf instance-name {
        type instance-name;
        mandatory true;
        description
          "instance name or all";
      }
      leaf afi-safi-name {
        type afi-safi-type;
        mandatory true;
        description
          "AFI and SAFI";
      }
      leaf ip-addr {
        type inet:ip-address;
        mandatory true;
        description
          "Neighbor address";
      }
    }
    csc:xr-task "bgp";
    csc:cli-command "clear bgp instance <instance-name> <afi-safi-name> update outq neighbor <ip-addr> refresh";
  }
  rpc clear-bgp-instance-afi-safi-update-outq-neighbor-ip-addr-update-parent {
    description
      "Choose a particular BGP instance.
       Clear Update information (Do NOT execute without cisco support)(cisco-support).
       Clear Update generation OutQ counters (Do NOT execute without cisco support)(cisco-support).
       Neighbor.
       Update parents' OutQ counters too.
      ";
    input {
      leaf instance-name {
        type instance-name;
        mandatory true;
        description
          "instance name or all";
      }
      leaf afi-safi-name {
        type afi-safi-type;
        mandatory true;
        description
          "AFI and SAFI";
      }
      leaf ip-addr {
        type inet:ip-address;
        mandatory true;
        description
          "Neighbor address";
      }
    }
    csc:xr-task "bgp";
    csc:cli-command "clear bgp instance <instance-name> <afi-safi-name> update outq neighbor <ip-addr> update-parent";
  }
  rpc clear-bgp-instance-afi-safi-update-outq-neighbor-ip-addr {
    description
      "Choose a particular BGP instance.
       Clear Update information (Do NOT execute without cisco support)(cisco-support).
       Clear Update generation OutQ counters (Do NOT execute without cisco support)(cisco-support).
       Neighbor.
      ";
    input {
      leaf instance-name {
        type instance-name;
        mandatory true;
        description
          "instance name or all";
      }
      leaf afi-safi-name {
        type afi-safi-type;
        mandatory true;
        description
          "AFI and SAFI";
      }
      leaf ip-addr {
        type inet:ip-address;
        mandatory true;
        description
          "Neighbor address";
      }
    }
    csc:xr-task "bgp";
    csc:cli-command "clear bgp instance <instance-name> <afi-safi-name> update outq neighbor <ip-addr>";
  }
  rpc clear-bgp-instance-afi-safi-update-outq-update-group-sub-group-update-parent {
    description
      "Choose a particular BGP instance.
       Clear Update information (Do NOT execute without cisco support)(cisco-support).
       Clear Update generation OutQ counters (Do NOT execute without cisco support)(cisco-support).
       Update-group.
       Sub-group.
       Update parents' OutQ counters too.
      ";
    input {
      leaf instance-name {
        type instance-name;
        mandatory true;
        description
          "instance name or all";
      }
      leaf afi-safi-name {
        type afi-safi-type;
        mandatory true;
        description
          "AFI and SAFI";
      }
      leaf update-group {
        type update-group-id;
        mandatory true;
        description
          "Update-group process ID <x.y>";
      }
      leaf sub-group {
        type update-group-id;
        mandatory true;
        description
          "Sub-group process ID <x.y>";
      }
    }
    csc:xr-task "bgp";
    csc:cli-command "clear bgp instance <instance-name> <afi-safi-name> update outq update-group <update-group> sub-group <sub-group> update-parent";
  }
  rpc clear-bgp-instance-afi-safi-update-outq-update-group-sub-group {
    description
      "Choose a particular BGP instance.
       Clear Update information (Do NOT execute without cisco support)(cisco-support).
       Clear Update generation OutQ counters (Do NOT execute without cisco support)(cisco-support).
       Update-group.
       Sub-group.
      ";
    input {
      leaf instance-name {
        type instance-name;
        mandatory true;
        description
          "instance name or all";
      }
      leaf afi-safi-name {
        type afi-safi-type;
        mandatory true;
        description
          "AFI and SAFI";
      }
      leaf update-group {
        type update-group-id;
        mandatory true;
        description
          "Update-group process ID <x.y>";
      }
      leaf sub-group {
        type update-group-id;
        mandatory true;
        description
          "Sub-group process ID <x.y>";
      }
    }
    csc:xr-task "bgp";
    csc:cli-command "clear bgp instance <instance-name> <afi-safi-name> update outq update-group <update-group> sub-group <sub-group>";
  }
  rpc clear-bgp-instance-afi-safi-update-outq-update-group-sub-group-refresh-sub-group-update-parent {
    description
      "Choose a particular BGP instance.
       Clear Update information (Do NOT execute without cisco support)(cisco-support).
       Clear Update generation OutQ counters (Do NOT execute without cisco support)(cisco-support).
       Update-group.
       Sub-group.
       Update parents' OutQ counters too.
      ";
    input {
      leaf instance-name {
        type instance-name;
        mandatory true;
        description
          "instance name or all";
      }
      leaf afi-safi-name {
        type afi-safi-type;
        mandatory true;
        description
          "AFI and SAFI";
      }
      leaf update-group {
        type update-group-id;
        mandatory true;
        description
          "Update-group process ID <x.y>";
      }
      leaf refresh-sub-group {
        type refresh-sub-group-id;
        mandatory true;
        description
          "Refresh Sub-group process ID <x.y:z>";
      }
    }
    csc:xr-task "bgp";
    csc:cli-command "clear bgp instance <instance-name> <afi-safi-name> update outq update-group <update-group> sub-group <refresh-sub-group> update-parent";
  }
  rpc clear-bgp-instance-afi-safi-update-outq-update-group-sub-group-refresh-sub-group {
    description
      "Choose a particular BGP instance.
       Clear Update information (Do NOT execute without cisco support)(cisco-support).
       Clear Update generation OutQ counters (Do NOT execute without cisco support)(cisco-support).
       Update-group.
       Sub-group.
      ";
    input {
      leaf instance-name {
        type instance-name;
        mandatory true;
        description
          "instance name or all";
      }
      leaf afi-safi-name {
        type afi-safi-type;
        mandatory true;
        description
          "AFI and SAFI";
      }
      leaf update-group {
        type update-group-id;
        mandatory true;
        description
          "Update-group process ID <x.y>";
      }
      leaf refresh-sub-group {
        type refresh-sub-group-id;
        mandatory true;
        description
          "Refresh Sub-group process ID <x.y:z>";
      }
    }
    csc:xr-task "bgp";
    csc:cli-command "clear bgp instance <instance-name> <afi-safi-name> update outq update-group <update-group> sub-group <refresh-sub-group>";
  }
  rpc clear-bgp-instance-afi-safi-update-outq-update-group-update-parent {
    description
      "Choose a particular BGP instance.
       Clear Update information (Do NOT execute without cisco support)(cisco-support).
       Clear Update generation OutQ counters (Do NOT execute without cisco support)(cisco-support).
       Update-group.
       Update parents' OutQ counters too.
      ";
    input {
      leaf instance-name {
        type instance-name;
        mandatory true;
        description
          "instance name or all";
      }
      leaf afi-safi-name {
        type afi-safi-type;
        mandatory true;
        description
          "AFI and SAFI";
      }
      leaf update-group {
        type update-group-id;
        mandatory true;
        description
          "Update-group process ID <x.y>";
      }
    }
    csc:xr-task "bgp";
    csc:cli-command "clear bgp instance <instance-name> <afi-safi-name> update outq update-group <update-group> update-parent";
  }
  rpc clear-bgp-instance-afi-safi-update-outq-update-group {
    description
      "Choose a particular BGP instance.
       Clear Update information (Do NOT execute without cisco support)(cisco-support).
       Clear Update generation OutQ counters (Do NOT execute without cisco support)(cisco-support).
       Update-group.
      ";
    input {
      leaf instance-name {
        type instance-name;
        mandatory true;
        description
          "instance name or all";
      }
      leaf afi-safi-name {
        type afi-safi-type;
        mandatory true;
        description
          "AFI and SAFI";
      }
      leaf update-group {
        type update-group-id;
        mandatory true;
        description
          "Update-group process ID <x.y>";
      }
    }
    csc:xr-task "bgp";
    csc:cli-command "clear bgp instance <instance-name> <afi-safi-name> update outq update-group <update-group>";
  }
  rpc clear-bgp-instance-as-graceful {
    description
      "Choose a particular BGP instance.
       Clear peers in a specific AS.
       Clear with a hard reset and a graceful restart.
      ";
    input {
      leaf instance-name {
        type instance-name;
        mandatory true;
        description
          "instance name or all";
      }
      leaf as-number {
        type as-number;
        mandatory true;
        description
          "AS number";
      }
    }
    csc:xr-task "bgp";
    csc:cli-command "clear bgp instance <instance-name> as <as-number> graceful";
  }
  rpc clear-bgp-instance-as {
    description
      "Choose a particular BGP instance.
       Clear peers in a specific AS.
      ";
    input {
      leaf instance-name {
        type instance-name;
        mandatory true;
        description
          "instance name or all";
      }
      leaf as-number {
        type as-number;
        mandatory true;
        description
          "AS number";
      }
    }
    csc:xr-task "bgp";
    csc:cli-command "clear bgp instance <instance-name> as <as-number>";
  }
  rpc clear-bgp-instance-bestpath-ip-addr-ip-netmask {
    description
      "Choose a particular BGP instance.
       re-run BGP bestpath selection.
      ";
    input {
      leaf instance-name {
        type instance-name;
        mandatory true;
        description
          "instance name or all";
      }
      leaf ip-addr {
        type inet:ip-address;
        mandatory true;
        description
          "Network";
      }
      leaf ip-netmask {
        type ip-netmask;
        mandatory true;
        description
          "Mask";
      }
    }
    csc:xr-task "bgp";
    csc:cli-command "clear bgp instance <instance-name> bestpath <ip-addr> <ip-netmask>";
  }
  rpc clear-bgp-instance-bestpath-ip-addr {
    description
      "Choose a particular BGP instance.
       re-run BGP bestpath selection.
      ";
    input {
      leaf instance-name {
        type instance-name;
        mandatory true;
        description
          "instance name or all";
      }
      leaf ip-addr {
        type inet:ip-address;
        mandatory true;
        description
          "Network";
      }
    }
    csc:xr-task "bgp";
    csc:cli-command "clear bgp instance <instance-name> bestpath <ip-addr>";
  }
  rpc clear-bgp-instance-bestpath-ip-prefix {
    description
      "Choose a particular BGP instance.
       re-run BGP bestpath selection.
      ";
    input {
      leaf instance-name {
        type instance-name;
        mandatory true;
        description
          "instance name or all";
      }
      leaf ip-prefix {
        type inet:ip-prefix;
        mandatory true;
        description
          "Network and masklength";
      }
    }
    csc:xr-task "bgp";
    csc:cli-command "clear bgp instance <instance-name> bestpath <ip-prefix>";
  }
  rpc clear-bgp-instance-bestpath-afi-safi-ip-addr-ip-netmask {
    description
      "Choose a particular BGP instance.
       re-run BGP bestpath selection.
      ";
    input {
      leaf instance-name {
        type instance-name;
        mandatory true;
        description
          "instance name or all";
      }
      leaf afi-safi-name {
        type afi-safi-type;
        mandatory true;
        description
          "AFI and SAFI";
      }
      leaf ip-addr {
        type inet:ip-address;
        mandatory true;
        description
          "Network";
      }
      leaf ip-netmask {
        type ip-netmask;
        mandatory true;
        description
          "Mask";
      }
    }
    csc:xr-task "bgp";
    csc:cli-command "clear bgp instance <instance-name> bestpath <afi-safi-name> <ip-addr> <ip-netmask>";
  }
  rpc clear-bgp-instance-bestpath-afi-safi-ip-addr {
    description
      "Choose a particular BGP instance.
       re-run BGP bestpath selection.
      ";
    input {
      leaf instance-name {
        type instance-name;
        mandatory true;
        description
          "instance name or all";
      }
      leaf afi-safi-name {
        type afi-safi-type;
        mandatory true;
        description
          "AFI and SAFI";
      }
      leaf ip-addr {
        type inet:ip-address;
        mandatory true;
        description
          "Network";
      }
    }
    csc:xr-task "bgp";
    csc:cli-command "clear bgp instance <instance-name> bestpath <afi-safi-name> <ip-addr>";
  }
  rpc clear-bgp-instance-bestpath-afi-safi-ip-prefix {
    description
      "Choose a particular BGP instance.
       re-run BGP bestpath selection.
      ";
    input {
      leaf instance-name {
        type instance-name;
        mandatory true;
        description
          "instance name or all";
      }
      leaf afi-safi-name {
        type afi-safi-type;
        mandatory true;
        description
          "AFI and SAFI";
      }
      leaf ip-prefix {
        type inet:ip-prefix;
        mandatory true;
        description
          "Network and masklength";
      }
    }
    csc:xr-task "bgp";
    csc:cli-command "clear bgp instance <instance-name> bestpath <afi-safi-name> <ip-prefix>";
  }
  rpc clear-bgp-instance-bestpath-afi-safi-bridge-domain-ip-addr-ip-netmask {
    description
      "Choose a particular BGP instance.
       re-run BGP bestpath selection.
       Display routes for a specified Bridge Domain.
      ";
    input {
      leaf instance-name {
        type instance-name;
        mandatory true;
        description
          "instance name or all";
      }
      leaf afi-safi-name {
        type afi-safi-type;
        mandatory true;
        description
          "AFI and SAFI";
      }
      leaf bridge-domain-name {
        type string;
        mandatory true;
        description
          "Bridge Domain";
      }
      leaf ip-addr {
        type inet:ip-address;
        mandatory true;
        description
          "Network";
      }
      leaf ip-netmask {
        type ip-netmask;
        mandatory true;
        description
          "Mask";
      }
    }
    csc:xr-task "bgp";
    csc:cli-command "clear bgp instance <instance-name> bestpath <afi-safi-name> bridge-domain <bridge-domain-name> <ip-addr> <ip-netmask>";
  }
  rpc clear-bgp-instance-bestpath-afi-safi-bridge-domain-ip-addr {
    description
      "Choose a particular BGP instance.
       re-run BGP bestpath selection.
       Display routes for a specified Bridge Domain.
      ";
    input {
      leaf instance-name {
        type instance-name;
        mandatory true;
        description
          "instance name or all";
      }
      leaf afi-safi-name {
        type afi-safi-type;
        mandatory true;
        description
          "AFI and SAFI";
      }
      leaf bridge-domain-name {
        type string;
        mandatory true;
        description
          "Bridge Domain";
      }
      leaf ip-addr {
        type inet:ip-address;
        mandatory true;
        description
          "Network";
      }
    }
    csc:xr-task "bgp";
    csc:cli-command "clear bgp instance <instance-name> bestpath <afi-safi-name> bridge-domain <bridge-domain-name> <ip-addr>";
  }
  rpc clear-bgp-instance-bestpath-afi-safi-bridge-domain-ip-prefix {
    description
      "Choose a particular BGP instance.
       re-run BGP bestpath selection.
       Display routes for a specified Bridge Domain.
      ";
    input {
      leaf instance-name {
        type instance-name;
        mandatory true;
        description
          "instance name or all";
      }
      leaf afi-safi-name {
        type afi-safi-type;
        mandatory true;
        description
          "AFI and SAFI";
      }
      leaf bridge-domain-name {
        type string;
        mandatory true;
        description
          "Bridge Domain";
      }
      leaf ip-prefix {
        type inet:ip-prefix;
        mandatory true;
        description
          "Network and masklength";
      }
    }
    csc:xr-task "bgp";
    csc:cli-command "clear bgp instance <instance-name> bestpath <afi-safi-name> bridge-domain <bridge-domain-name> <ip-prefix>";
  }
  rpc clear-bgp-instance-bestpath-afi-safi-rd-ip-addr-ip-netmask {
    description
      "Choose a particular BGP instance.
       re-run BGP bestpath selection.
       Display routes with a specific route distinguisher.
      ";
    input {
      leaf instance-name {
        type instance-name;
        mandatory true;
        description
          "instance name or all";
      }
      leaf afi-safi-name {
        type afi-safi-type;
        mandatory true;
        description
          "AFI and SAFI";
      }
      leaf rd {
        type rd;
        mandatory true;
        description
          "Route distinguisher";
      }
      leaf ip-addr {
        type inet:ip-address;
        mandatory true;
        description
          "Network";
      }
      leaf ip-netmask {
        type ip-netmask;
        mandatory true;
        description
          "Mask";
      }
    }
    csc:xr-task "bgp";
    csc:cli-command "clear bgp instance <instance-name> bestpath <afi-safi-name> rd <rd> <ip-addr> <ip-netmask>";
  }
  rpc clear-bgp-instance-bestpath-afi-safi-rd-ip-addr {
    description
      "Choose a particular BGP instance.
       re-run BGP bestpath selection.
       Display routes with a specific route distinguisher.
      ";
    input {
      leaf instance-name {
        type instance-name;
        mandatory true;
        description
          "instance name or all";
      }
      leaf afi-safi-name {
        type afi-safi-type;
        mandatory true;
        description
          "AFI and SAFI";
      }
      leaf rd {
        type rd;
        mandatory true;
        description
          "Route distinguisher";
      }
      leaf ip-addr {
        type inet:ip-address;
        mandatory true;
        description
          "Network";
      }
    }
    csc:xr-task "bgp";
    csc:cli-command "clear bgp instance <instance-name> bestpath <afi-safi-name> rd <rd> <ip-addr>";
  }
  rpc clear-bgp-instance-bestpath-afi-safi-rd-ip-prefix {
    description
      "Choose a particular BGP instance.
       re-run BGP bestpath selection.
       Display routes with a specific route distinguisher.
      ";
    input {
      leaf instance-name {
        type instance-name;
        mandatory true;
        description
          "instance name or all";
      }
      leaf afi-safi-name {
        type afi-safi-type;
        mandatory true;
        description
          "AFI and SAFI";
      }
      leaf rd {
        type rd;
        mandatory true;
        description
          "Route distinguisher";
      }
      leaf ip-prefix {
        type inet:ip-prefix;
        mandatory true;
        description
          "Network and masklength";
      }
    }
    csc:xr-task "bgp";
    csc:cli-command "clear bgp instance <instance-name> bestpath <afi-safi-name> rd <rd> <ip-prefix>";
  }
  rpc clear-bgp-instance-bestpath-afi-safi-ipv4-addr-ipv4-mask {
    description
      "Choose a particular BGP instance.
       re-run BGP bestpath selection.
      ";
    input {
      leaf instance-name {
        type instance-name;
        mandatory true;
        description
          "instance name or all";
      }
      leaf afi-safi-name {
        type afi-safi-type;
        mandatory true;
        description
          "AFI and SAFI";
      }
      leaf ipv4-addr {
        type inet:ipv4-address;
        mandatory true;
        description
          "IPv4 network";
      }
      leaf ipv4-mask {
        type ipv4-netmask;
        mandatory true;
        description
          "IPv4 mask";
      }
    }
    csc:xr-task "bgp";
    csc:cli-command "clear bgp instance <instance-name> bestpath <afi-safi-name> <ipv4-addr> <ipv4-mask>";
  }
  rpc clear-bgp-instance-bestpath-afi-safi-ipv4-addr {
    description
      "Choose a particular BGP instance.
       re-run BGP bestpath selection.
      ";
    input {
      leaf instance-name {
        type instance-name;
        mandatory true;
        description
          "instance name or all";
      }
      leaf afi-safi-name {
        type afi-safi-type;
        mandatory true;
        description
          "AFI and SAFI";
      }
      leaf ipv4-addr {
        type inet:ipv4-address;
        mandatory true;
        description
          "IPv4 network";
      }
    }
    csc:xr-task "bgp";
    csc:cli-command "clear bgp instance <instance-name> bestpath <afi-safi-name> <ipv4-addr>";
  }
  rpc clear-bgp-instance-bestpath-afi-safi-ipv4-prefix {
    description
      "Choose a particular BGP instance.
       re-run BGP bestpath selection.
      ";
    input {
      leaf instance-name {
        type instance-name;
        mandatory true;
        description
          "instance name or all";
      }
      leaf afi-safi-name {
        type afi-safi-type;
        mandatory true;
        description
          "AFI and SAFI";
      }
      leaf ipv4-prefix {
        type inet:ipv4-prefix;
        mandatory true;
        description
          "IPv4 network and masklength";
      }
    }
    csc:xr-task "bgp";
    csc:cli-command "clear bgp instance <instance-name> bestpath <afi-safi-name> <ipv4-prefix>";
  }
  rpc clear-bgp-instance-bestpath-afi-safi-rd-ipv4-addr {
    description
      "Choose a particular BGP instance.
       re-run BGP bestpath selection.
       Display routes with a specific route distinguisher.
      ";
    input {
      leaf instance-name {
        type instance-name;
        mandatory true;
        description
          "instance name or all";
      }
      leaf afi-safi-name {
        type afi-safi-type;
        mandatory true;
        description
          "AFI and SAFI";
      }
      leaf rd {
        type rd;
        mandatory true;
        description
          "Route distinguisher";
      }
      leaf ipv4-addr {
        type inet:ipv4-address;
        mandatory true;
        description
          "IPv4 MDT network";
      }
    }
    csc:xr-task "bgp";
    csc:cli-command "clear bgp instance <instance-name> bestpath <afi-safi-name> rd <rd> <ipv4-addr>";
  }
  rpc clear-bgp-instance-bestpath-afi-safi-vrf-ipv4-addr {
    description
      "Choose a particular BGP instance.
       re-run BGP bestpath selection.
       Display routes for a specified VRF.
      ";
    input {
      leaf instance-name {
        type instance-name;
        mandatory true;
        description
          "instance name or all";
      }
      leaf afi-safi-name {
        type afi-safi-type;
        mandatory true;
        description
          "AFI and SAFI";
      }
      leaf vrf-name {
        type string;
        mandatory true;
        description
          "VRF name";
      }
      leaf ipv4-addr {
        type inet:ipv4-address;
        mandatory true;
        description
          "IPv4 MDT network";
      }
    }
    csc:xr-task "bgp";
    csc:cli-command "clear bgp instance <instance-name> bestpath <afi-safi-name> vrf <vrf-name> <ipv4-addr>";
  }
  rpc clear-bgp-instance-bestpath-afi-safi-network {
    description
      "Choose a particular BGP instance.
       re-run BGP bestpath selection.
      ";
    input {
      leaf instance-name {
        type instance-name;
        mandatory true;
        description
          "instance name or all";
      }
      leaf afi-safi-name {
        type afi-safi-type;
        mandatory true;
        description
          "AFI and SAFI";
      }
      leaf network {
        type string;
        mandatory true;
        description
          "Address family modifier specific network";
      }
    }
    csc:xr-task "bgp";
    csc:cli-command "clear bgp instance <instance-name> bestpath <afi-safi-name> <network>";
  }
  rpc clear-bgp-instance-bestpath-afi-safi-rd-network {
    description
      "Choose a particular BGP instance.
       re-run BGP bestpath selection.
       Display routes with a specific route distinguisher.
      ";
    input {
      leaf instance-name {
        type instance-name;
        mandatory true;
        description
          "instance name or all";
      }
      leaf afi-safi-name {
        type afi-safi-type;
        mandatory true;
        description
          "AFI and SAFI";
      }
      leaf rd {
        type rd;
        mandatory true;
        description
          "Route distinguisher";
      }
      leaf network {
        type string;
        mandatory true;
        description
          "Address family modifier specific network";
      }
    }
    csc:xr-task "bgp";
    csc:cli-command "clear bgp instance <instance-name> bestpath <afi-safi-name> rd <rd> <network>";
  }
  rpc clear-bgp-instance-bestpath-afi-safi-vrf-network {
    description
      "Choose a particular BGP instance.
       re-run BGP bestpath selection.
       Display routes for a specified VRF.
      ";
    input {
      leaf instance-name {
        type instance-name;
        mandatory true;
        description
          "instance name or all";
      }
      leaf afi-safi-name {
        type afi-safi-type;
        mandatory true;
        description
          "AFI and SAFI";
      }
      leaf vrf-name {
        type string;
        mandatory true;
        description
          "VRF name";
      }
      leaf network {
        type string;
        mandatory true;
        description
          "Address family modifier specific network";
      }
    }
    csc:xr-task "bgp";
    csc:cli-command "clear bgp instance <instance-name> bestpath <afi-safi-name> vrf <vrf-name> <network>";
  }
  rpc clear-bgp-instance-bestpath-afi-safi-rt-constraint-network {
    description
      "Choose a particular BGP instance.
       re-run BGP bestpath selection.
      ";
    input {
      leaf instance-name {
        type instance-name;
        mandatory true;
        description
          "instance name or all";
      }
      leaf afi-safi-name {
        type afi-safi-type;
        mandatory true;
        description
          "AFI and SAFI";
      }
      leaf rt-constraint-network {
        type string;
        mandatory true;
        description
          "RT-Constraint network";
      }
    }
    csc:xr-task "bgp";
    csc:cli-command "clear bgp instance <instance-name> bestpath <afi-safi-name> <rt-constraint-network>";
  }
  rpc clear-bgp-instance-bestpath-afi-safi-ipv4-tunnel-network {
    description
      "Choose a particular BGP instance.
       re-run BGP bestpath selection.
      ";
    input {
      leaf instance-name {
        type instance-name;
        mandatory true;
        description
          "instance name or all";
      }
      leaf afi-safi-name {
        type afi-safi-type;
        mandatory true;
        description
          "AFI and SAFI";
      }
      leaf ipv4-tunnel-network {
        type string;
        mandatory true;
        description
          "IPv4 Tunnel network <Tunnel-ID>:<IPv4 Address>";
      }
    }
    csc:xr-task "bgp";
    csc:cli-command "clear bgp instance <instance-name> bestpath <afi-safi-name> <ipv4-tunnel-network>";
  }
  rpc clear-bgp-instance-bestpath-afi-safi-ipv6-addr-ipv6-netmask {
    description
      "Choose a particular BGP instance.
       re-run BGP bestpath selection.
      ";
    input {
      leaf instance-name {
        type instance-name;
        mandatory true;
        description
          "instance name or all";
      }
      leaf afi-safi-name {
        type afi-safi-type;
        mandatory true;
        description
          "AFI and SAFI";
      }
      leaf ipv6-addr {
        type inet:ipv6-address;
        mandatory true;
        description
          "IPv6 network";
      }
      leaf ipv6-netmask {
        type ipv6-netmask;
        mandatory true;
        description
          "IPv6 mask";
      }
    }
    csc:xr-task "bgp";
    csc:cli-command "clear bgp instance <instance-name> bestpath <afi-safi-name> <ipv6-addr> <ipv6-netmask>";
  }
  rpc clear-bgp-instance-bestpath-afi-safi-ipv6-addr {
    description
      "Choose a particular BGP instance.
       re-run BGP bestpath selection.
      ";
    input {
      leaf instance-name {
        type instance-name;
        mandatory true;
        description
          "instance name or all";
      }
      leaf afi-safi-name {
        type afi-safi-type;
        mandatory true;
        description
          "AFI and SAFI";
      }
      leaf ipv6-addr {
        type inet:ipv6-address;
        mandatory true;
        description
          "IPv6 network";
      }
    }
    csc:xr-task "bgp";
    csc:cli-command "clear bgp instance <instance-name> bestpath <afi-safi-name> <ipv6-addr>";
  }
  rpc clear-bgp-instance-bestpath-afi-safi-ipv6-prefix {
    description
      "Choose a particular BGP instance.
       re-run BGP bestpath selection.
      ";
    input {
      leaf instance-name {
        type instance-name;
        mandatory true;
        description
          "instance name or all";
      }
      leaf afi-safi-name {
        type afi-safi-type;
        mandatory true;
        description
          "AFI and SAFI";
      }
      leaf ipv6-prefix {
        type inet:ipv6-prefix;
        mandatory true;
        description
          "IPv6 network and masklength";
      }
    }
    csc:xr-task "bgp";
    csc:cli-command "clear bgp instance <instance-name> bestpath <afi-safi-name> <ipv6-prefix>";
  }
  rpc clear-bgp-instance-bestpath-afi-safi-rd {
    description
      "Choose a particular BGP instance.
       re-run BGP bestpath selection.
       Display routes with a specific route distinguisher.
      ";
    input {
      leaf instance-name {
        type instance-name;
        mandatory true;
        description
          "instance name or all";
      }
      leaf afi-safi-name {
        type afi-safi-type;
        mandatory true;
        description
          "AFI and SAFI";
      }
      leaf rd {
        type rd;
        mandatory true;
        description
          "Route distinguisher";
      }
    }
    csc:xr-task "bgp";
    csc:cli-command "clear bgp instance <instance-name> bestpath <afi-safi-name> rd <rd>";
  }
  rpc clear-bgp-instance-bestpath-afi-safi-vrf {
    description
      "Choose a particular BGP instance.
       re-run BGP bestpath selection.
       Display routes for a specified VRF.
      ";
    input {
      leaf instance-name {
        type instance-name;
        mandatory true;
        description
          "instance name or all";
      }
      leaf afi-safi-name {
        type afi-safi-type;
        mandatory true;
        description
          "AFI and SAFI";
      }
      leaf vrf-name {
        type string;
        mandatory true;
        description
          "VRF name";
      }
    }
    csc:xr-task "bgp";
    csc:cli-command "clear bgp instance <instance-name> bestpath <afi-safi-name> vrf <vrf-name>";
  }
  rpc clear-bgp-instance-bestpath-afi-safi {
    description
      "Choose a particular BGP instance.
       re-run BGP bestpath selection.
      ";
    input {
      leaf instance-name {
        type instance-name;
        mandatory true;
        description
          "instance name or all";
      }
      leaf afi-safi-name {
        type afi-safi-type;
        mandatory true;
        description
          "AFI and SAFI";
      }
    }
    csc:xr-task "bgp";
    csc:cli-command "clear bgp instance <instance-name> bestpath <afi-safi-name>";
  }
  rpc clear-bgp-instance-bestpath-afi-safi-sr-policy-prefix {
    description
      "Choose a particular BGP instance.
       re-run BGP bestpath selection.
      ";
    input {
      leaf instance-name {
        type instance-name;
        mandatory true;
        description
          "instance name or all";
      }
      leaf afi-safi-name {
        type afi-safi-type;
        mandatory true;
        description
          "AFI and SAFI";
      }
      leaf sr-policy-prefix {
        type string;
        mandatory true;
        description
          "SR Policy prefix";
      }
    }
    csc:xr-task "bgp";
    csc:cli-command "clear bgp instance <instance-name> bestpath <afi-safi-name> <sr-policy-prefix>";
  }
  rpc clear-bgp-instance-bestpath-afi-safi-bridge-domain-ipv4-prefix {
    description
      "Choose a particular BGP instance.
       re-run BGP bestpath selection.
       Display routes for a specified Bridge Domain.
      ";
    input {
      leaf instance-name {
        type instance-name;
        mandatory true;
        description
          "instance name or all";
      }
      leaf afi-safi-name {
        type afi-safi-type;
        mandatory true;
        description
          "AFI and SAFI";
      }
      leaf bridge-domain-name {
        type string;
        mandatory true;
        description
          "Bridge Domain";
      }
      leaf ipv4-prefix {
        type inet:ipv4-prefix;
        mandatory true;
        description
          "L2VPN EVPN Prefix";
      }
    }
    csc:xr-task "bgp";
    csc:cli-command "clear bgp instance <instance-name> bestpath <afi-safi-name> bridge-domain <bridge-domain-name> <ipv4-prefix>";
  }
  rpc clear-bgp-instance-bestpath-afi-safi-rd-ipv4-prefix {
    description
      "Choose a particular BGP instance.
       re-run BGP bestpath selection.
       Display routes with a specific route distinguisher.
      ";
    input {
      leaf instance-name {
        type instance-name;
        mandatory true;
        description
          "instance name or all";
      }
      leaf afi-safi-name {
        type afi-safi-type;
        mandatory true;
        description
          "AFI and SAFI";
      }
      leaf rd {
        type rd;
        mandatory true;
        description
          "Route distinguisher";
      }
      leaf ipv4-prefix {
        type inet:ipv4-prefix;
        mandatory true;
        description
          "L2VPN EVPN Prefix";
      }
    }
    csc:xr-task "bgp";
    csc:cli-command "clear bgp instance <instance-name> bestpath <afi-safi-name> rd <rd> <ipv4-prefix>";
  }
  rpc clear-bgp-instance-bestpath-afi-safi-mp2mp-ipv4-prefix {
    description
      "Choose a particular BGP instance.
       re-run BGP bestpath selection.
       Display routes for a specified Xconnect group:MP2MP.
      ";
    input {
      leaf instance-name {
        type instance-name;
        mandatory true;
        description
          "instance name or all";
      }
      leaf afi-safi-name {
        type afi-safi-type;
        mandatory true;
        description
          "AFI and SAFI";
      }
      leaf mp2mp {
        type string;
        mandatory true;
        description
          "Xconnect Group:mp2mp";
      }
      leaf ipv4-prefix {
        type inet:ipv4-prefix;
        mandatory true;
        description
          "L2VPN VPWS Prefix";
      }
    }
    csc:xr-task "bgp";
    csc:cli-command "clear bgp instance <instance-name> bestpath <afi-safi-name> mp2mp <mp2mp> <ipv4-prefix>";
  }
  rpc clear-bgp-instance-bestpath-afi-safi-vrf-ipv4-prefix {
    description
      "Choose a particular BGP instance.
       re-run BGP bestpath selection.
       Display routes for a specified VRF.
      ";
    input {
      leaf instance-name {
        type instance-name;
        mandatory true;
        description
          "instance name or all";
      }
      leaf afi-safi-name {
        type afi-safi-type;
        mandatory true;
        description
          "AFI and SAFI";
      }
      leaf vrf-name {
        type string;
        mandatory true;
        description
          "VRF name";
      }
      leaf ipv4-prefix {
        type inet:ipv4-prefix;
        mandatory true;
        description
          "VPN Fspec Prefix";
      }
    }
    csc:xr-task "bgp";
    csc:cli-command "clear bgp instance <instance-name> bestpath <afi-safi-name> vrf <vrf-name> <ipv4-prefix>";
  }
  rpc clear-bgp-instance-bestpath-afi-safi-rd-ipv4-addr-ipv4-mask {
    description
      "Choose a particular BGP instance.
       re-run BGP bestpath selection.
       Display routes with a specific route distinguisher.
      ";
    input {
      leaf instance-name {
        type instance-name;
        mandatory true;
        description
          "instance name or all";
      }
      leaf afi-safi-name {
        type afi-safi-type;
        mandatory true;
        description
          "AFI and SAFI";
      }
      leaf rd {
        type rd;
        mandatory true;
        description
          "Route distinguisher";
      }
      leaf ipv4-addr {
        type inet:ipv4-address;
        mandatory true;
        description
          "IPv4 network";
      }
      leaf ipv4-mask {
        type ipv4-netmask;
        mandatory true;
        description
          "IPv4 mask";
      }
    }
    csc:xr-task "bgp";
    csc:cli-command "clear bgp instance <instance-name> bestpath <afi-safi-name> rd <rd> <ipv4-addr> <ipv4-mask>";
  }
  rpc clear-bgp-instance-bestpath-afi-safi-vrf-ipv4-addr-ipv4-mask {
    description
      "Choose a particular BGP instance.
       re-run BGP bestpath selection.
       Display routes for a specified VRF.
      ";
    input {
      leaf instance-name {
        type instance-name;
        mandatory true;
        description
          "instance name or all";
      }
      leaf afi-safi-name {
        type afi-safi-type;
        mandatory true;
        description
          "AFI and SAFI";
      }
      leaf vrf-name {
        type string;
        mandatory true;
        description
          "VRF name";
      }
      leaf ipv4-addr {
        type inet:ipv4-address;
        mandatory true;
        description
          "IPv4 network";
      }
      leaf ipv4-mask {
        type ipv4-netmask;
        mandatory true;
        description
          "IPv4 mask";
      }
    }
    csc:xr-task "bgp";
    csc:cli-command "clear bgp instance <instance-name> bestpath <afi-safi-name> vrf <vrf-name> <ipv4-addr> <ipv4-mask>";
  }
  rpc clear-bgp-instance-bestpath-afi-safi-rd-ipv6-addr-ipv6-netmask {
    description
      "Choose a particular BGP instance.
       re-run BGP bestpath selection.
       Display routes with a specific route distinguisher.
      ";
    input {
      leaf instance-name {
        type instance-name;
        mandatory true;
        description
          "instance name or all";
      }
      leaf afi-safi-name {
        type afi-safi-type;
        mandatory true;
        description
          "AFI and SAFI";
      }
      leaf rd {
        type rd;
        mandatory true;
        description
          "Route distinguisher";
      }
      leaf ipv6-addr {
        type inet:ipv6-address;
        mandatory true;
        description
          "IPv6 network";
      }
      leaf ipv6-netmask {
        type ipv6-netmask;
        mandatory true;
        description
          "IPv6 mask";
      }
    }
    csc:xr-task "bgp";
    csc:cli-command "clear bgp instance <instance-name> bestpath <afi-safi-name> rd <rd> <ipv6-addr> <ipv6-netmask>";
  }
  rpc clear-bgp-instance-bestpath-afi-safi-rd-ipv6-addr {
    description
      "Choose a particular BGP instance.
       re-run BGP bestpath selection.
       Display routes with a specific route distinguisher.
      ";
    input {
      leaf instance-name {
        type instance-name;
        mandatory true;
        description
          "instance name or all";
      }
      leaf afi-safi-name {
        type afi-safi-type;
        mandatory true;
        description
          "AFI and SAFI";
      }
      leaf rd {
        type rd;
        mandatory true;
        description
          "Route distinguisher";
      }
      leaf ipv6-addr {
        type inet:ipv6-address;
        mandatory true;
        description
          "IPv6 network";
      }
    }
    csc:xr-task "bgp";
    csc:cli-command "clear bgp instance <instance-name> bestpath <afi-safi-name> rd <rd> <ipv6-addr>";
  }
  rpc clear-bgp-instance-bestpath-afi-safi-rd-ipv6-prefix {
    description
      "Choose a particular BGP instance.
       re-run BGP bestpath selection.
       Display routes with a specific route distinguisher.
      ";
    input {
      leaf instance-name {
        type instance-name;
        mandatory true;
        description
          "instance name or all";
      }
      leaf afi-safi-name {
        type afi-safi-type;
        mandatory true;
        description
          "AFI and SAFI";
      }
      leaf rd {
        type rd;
        mandatory true;
        description
          "Route distinguisher";
      }
      leaf ipv6-prefix {
        type inet:ipv6-prefix;
        mandatory true;
        description
          "IPv6 network and masklength";
      }
    }
    csc:xr-task "bgp";
    csc:cli-command "clear bgp instance <instance-name> bestpath <afi-safi-name> rd <rd> <ipv6-prefix>";
  }
  rpc clear-bgp-instance-bestpath-afi-safi-vrf-ipv6-addr-ipv6-netmask {
    description
      "Choose a particular BGP instance.
       re-run BGP bestpath selection.
       Display routes for a specified VRF.
      ";
    input {
      leaf instance-name {
        type instance-name;
        mandatory true;
        description
          "instance name or all";
      }
      leaf afi-safi-name {
        type afi-safi-type;
        mandatory true;
        description
          "AFI and SAFI";
      }
      leaf vrf-name {
        type string;
        mandatory true;
        description
          "VRF name";
      }
      leaf ipv6-addr {
        type inet:ipv6-address;
        mandatory true;
        description
          "IPv6 network";
      }
      leaf ipv6-netmask {
        type ipv6-netmask;
        mandatory true;
        description
          "IPv6 mask";
      }
    }
    csc:xr-task "bgp";
    csc:cli-command "clear bgp instance <instance-name> bestpath <afi-safi-name> vrf <vrf-name> <ipv6-addr> <ipv6-netmask>";
  }
  rpc clear-bgp-instance-bestpath-afi-safi-vrf-ipv6-addr {
    description
      "Choose a particular BGP instance.
       re-run BGP bestpath selection.
       Display routes for a specified VRF.
      ";
    input {
      leaf instance-name {
        type instance-name;
        mandatory true;
        description
          "instance name or all";
      }
      leaf afi-safi-name {
        type afi-safi-type;
        mandatory true;
        description
          "AFI and SAFI";
      }
      leaf vrf-name {
        type string;
        mandatory true;
        description
          "VRF name";
      }
      leaf ipv6-addr {
        type inet:ipv6-address;
        mandatory true;
        description
          "IPv6 network";
      }
    }
    csc:xr-task "bgp";
    csc:cli-command "clear bgp instance <instance-name> bestpath <afi-safi-name> vrf <vrf-name> <ipv6-addr>";
  }
  rpc clear-bgp-instance-bestpath-afi-safi-vrf-ipv6-prefix {
    description
      "Choose a particular BGP instance.
       re-run BGP bestpath selection.
       Display routes for a specified VRF.
      ";
    input {
      leaf instance-name {
        type instance-name;
        mandatory true;
        description
          "instance name or all";
      }
      leaf afi-safi-name {
        type afi-safi-type;
        mandatory true;
        description
          "AFI and SAFI";
      }
      leaf vrf-name {
        type string;
        mandatory true;
        description
          "VRF name";
      }
      leaf ipv6-prefix {
        type inet:ipv6-prefix;
        mandatory true;
        description
          "IPv6 network and masklength";
      }
    }
    csc:xr-task "bgp";
    csc:cli-command "clear bgp instance <instance-name> bestpath <afi-safi-name> vrf <vrf-name> <ipv6-prefix>";
  }
  rpc clear-bgp-instance-bestpath-vrf-ip-addr-ip-netmask {
    description
      "Choose a particular BGP instance.
       re-run BGP bestpath selection.
       Specify a VRF.
      ";
    input {
      leaf instance-name {
        type instance-name;
        mandatory true;
        description
          "instance name or all";
      }
      leaf vrf-all {
        type vrf-name;
        mandatory true;
        description
          "VRF name or all";
      }
      leaf ip-addr {
        type inet:ip-address;
        mandatory true;
        description
          "Network";
      }
      leaf ip-netmask {
        type ip-netmask;
        mandatory true;
        description
          "Mask";
      }
    }
    csc:xr-task "bgp";
    csc:cli-command "clear bgp instance <instance-name> bestpath vrf <vrf-all> <ip-addr> <ip-netmask>";
  }
  rpc clear-bgp-instance-bestpath-vrf-ip-addr {
    description
      "Choose a particular BGP instance.
       re-run BGP bestpath selection.
       Specify a VRF.
      ";
    input {
      leaf instance-name {
        type instance-name;
        mandatory true;
        description
          "instance name or all";
      }
      leaf vrf-all {
        type vrf-name;
        mandatory true;
        description
          "VRF name or all";
      }
      leaf ip-addr {
        type inet:ip-address;
        mandatory true;
        description
          "Network";
      }
    }
    csc:xr-task "bgp";
    csc:cli-command "clear bgp instance <instance-name> bestpath vrf <vrf-all> <ip-addr>";
  }
  rpc clear-bgp-instance-bestpath-vrf-ip-prefix {
    description
      "Choose a particular BGP instance.
       re-run BGP bestpath selection.
       Specify a VRF.
      ";
    input {
      leaf instance-name {
        type instance-name;
        mandatory true;
        description
          "instance name or all";
      }
      leaf vrf-all {
        type vrf-name;
        mandatory true;
        description
          "VRF name or all";
      }
      leaf ip-prefix {
        type inet:ip-prefix;
        mandatory true;
        description
          "Network and masklength";
      }
    }
    csc:xr-task "bgp";
    csc:cli-command "clear bgp instance <instance-name> bestpath vrf <vrf-all> <ip-prefix>";
  }
  rpc clear-bgp-instance-bestpath-vrf-afi-safi-ipv4-prefix {
    description
      "Choose a particular BGP instance.
       re-run BGP bestpath selection.
       Specify a VRF.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
      leaf ipv4-prefix {
        type inet:ipv4-prefix;
        mandatory true;
        description
          "Fspec IPv4 Prefix";
      }
    }
    csc:xr-task "bgp";
    csc:cli-command "clear bgp instance <instance-name> bestpath vrf <vrf-all> <afi-safi-name> <ipv4-prefix>";
  }
  rpc clear-bgp-instance-bestpath-vrf-afi-safi-ipv4-addr-ipv4-mask {
    description
      "Choose a particular BGP instance.
       re-run BGP bestpath selection.
       Specify a VRF.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
      leaf ipv4-addr {
        type inet:ipv4-address;
        mandatory true;
        description
          "IPv4 network";
      }
      leaf ipv4-mask {
        type ipv4-netmask;
        mandatory true;
        description
          "IPv4 mask";
      }
    }
    csc:xr-task "bgp";
    csc:cli-command "clear bgp instance <instance-name> bestpath vrf <vrf-all> <afi-safi-name> <ipv4-addr> <ipv4-mask>";
  }
  rpc clear-bgp-instance-bestpath-vrf-afi-safi-ipv4-addr {
    description
      "Choose a particular BGP instance.
       re-run BGP bestpath selection.
       Specify a VRF.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
      leaf ipv4-addr {
        type inet:ipv4-address;
        mandatory true;
        description
          "IPv4 network";
      }
    }
    csc:xr-task "bgp";
    csc:cli-command "clear bgp instance <instance-name> bestpath vrf <vrf-all> <afi-safi-name> <ipv4-addr>";
  }
  rpc clear-bgp-instance-bestpath-vrf-afi-safi-network {
    description
      "Choose a particular BGP instance.
       re-run BGP bestpath selection.
       Specify a VRF.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
      leaf network {
        type string;
        mandatory true;
        description
          "Address family modifier specific network";
      }
    }
    csc:xr-task "bgp";
    csc:cli-command "clear bgp instance <instance-name> bestpath vrf <vrf-all> <afi-safi-name> <network>";
  }
  rpc clear-bgp-instance-bestpath-vrf-afi-safi-rd-network {
    description
      "Choose a particular BGP instance.
       re-run BGP bestpath selection.
       Specify a VRF.
       Display routes with a specific route distinguisher.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
      leaf rd {
        type rd;
        mandatory true;
        description
          "Route distinguisher";
      }
      leaf network {
        type string;
        mandatory true;
        description
          "Address family modifier specific network";
      }
    }
    csc:xr-task "bgp";
    csc:cli-command "clear bgp instance <instance-name> bestpath vrf <vrf-all> <afi-safi-name> rd <rd> <network>";
  }
  rpc clear-bgp-instance-bestpath-vrf-afi-safi-vrf-network {
    description
      "Choose a particular BGP instance.
       re-run BGP bestpath selection.
       Specify a VRF.
       Display routes for a specified VRF.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
      leaf vrf-name {
        type string;
        mandatory true;
        description
          "VRF name";
      }
      leaf network {
        type string;
        mandatory true;
        description
          "Address family modifier specific network";
      }
    }
    csc:xr-task "bgp";
    csc:cli-command "clear bgp instance <instance-name> bestpath vrf <vrf-all> <afi-safi-name> vrf <vrf-name> <network>";
  }
  rpc clear-bgp-instance-bestpath-vrf-afi-safi-ipv6-addr-ipv6-netmask {
    description
      "Choose a particular BGP instance.
       re-run BGP bestpath selection.
       Specify a VRF.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
      leaf ipv6-addr {
        type inet:ipv6-address;
        mandatory true;
        description
          "IPv6 network";
      }
      leaf ipv6-netmask {
        type ipv6-netmask;
        mandatory true;
        description
          "IPv6 mask";
      }
    }
    csc:xr-task "bgp";
    csc:cli-command "clear bgp instance <instance-name> bestpath vrf <vrf-all> <afi-safi-name> <ipv6-addr> <ipv6-netmask>";
  }
  rpc clear-bgp-instance-bestpath-vrf-afi-safi-ipv6-addr {
    description
      "Choose a particular BGP instance.
       re-run BGP bestpath selection.
       Specify a VRF.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
      leaf ipv6-addr {
        type inet:ipv6-address;
        mandatory true;
        description
          "IPv6 network";
      }
    }
    csc:xr-task "bgp";
    csc:cli-command "clear bgp instance <instance-name> bestpath vrf <vrf-all> <afi-safi-name> <ipv6-addr>";
  }
  rpc clear-bgp-instance-bestpath-vrf-afi-safi-ipv6-prefix {
    description
      "Choose a particular BGP instance.
       re-run BGP bestpath selection.
       Specify a VRF.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
      leaf ipv6-prefix {
        type inet:ipv6-prefix;
        mandatory true;
        description
          "IPv6 network and masklength";
      }
    }
    csc:xr-task "bgp";
    csc:cli-command "clear bgp instance <instance-name> bestpath vrf <vrf-all> <afi-safi-name> <ipv6-prefix>";
  }
  rpc clear-bgp-instance-bestpath-vrf-afi-safi-rd {
    description
      "Choose a particular BGP instance.
       re-run BGP bestpath selection.
       Specify a VRF.
       Display routes with a specific route distinguisher.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
      leaf rd {
        type rd;
        mandatory true;
        description
          "Route distinguisher";
      }
    }
    csc:xr-task "bgp";
    csc:cli-command "clear bgp instance <instance-name> bestpath vrf <vrf-all> <afi-safi-name> rd <rd>";
  }
  rpc clear-bgp-instance-bestpath-vrf-afi-safi-vrf {
    description
      "Choose a particular BGP instance.
       re-run BGP bestpath selection.
       Specify a VRF.
       Display routes for a specified VRF.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
      leaf vrf-name {
        type string;
        mandatory true;
        description
          "VRF name";
      }
    }
    csc:xr-task "bgp";
    csc:cli-command "clear bgp instance <instance-name> bestpath vrf <vrf-all> <afi-safi-name> vrf <vrf-name>";
  }
  rpc clear-bgp-instance-bestpath-vrf-afi-safi {
    description
      "Choose a particular BGP instance.
       re-run BGP bestpath selection.
       Specify a VRF.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
    }
    csc:xr-task "bgp";
    csc:cli-command "clear bgp instance <instance-name> bestpath vrf <vrf-all> <afi-safi-name>";
  }
  rpc clear-bgp-instance-external-graceful {
    description
      "Choose a particular BGP instance.
       Clear all external peers.
       Clear with a hard reset and a graceful restart.
      ";
    input {
      leaf instance-name {
        type instance-name;
        mandatory true;
        description
          "instance name or all";
      }
    }
    csc:xr-task "bgp";
    csc:cli-command "clear bgp instance <instance-name> external graceful";
  }
  rpc clear-bgp-instance-external {
    description
      "Choose a particular BGP instance.
       Clear all external peers.
      ";
    input {
      leaf instance-name {
        type instance-name;
        mandatory true;
        description
          "instance name or all";
      }
    }
    csc:xr-task "bgp";
    csc:cli-command "clear bgp instance <instance-name> external";
  }
  rpc clear-bgp-instance-afi-safi-dampening-ipv4-prefix {
    description
      "Choose a particular BGP instance.
       Clear route flap dampening information.
      ";
    input {
      leaf instance-name {
        type instance-name;
        mandatory true;
        description
          "instance name or all";
      }
      leaf afi-safi-name {
        type afi-safi-type;
        mandatory true;
        description
          "AFI and SAFI";
      }
      leaf ipv4-prefix {
        type inet:ipv4-prefix;
        mandatory true;
        description
          "IPv4 Network and mask or masklength to clear dampening information";
      }
    }
    csc:xr-task "bgp";
    csc:cli-command "clear bgp instance <instance-name> <afi-safi-name> dampening <ipv4-prefix>";
  }
  rpc clear-bgp-instance-afi-safi-flap-statistics-ipv4-prefix {
    description
      "Choose a particular BGP instance.
       Clear flap statistics.
      ";
    input {
      leaf instance-name {
        type instance-name;
        mandatory true;
        description
          "instance name or all";
      }
      leaf afi-safi-name {
        type afi-safi-type;
        mandatory true;
        description
          "AFI and SAFI";
      }
      leaf ipv4-prefix {
        type inet:ipv4-prefix;
        mandatory true;
        description
          "IPv4 Network and mask or masklength to clear flap statistics";
      }
    }
    csc:xr-task "bgp";
    csc:cli-command "clear bgp instance <instance-name> <afi-safi-name> flap-statistics <ipv4-prefix>";
  }
  rpc clear-bgp-instance-afi-safi-dampening-ipv6-prefix {
    description
      "Choose a particular BGP instance.
       Clear route flap dampening information.
      ";
    input {
      leaf instance-name {
        type instance-name;
        mandatory true;
        description
          "instance name or all";
      }
      leaf afi-safi-name {
        type afi-safi-type;
        mandatory true;
        description
          "AFI and SAFI";
      }
      leaf ipv6-prefix {
        type inet:ipv6-prefix;
        mandatory true;
        description
          "IPv6 Network and mask or masklength to clear dampening information";
      }
    }
    csc:xr-task "bgp";
    csc:cli-command "clear bgp instance <instance-name> <afi-safi-name> dampening <ipv6-prefix>";
  }
  rpc clear-bgp-instance-afi-safi-flap-statistics-ipv6-prefix {
    description
      "Choose a particular BGP instance.
       Clear flap statistics.
      ";
    input {
      leaf instance-name {
        type instance-name;
        mandatory true;
        description
          "instance name or all";
      }
      leaf afi-safi-name {
        type afi-safi-type;
        mandatory true;
        description
          "AFI and SAFI";
      }
      leaf ipv6-prefix {
        type inet:ipv6-prefix;
        mandatory true;
        description
          "IPv6 Network and mask or masklength to clear flap statistics";
      }
    }
    csc:xr-task "bgp";
    csc:cli-command "clear bgp instance <instance-name> <afi-safi-name> flap-statistics <ipv6-prefix>";
  }
  rpc clear-bgp-instance-nexthop-performance-statistics {
    description
      "Choose a particular BGP instance.
       Clear nexthop.
       Performance statistics information related to processing.
      ";
    input {
      leaf instance-name {
        type instance-name;
        mandatory true;
        description
          "instance name or all";
      }
    }
    csc:xr-task "bgp";
    csc:cli-command "clear bgp instance <instance-name> nexthop performance-statistics";
  }
  rpc clear-bgp-instance-nexthop-registration-ip-addr {
    description
      "Choose a particular BGP instance.
       Clear nexthop.
       Registration with RIB and reregister.
      ";
    input {
      leaf instance-name {
        type instance-name;
        mandatory true;
        description
          "instance name or all";
      }
      leaf ip-addr {
        type inet:ip-address;
        mandatory true;
        description
          "Nexthop address";
      }
    }
    csc:xr-task "bgp";
    csc:cli-command "clear bgp instance <instance-name> nexthop registration <ip-addr>";
  }
  rpc clear-bgp-instance-peer-drops-all {
    description
      "Choose a particular BGP instance.
       Clear established/dropped counters for a peer.
       All Neighbors.
      ";
    input {
      leaf instance-name {
        type instance-name;
        mandatory true;
        description
          "instance name or all";
      }
    }
    csc:xr-task "bgp";
    csc:cli-command "clear bgp instance <instance-name> peer-drops *";
  }
  rpc clear-bgp-instance-peer-drops-ip-addr {
    description
      "Choose a particular BGP instance.
       Clear established/dropped counters for a peer.
      ";
    input {
      leaf instance-name {
        type instance-name;
        mandatory true;
        description
          "instance name or all";
      }
      leaf ip-addr {
        type inet:ip-address;
        mandatory true;
        description
          "BGP neighbor IP address";
      }
    }
    csc:xr-task "bgp";
    csc:cli-command "clear bgp instance <instance-name> peer-drops <ip-addr>";
  }
  rpc clear-bgp-instance-performance-statistics {
    description
      "Choose a particular BGP instance.
       Clear performance statistics.
      ";
    input {
      leaf instance-name {
        type instance-name;
        mandatory true;
        description
          "instance name or all";
      }
    }
    csc:xr-task "bgp";
    csc:cli-command "clear bgp instance <instance-name> performance-statistics";
  }
  rpc clear-bgp-instance-rpki-server-all-serial-query {
    description
      "Choose a particular BGP instance.
       RPKI clear command.
       clear RPKI cache-server.
       clear all RPKI cache-servers.
       send serial-queries to all cache-servers (with latest serial numbers).
      ";
    input {
      leaf instance-name {
        type instance-name;
        mandatory true;
        description
          "instance name or all";
      }
    }
    csc:xr-task "bgp";
    csc:cli-command "clear bgp instance <instance-name> rpki server * serial-query";
  }
  rpc clear-bgp-instance-rpki-server-all {
    description
      "Choose a particular BGP instance.
       RPKI clear command.
       clear RPKI cache-server.
       clear all RPKI cache-servers.
      ";
    input {
      leaf instance-name {
        type instance-name;
        mandatory true;
        description
          "instance name or all";
      }
    }
    csc:xr-task "bgp";
    csc:cli-command "clear bgp instance <instance-name> rpki server *";
  }
  rpc clear-bgp-instance-rpki-server-rpki-server {
    description
      "Choose a particular BGP instance.
       RPKI clear command.
       clear RPKI cache-server.
      ";
    input {
      leaf instance-name {
        type instance-name;
        mandatory true;
        description
          "instance name or all";
      }
      leaf rpki-server {
        type string;
        mandatory true;
        description
          "clear a specific RPKI cache-server (hostname or IP address)";
      }
    }
    csc:xr-task "bgp";
    csc:cli-command "clear bgp instance <instance-name> rpki server <rpki-server>";
  }
  rpc clear-bgp-instance-rpki-validation-ipv4 {
    description
      "Choose a particular BGP instance.
       RPKI clear command.
       clear RPKI origin-validation (trigger origin validation).
       trigger origin validation walk for the IPv4 table.
      ";
    input {
      leaf instance-name {
        type instance-name;
        mandatory true;
        description
          "instance name or all";
      }
    }
    csc:xr-task "bgp";
    csc:cli-command "clear bgp instance <instance-name> rpki validation ipv4";
  }
  rpc clear-bgp-instance-rpki-validation-ipv6 {
    description
      "Choose a particular BGP instance.
       RPKI clear command.
       clear RPKI origin-validation (trigger origin validation).
       trigger origin validation walk for the IPv6 table.
      ";
    input {
      leaf instance-name {
        type instance-name;
        mandatory true;
        description
          "instance name or all";
      }
    }
    csc:xr-task "bgp";
    csc:cli-command "clear bgp instance <instance-name> rpki validation ipv6";
  }
  rpc clear-bgp-instance-rpki-validation {
    description
      "Choose a particular BGP instance.
       RPKI clear command.
       clear RPKI origin-validation (trigger origin validation).
      ";
    input {
      leaf instance-name {
        type instance-name;
        mandatory true;
        description
          "instance name or all";
      }
    }
    csc:xr-task "bgp";
    csc:cli-command "clear bgp instance <instance-name> rpki validation";
  }
  rpc clear-bgp-instance-shutdown {
    description
      "Choose a particular BGP instance.
       Clear all peers which were shut down due to low memory.
      ";
    input {
      leaf instance-name {
        type instance-name;
        mandatory true;
        description
          "instance name or all";
      }
    }
    csc:xr-task "bgp";
    csc:cli-command "clear bgp instance <instance-name> shutdown";
  }
  rpc clear-bgp-instance-update-outq-address-family-update-parent {
    description
      "Choose a particular BGP instance.
       Clear Update information (Do NOT execute without cisco support)(cisco-support).
       Clear Update generation OutQ counters (Do NOT execute without cisco support)(cisco-support).
       Address-family.
       Update parents' OutQ counters too.
      ";
    input {
      leaf instance-name {
        type instance-name;
        mandatory true;
        description
          "instance name or all";
      }
    }
    csc:xr-task "bgp";
    csc:cli-command "clear bgp instance <instance-name> update outq address-family update-parent";
  }
  rpc clear-bgp-instance-update-outq-address-family {
    description
      "Choose a particular BGP instance.
       Clear Update information (Do NOT execute without cisco support)(cisco-support).
       Clear Update generation OutQ counters (Do NOT execute without cisco support)(cisco-support).
       Address-family.
      ";
    input {
      leaf instance-name {
        type instance-name;
        mandatory true;
        description
          "instance name or all";
      }
    }
    csc:xr-task "bgp";
    csc:cli-command "clear bgp instance <instance-name> update outq address-family";
  }
  rpc clear-bgp-instance-update-outq-neighbor-ip-addr-refresh-update-parent {
    description
      "Choose a particular BGP instance.
       Clear Update information (Do NOT execute without cisco support)(cisco-support).
       Clear Update generation OutQ counters (Do NOT execute without cisco support)(cisco-support).
       Neighbor.
       Refresh OutQ.
       Update parents' OutQ counters too.
      ";
    input {
      leaf instance-name {
        type instance-name;
        mandatory true;
        description
          "instance name or all";
      }
      leaf ip-addr {
        type inet:ip-address;
        mandatory true;
        description
          "Neighbor address";
      }
    }
    csc:xr-task "bgp";
    csc:cli-command "clear bgp instance <instance-name> update outq neighbor <ip-addr> refresh update-parent";
  }
  rpc clear-bgp-instance-update-outq-neighbor-ip-addr-refresh {
    description
      "Choose a particular BGP instance.
       Clear Update information (Do NOT execute without cisco support)(cisco-support).
       Clear Update generation OutQ counters (Do NOT execute without cisco support)(cisco-support).
       Neighbor.
       Refresh OutQ.
      ";
    input {
      leaf instance-name {
        type instance-name;
        mandatory true;
        description
          "instance name or all";
      }
      leaf ip-addr {
        type inet:ip-address;
        mandatory true;
        description
          "Neighbor address";
      }
    }
    csc:xr-task "bgp";
    csc:cli-command "clear bgp instance <instance-name> update outq neighbor <ip-addr> refresh";
  }
  rpc clear-bgp-instance-update-outq-neighbor-ip-addr-update-parent {
    description
      "Choose a particular BGP instance.
       Clear Update information (Do NOT execute without cisco support)(cisco-support).
       Clear Update generation OutQ counters (Do NOT execute without cisco support)(cisco-support).
       Neighbor.
       Update parents' OutQ counters too.
      ";
    input {
      leaf instance-name {
        type instance-name;
        mandatory true;
        description
          "instance name or all";
      }
      leaf ip-addr {
        type inet:ip-address;
        mandatory true;
        description
          "Neighbor address";
      }
    }
    csc:xr-task "bgp";
    csc:cli-command "clear bgp instance <instance-name> update outq neighbor <ip-addr> update-parent";
  }
  rpc clear-bgp-instance-update-outq-neighbor-ip-addr {
    description
      "Choose a particular BGP instance.
       Clear Update information (Do NOT execute without cisco support)(cisco-support).
       Clear Update generation OutQ counters (Do NOT execute without cisco support)(cisco-support).
       Neighbor.
      ";
    input {
      leaf instance-name {
        type instance-name;
        mandatory true;
        description
          "instance name or all";
      }
      leaf ip-addr {
        type inet:ip-address;
        mandatory true;
        description
          "Neighbor address";
      }
    }
    csc:xr-task "bgp";
    csc:cli-command "clear bgp instance <instance-name> update outq neighbor <ip-addr>";
  }
  rpc clear-bgp-instance-update-outq-process {
    description
      "Choose a particular BGP instance.
       Clear Update information (Do NOT execute without cisco support)(cisco-support).
       Clear Update generation OutQ counters (Do NOT execute without cisco support)(cisco-support).
       Process.
      ";
    input {
      leaf instance-name {
        type instance-name;
        mandatory true;
        description
          "instance name or all";
      }
    }
    csc:xr-task "bgp";
    csc:cli-command "clear bgp instance <instance-name> update outq process";
  }
  rpc clear-bgp-instance-update-outq-update-group-sub-group-update-parent {
    description
      "Choose a particular BGP instance.
       Clear Update information (Do NOT execute without cisco support)(cisco-support).
       Clear Update generation OutQ counters (Do NOT execute without cisco support)(cisco-support).
       Update-group.
       Sub-group.
       Update parents' OutQ counters too.
      ";
    input {
      leaf instance-name {
        type instance-name;
        mandatory true;
        description
          "instance name or all";
      }
      leaf update-group {
        type update-group-id;
        mandatory true;
        description
          "Update-group process ID <x.y>";
      }
      leaf sub-group {
        type update-group-id;
        mandatory true;
        description
          "Sub-group process ID <x.y>";
      }
    }
    csc:xr-task "bgp";
    csc:cli-command "clear bgp instance <instance-name> update outq update-group <update-group> sub-group <sub-group> update-parent";
  }
  rpc clear-bgp-instance-update-outq-update-group-sub-group {
    description
      "Choose a particular BGP instance.
       Clear Update information (Do NOT execute without cisco support)(cisco-support).
       Clear Update generation OutQ counters (Do NOT execute without cisco support)(cisco-support).
       Update-group.
       Sub-group.
      ";
    input {
      leaf instance-name {
        type instance-name;
        mandatory true;
        description
          "instance name or all";
      }
      leaf update-group {
        type update-group-id;
        mandatory true;
        description
          "Update-group process ID <x.y>";
      }
      leaf sub-group {
        type update-group-id;
        mandatory true;
        description
          "Sub-group process ID <x.y>";
      }
    }
    csc:xr-task "bgp";
    csc:cli-command "clear bgp instance <instance-name> update outq update-group <update-group> sub-group <sub-group>";
  }
  rpc clear-bgp-instance-update-outq-update-group-sub-group-refresh-sub-group-update-parent {
    description
      "Choose a particular BGP instance.
       Clear Update information (Do NOT execute without cisco support)(cisco-support).
       Clear Update generation OutQ counters (Do NOT execute without cisco support)(cisco-support).
       Update-group.
       Sub-group.
       Update parents' OutQ counters too.
      ";
    input {
      leaf instance-name {
        type instance-name;
        mandatory true;
        description
          "instance name or all";
      }
      leaf update-group {
        type update-group-id;
        mandatory true;
        description
          "Update-group process ID <x.y>";
      }
      leaf refresh-sub-group {
        type refresh-sub-group-id;
        mandatory true;
        description
          "Refresh Sub-group process ID <x.y:z>";
      }
    }
    csc:xr-task "bgp";
    csc:cli-command "clear bgp instance <instance-name> update outq update-group <update-group> sub-group <refresh-sub-group> update-parent";
  }
  rpc clear-bgp-instance-update-outq-update-group-sub-group-refresh-sub-group {
    description
      "Choose a particular BGP instance.
       Clear Update information (Do NOT execute without cisco support)(cisco-support).
       Clear Update generation OutQ counters (Do NOT execute without cisco support)(cisco-support).
       Update-group.
       Sub-group.
      ";
    input {
      leaf instance-name {
        type instance-name;
        mandatory true;
        description
          "instance name or all";
      }
      leaf update-group {
        type update-group-id;
        mandatory true;
        description
          "Update-group process ID <x.y>";
      }
      leaf refresh-sub-group {
        type refresh-sub-group-id;
        mandatory true;
        description
          "Refresh Sub-group process ID <x.y:z>";
      }
    }
    csc:xr-task "bgp";
    csc:cli-command "clear bgp instance <instance-name> update outq update-group <update-group> sub-group <refresh-sub-group>";
  }
  rpc clear-bgp-instance-update-outq-update-group-update-parent {
    description
      "Choose a particular BGP instance.
       Clear Update information (Do NOT execute without cisco support)(cisco-support).
       Clear Update generation OutQ counters (Do NOT execute without cisco support)(cisco-support).
       Update-group.
       Update parents' OutQ counters too.
      ";
    input {
      leaf instance-name {
        type instance-name;
        mandatory true;
        description
          "instance name or all";
      }
      leaf update-group {
        type update-group-id;
        mandatory true;
        description
          "Update-group process ID <x.y>";
      }
    }
    csc:xr-task "bgp";
    csc:cli-command "clear bgp instance <instance-name> update outq update-group <update-group> update-parent";
  }
  rpc clear-bgp-instance-update-outq-update-group {
    description
      "Choose a particular BGP instance.
       Clear Update information (Do NOT execute without cisco support)(cisco-support).
       Clear Update generation OutQ counters (Do NOT execute without cisco support)(cisco-support).
       Update-group.
      ";
    input {
      leaf instance-name {
        type instance-name;
        mandatory true;
        description
          "instance name or all";
      }
      leaf update-group {
        type update-group-id;
        mandatory true;
        description
          "Update-group process ID <x.y>";
      }
    }
    csc:xr-task "bgp";
    csc:cli-command "clear bgp instance <instance-name> update outq update-group <update-group>";
  }
  rpc clear-bgp-instance-version-ip-addr-ip-netmask {
    description
      "Choose a particular BGP instance.
       clear BGP prefix version.
      ";
    input {
      leaf instance-name {
        type instance-name;
        mandatory true;
        description
          "instance name or all";
      }
      leaf ip-addr {
        type inet:ip-address;
        mandatory true;
        description
          "Network";
      }
      leaf ip-netmask {
        type ip-netmask;
        mandatory true;
        description
          "Mask";
      }
    }
    csc:xr-task "bgp";
    csc:cli-command "clear bgp instance <instance-name> version <ip-addr> <ip-netmask>";
  }
  rpc clear-bgp-instance-version-ip-addr {
    description
      "Choose a particular BGP instance.
       clear BGP prefix version.
      ";
    input {
      leaf instance-name {
        type instance-name;
        mandatory true;
        description
          "instance name or all";
      }
      leaf ip-addr {
        type inet:ip-address;
        mandatory true;
        description
          "Network";
      }
    }
    csc:xr-task "bgp";
    csc:cli-command "clear bgp instance <instance-name> version <ip-addr>";
  }
  rpc clear-bgp-instance-version-ip-prefix {
    description
      "Choose a particular BGP instance.
       clear BGP prefix version.
      ";
    input {
      leaf instance-name {
        type instance-name;
        mandatory true;
        description
          "instance name or all";
      }
      leaf ip-prefix {
        type inet:ip-prefix;
        mandatory true;
        description
          "Network and masklength";
      }
    }
    csc:xr-task "bgp";
    csc:cli-command "clear bgp instance <instance-name> version <ip-prefix>";
  }
  rpc clear-bgp-instance-version-afi-safi-ip-addr-ip-netmask {
    description
      "Choose a particular BGP instance.
       clear BGP prefix version.
      ";
    input {
      leaf instance-name {
        type instance-name;
        mandatory true;
        description
          "instance name or all";
      }
      leaf afi-safi-name {
        type afi-safi-type;
        mandatory true;
        description
          "AFI and SAFI";
      }
      leaf ip-addr {
        type inet:ip-address;
        mandatory true;
        description
          "Network";
      }
      leaf ip-netmask {
        type ip-netmask;
        mandatory true;
        description
          "Mask";
      }
    }
    csc:xr-task "bgp";
    csc:cli-command "clear bgp instance <instance-name> version <afi-safi-name> <ip-addr> <ip-netmask>";
  }
  rpc clear-bgp-instance-version-afi-safi-ip-addr {
    description
      "Choose a particular BGP instance.
       clear BGP prefix version.
      ";
    input {
      leaf instance-name {
        type instance-name;
        mandatory true;
        description
          "instance name or all";
      }
      leaf afi-safi-name {
        type afi-safi-type;
        mandatory true;
        description
          "AFI and SAFI";
      }
      leaf ip-addr {
        type inet:ip-address;
        mandatory true;
        description
          "Network";
      }
    }
    csc:xr-task "bgp";
    csc:cli-command "clear bgp instance <instance-name> version <afi-safi-name> <ip-addr>";
  }
  rpc clear-bgp-instance-version-afi-safi-ip-prefix {
    description
      "Choose a particular BGP instance.
       clear BGP prefix version.
      ";
    input {
      leaf instance-name {
        type instance-name;
        mandatory true;
        description
          "instance name or all";
      }
      leaf afi-safi-name {
        type afi-safi-type;
        mandatory true;
        description
          "AFI and SAFI";
      }
      leaf ip-prefix {
        type inet:ip-prefix;
        mandatory true;
        description
          "Network and masklength";
      }
    }
    csc:xr-task "bgp";
    csc:cli-command "clear bgp instance <instance-name> version <afi-safi-name> <ip-prefix>";
  }
  rpc clear-bgp-instance-version-afi-safi-bridge-domain-ip-addr-ip-netmask {
    description
      "Choose a particular BGP instance.
       clear BGP prefix version.
       Display routes for a specified Bridge Domain.
      ";
    input {
      leaf instance-name {
        type instance-name;
        mandatory true;
        description
          "instance name or all";
      }
      leaf afi-safi-name {
        type afi-safi-type;
        mandatory true;
        description
          "AFI and SAFI";
      }
      leaf bridge-domain-name {
        type string;
        mandatory true;
        description
          "Bridge Domain";
      }
      leaf ip-addr {
        type inet:ip-address;
        mandatory true;
        description
          "Network";
      }
      leaf ip-netmask {
        type ip-netmask;
        mandatory true;
        description
          "Mask";
      }
    }
    csc:xr-task "bgp";
    csc:cli-command "clear bgp instance <instance-name> version <afi-safi-name> bridge-domain <bridge-domain-name> <ip-addr> <ip-netmask>";
  }
  rpc clear-bgp-instance-version-afi-safi-bridge-domain-ip-addr {
    description
      "Choose a particular BGP instance.
       clear BGP prefix version.
       Display routes for a specified Bridge Domain.
      ";
    input {
      leaf instance-name {
        type instance-name;
        mandatory true;
        description
          "instance name or all";
      }
      leaf afi-safi-name {
        type afi-safi-type;
        mandatory true;
        description
          "AFI and SAFI";
      }
      leaf bridge-domain-name {
        type string;
        mandatory true;
        description
          "Bridge Domain";
      }
      leaf ip-addr {
        type inet:ip-address;
        mandatory true;
        description
          "Network";
      }
    }
    csc:xr-task "bgp";
    csc:cli-command "clear bgp instance <instance-name> version <afi-safi-name> bridge-domain <bridge-domain-name> <ip-addr>";
  }
  rpc clear-bgp-instance-version-afi-safi-bridge-domain-ip-prefix {
    description
      "Choose a particular BGP instance.
       clear BGP prefix version.
       Display routes for a specified Bridge Domain.
      ";
    input {
      leaf instance-name {
        type instance-name;
        mandatory true;
        description
          "instance name or all";
      }
      leaf afi-safi-name {
        type afi-safi-type;
        mandatory true;
        description
          "AFI and SAFI";
      }
      leaf bridge-domain-name {
        type string;
        mandatory true;
        description
          "Bridge Domain";
      }
      leaf ip-prefix {
        type inet:ip-prefix;
        mandatory true;
        description
          "Network and masklength";
      }
    }
    csc:xr-task "bgp";
    csc:cli-command "clear bgp instance <instance-name> version <afi-safi-name> bridge-domain <bridge-domain-name> <ip-prefix>";
  }
  rpc clear-bgp-instance-version-afi-safi-rd-ip-addr-ip-netmask {
    description
      "Choose a particular BGP instance.
       clear BGP prefix version.
       Display routes with a specific route distinguisher.
      ";
    input {
      leaf instance-name {
        type instance-name;
        mandatory true;
        description
          "instance name or all";
      }
      leaf afi-safi-name {
        type afi-safi-type;
        mandatory true;
        description
          "AFI and SAFI";
      }
      leaf rd {
        type rd;
        mandatory true;
        description
          "Route distinguisher";
      }
      leaf ip-addr {
        type inet:ip-address;
        mandatory true;
        description
          "Network";
      }
      leaf ip-netmask {
        type ip-netmask;
        mandatory true;
        description
          "Mask";
      }
    }
    csc:xr-task "bgp";
    csc:cli-command "clear bgp instance <instance-name> version <afi-safi-name> rd <rd> <ip-addr> <ip-netmask>";
  }
  rpc clear-bgp-instance-version-afi-safi-rd-ip-addr {
    description
      "Choose a particular BGP instance.
       clear BGP prefix version.
       Display routes with a specific route distinguisher.
      ";
    input {
      leaf instance-name {
        type instance-name;
        mandatory true;
        description
          "instance name or all";
      }
      leaf afi-safi-name {
        type afi-safi-type;
        mandatory true;
        description
          "AFI and SAFI";
      }
      leaf rd {
        type rd;
        mandatory true;
        description
          "Route distinguisher";
      }
      leaf ip-addr {
        type inet:ip-address;
        mandatory true;
        description
          "Network";
      }
    }
    csc:xr-task "bgp";
    csc:cli-command "clear bgp instance <instance-name> version <afi-safi-name> rd <rd> <ip-addr>";
  }
  rpc clear-bgp-instance-version-afi-safi-rd-ip-prefix {
    description
      "Choose a particular BGP instance.
       clear BGP prefix version.
       Display routes with a specific route distinguisher.
      ";
    input {
      leaf instance-name {
        type instance-name;
        mandatory true;
        description
          "instance name or all";
      }
      leaf afi-safi-name {
        type afi-safi-type;
        mandatory true;
        description
          "AFI and SAFI";
      }
      leaf rd {
        type rd;
        mandatory true;
        description
          "Route distinguisher";
      }
      leaf ip-prefix {
        type inet:ip-prefix;
        mandatory true;
        description
          "Network and masklength";
      }
    }
    csc:xr-task "bgp";
    csc:cli-command "clear bgp instance <instance-name> version <afi-safi-name> rd <rd> <ip-prefix>";
  }
  rpc clear-bgp-instance-version-afi-safi-ipv4-addr-ipv4-mask {
    description
      "Choose a particular BGP instance.
       clear BGP prefix version.
      ";
    input {
      leaf instance-name {
        type instance-name;
        mandatory true;
        description
          "instance name or all";
      }
      leaf afi-safi-name {
        type afi-safi-type;
        mandatory true;
        description
          "AFI and SAFI";
      }
      leaf ipv4-addr {
        type inet:ipv4-address;
        mandatory true;
        description
          "IPv4 network";
      }
      leaf ipv4-mask {
        type ipv4-netmask;
        mandatory true;
        description
          "IPv4 mask";
      }
    }
    csc:xr-task "bgp";
    csc:cli-command "clear bgp instance <instance-name> version <afi-safi-name> <ipv4-addr> <ipv4-mask>";
  }
  rpc clear-bgp-instance-version-afi-safi-ipv4-addr {
    description
      "Choose a particular BGP instance.
       clear BGP prefix version.
      ";
    input {
      leaf instance-name {
        type instance-name;
        mandatory true;
        description
          "instance name or all";
      }
      leaf afi-safi-name {
        type afi-safi-type;
        mandatory true;
        description
          "AFI and SAFI";
      }
      leaf ipv4-addr {
        type inet:ipv4-address;
        mandatory true;
        description
          "IPv4 network";
      }
    }
    csc:xr-task "bgp";
    csc:cli-command "clear bgp instance <instance-name> version <afi-safi-name> <ipv4-addr>";
  }
  rpc clear-bgp-instance-version-afi-safi-ipv4-prefix {
    description
      "Choose a particular BGP instance.
       clear BGP prefix version.
      ";
    input {
      leaf instance-name {
        type instance-name;
        mandatory true;
        description
          "instance name or all";
      }
      leaf afi-safi-name {
        type afi-safi-type;
        mandatory true;
        description
          "AFI and SAFI";
      }
      leaf ipv4-prefix {
        type inet:ipv4-prefix;
        mandatory true;
        description
          "IPv4 network and masklength";
      }
    }
    csc:xr-task "bgp";
    csc:cli-command "clear bgp instance <instance-name> version <afi-safi-name> <ipv4-prefix>";
  }
  rpc clear-bgp-instance-version-afi-safi-rd-ipv4-addr {
    description
      "Choose a particular BGP instance.
       clear BGP prefix version.
       Display routes with a specific route distinguisher.
      ";
    input {
      leaf instance-name {
        type instance-name;
        mandatory true;
        description
          "instance name or all";
      }
      leaf afi-safi-name {
        type afi-safi-type;
        mandatory true;
        description
          "AFI and SAFI";
      }
      leaf rd {
        type rd;
        mandatory true;
        description
          "Route distinguisher";
      }
      leaf ipv4-addr {
        type inet:ipv4-address;
        mandatory true;
        description
          "IPv4 MDT network";
      }
    }
    csc:xr-task "bgp";
    csc:cli-command "clear bgp instance <instance-name> version <afi-safi-name> rd <rd> <ipv4-addr>";
  }
  rpc clear-bgp-instance-version-afi-safi-vrf-ipv4-addr {
    description
      "Choose a particular BGP instance.
       clear BGP prefix version.
       Display routes for a specified VRF.
      ";
    input {
      leaf instance-name {
        type instance-name;
        mandatory true;
        description
          "instance name or all";
      }
      leaf afi-safi-name {
        type afi-safi-type;
        mandatory true;
        description
          "AFI and SAFI";
      }
      leaf vrf-name {
        type string;
        mandatory true;
        description
          "VRF name";
      }
      leaf ipv4-addr {
        type inet:ipv4-address;
        mandatory true;
        description
          "IPv4 MDT network";
      }
    }
    csc:xr-task "bgp";
    csc:cli-command "clear bgp instance <instance-name> version <afi-safi-name> vrf <vrf-name> <ipv4-addr>";
  }
  rpc clear-bgp-instance-version-afi-safi-network {
    description
      "Choose a particular BGP instance.
       clear BGP prefix version.
      ";
    input {
      leaf instance-name {
        type instance-name;
        mandatory true;
        description
          "instance name or all";
      }
      leaf afi-safi-name {
        type afi-safi-type;
        mandatory true;
        description
          "AFI and SAFI";
      }
      leaf network {
        type string;
        mandatory true;
        description
          "Address family modifier specific network";
      }
    }
    csc:xr-task "bgp";
    csc:cli-command "clear bgp instance <instance-name> version <afi-safi-name> <network>";
  }
  rpc clear-bgp-instance-version-afi-safi-rd-network {
    description
      "Choose a particular BGP instance.
       clear BGP prefix version.
       Display routes with a specific route distinguisher.
      ";
    input {
      leaf instance-name {
        type instance-name;
        mandatory true;
        description
          "instance name or all";
      }
      leaf afi-safi-name {
        type afi-safi-type;
        mandatory true;
        description
          "AFI and SAFI";
      }
      leaf rd {
        type rd;
        mandatory true;
        description
          "Route distinguisher";
      }
      leaf network {
        type string;
        mandatory true;
        description
          "Address family modifier specific network";
      }
    }
    csc:xr-task "bgp";
    csc:cli-command "clear bgp instance <instance-name> version <afi-safi-name> rd <rd> <network>";
  }
  rpc clear-bgp-instance-version-afi-safi-vrf-network {
    description
      "Choose a particular BGP instance.
       clear BGP prefix version.
       Display routes for a specified VRF.
      ";
    input {
      leaf instance-name {
        type instance-name;
        mandatory true;
        description
          "instance name or all";
      }
      leaf afi-safi-name {
        type afi-safi-type;
        mandatory true;
        description
          "AFI and SAFI";
      }
      leaf vrf-name {
        type string;
        mandatory true;
        description
          "VRF name";
      }
      leaf network {
        type string;
        mandatory true;
        description
          "Address family modifier specific network";
      }
    }
    csc:xr-task "bgp";
    csc:cli-command "clear bgp instance <instance-name> version <afi-safi-name> vrf <vrf-name> <network>";
  }
  rpc clear-bgp-instance-version-afi-safi-rt-constraint-network {
    description
      "Choose a particular BGP instance.
       clear BGP prefix version.
      ";
    input {
      leaf instance-name {
        type instance-name;
        mandatory true;
        description
          "instance name or all";
      }
      leaf afi-safi-name {
        type afi-safi-type;
        mandatory true;
        description
          "AFI and SAFI";
      }
      leaf rt-constraint-network {
        type string;
        mandatory true;
        description
          "RT-Constraint network";
      }
    }
    csc:xr-task "bgp";
    csc:cli-command "clear bgp instance <instance-name> version <afi-safi-name> <rt-constraint-network>";
  }
  rpc clear-bgp-instance-version-afi-safi-ipv4-tunnel-network {
    description
      "Choose a particular BGP instance.
       clear BGP prefix version.
      ";
    input {
      leaf instance-name {
        type instance-name;
        mandatory true;
        description
          "instance name or all";
      }
      leaf afi-safi-name {
        type afi-safi-type;
        mandatory true;
        description
          "AFI and SAFI";
      }
      leaf ipv4-tunnel-network {
        type string;
        mandatory true;
        description
          "IPv4 Tunnel network <Tunnel-ID>:<IPv4 Address>";
      }
    }
    csc:xr-task "bgp";
    csc:cli-command "clear bgp instance <instance-name> version <afi-safi-name> <ipv4-tunnel-network>";
  }
  rpc clear-bgp-instance-version-afi-safi-ipv6-addr-ipv6-netmask {
    description
      "Choose a particular BGP instance.
       clear BGP prefix version.
      ";
    input {
      leaf instance-name {
        type instance-name;
        mandatory true;
        description
          "instance name or all";
      }
      leaf afi-safi-name {
        type afi-safi-type;
        mandatory true;
        description
          "AFI and SAFI";
      }
      leaf ipv6-addr {
        type inet:ipv6-address;
        mandatory true;
        description
          "IPv6 network";
      }
      leaf ipv6-netmask {
        type ipv6-netmask;
        mandatory true;
        description
          "IPv6 mask";
      }
    }
    csc:xr-task "bgp";
    csc:cli-command "clear bgp instance <instance-name> version <afi-safi-name> <ipv6-addr> <ipv6-netmask>";
  }
  rpc clear-bgp-instance-version-afi-safi-ipv6-addr {
    description
      "Choose a particular BGP instance.
       clear BGP prefix version.
      ";
    input {
      leaf instance-name {
        type instance-name;
        mandatory true;
        description
          "instance name or all";
      }
      leaf afi-safi-name {
        type afi-safi-type;
        mandatory true;
        description
          "AFI and SAFI";
      }
      leaf ipv6-addr {
        type inet:ipv6-address;
        mandatory true;
        description
          "IPv6 network";
      }
    }
    csc:xr-task "bgp";
    csc:cli-command "clear bgp instance <instance-name> version <afi-safi-name> <ipv6-addr>";
  }
  rpc clear-bgp-instance-version-afi-safi-ipv6-prefix {
    description
      "Choose a particular BGP instance.
       clear BGP prefix version.
      ";
    input {
      leaf instance-name {
        type instance-name;
        mandatory true;
        description
          "instance name or all";
      }
      leaf afi-safi-name {
        type afi-safi-type;
        mandatory true;
        description
          "AFI and SAFI";
      }
      leaf ipv6-prefix {
        type inet:ipv6-prefix;
        mandatory true;
        description
          "IPv6 network and masklength";
      }
    }
    csc:xr-task "bgp";
    csc:cli-command "clear bgp instance <instance-name> version <afi-safi-name> <ipv6-prefix>";
  }
  rpc clear-bgp-instance-version-afi-safi-rd {
    description
      "Choose a particular BGP instance.
       clear BGP prefix version.
       Display routes with a specific route distinguisher.
      ";
    input {
      leaf instance-name {
        type instance-name;
        mandatory true;
        description
          "instance name or all";
      }
      leaf afi-safi-name {
        type afi-safi-type;
        mandatory true;
        description
          "AFI and SAFI";
      }
      leaf rd {
        type rd;
        mandatory true;
        description
          "Route distinguisher";
      }
    }
    csc:xr-task "bgp";
    csc:cli-command "clear bgp instance <instance-name> version <afi-safi-name> rd <rd>";
  }
  rpc clear-bgp-instance-version-afi-safi-vrf {
    description
      "Choose a particular BGP instance.
       clear BGP prefix version.
       Display routes for a specified VRF.
      ";
    input {
      leaf instance-name {
        type instance-name;
        mandatory true;
        description
          "instance name or all";
      }
      leaf afi-safi-name {
        type afi-safi-type;
        mandatory true;
        description
          "AFI and SAFI";
      }
      leaf vrf-name {
        type string;
        mandatory true;
        description
          "VRF name";
      }
    }
    csc:xr-task "bgp";
    csc:cli-command "clear bgp instance <instance-name> version <afi-safi-name> vrf <vrf-name>";
  }
  rpc clear-bgp-instance-version-afi-safi {
    description
      "Choose a particular BGP instance.
       clear BGP prefix version.
      ";
    input {
      leaf instance-name {
        type instance-name;
        mandatory true;
        description
          "instance name or all";
      }
      leaf afi-safi-name {
        type afi-safi-type;
        mandatory true;
        description
          "AFI and SAFI";
      }
    }
    csc:xr-task "bgp";
    csc:cli-command "clear bgp instance <instance-name> version <afi-safi-name>";
  }
  rpc clear-bgp-instance-version-afi-safi-sr-policy-prefix {
    description
      "Choose a particular BGP instance.
       clear BGP prefix version.
      ";
    input {
      leaf instance-name {
        type instance-name;
        mandatory true;
        description
          "instance name or all";
      }
      leaf afi-safi-name {
        type afi-safi-type;
        mandatory true;
        description
          "AFI and SAFI";
      }
      leaf sr-policy-prefix {
        type string;
        mandatory true;
        description
          "SR Policy prefix";
      }
    }
    csc:xr-task "bgp";
    csc:cli-command "clear bgp instance <instance-name> version <afi-safi-name> <sr-policy-prefix>";
  }
  rpc clear-bgp-instance-version-afi-safi-bridge-domain-ipv4-prefix {
    description
      "Choose a particular BGP instance.
       clear BGP prefix version.
       Display routes for a specified Bridge Domain.
      ";
    input {
      leaf instance-name {
        type instance-name;
        mandatory true;
        description
          "instance name or all";
      }
      leaf afi-safi-name {
        type afi-safi-type;
        mandatory true;
        description
          "AFI and SAFI";
      }
      leaf bridge-domain-name {
        type string;
        mandatory true;
        description
          "Bridge Domain";
      }
      leaf ipv4-prefix {
        type inet:ipv4-prefix;
        mandatory true;
        description
          "L2VPN EVPN Prefix";
      }
    }
    csc:xr-task "bgp";
    csc:cli-command "clear bgp instance <instance-name> version <afi-safi-name> bridge-domain <bridge-domain-name> <ipv4-prefix>";
  }
  rpc clear-bgp-instance-version-afi-safi-rd-ipv4-prefix {
    description
      "Choose a particular BGP instance.
       clear BGP prefix version.
       Display routes with a specific route distinguisher.
      ";
    input {
      leaf instance-name {
        type instance-name;
        mandatory true;
        description
          "instance name or all";
      }
      leaf afi-safi-name {
        type afi-safi-type;
        mandatory true;
        description
          "AFI and SAFI";
      }
      leaf rd {
        type rd;
        mandatory true;
        description
          "Route distinguisher";
      }
      leaf ipv4-prefix {
        type inet:ipv4-prefix;
        mandatory true;
        description
          "L2VPN EVPN Prefix";
      }
    }
    csc:xr-task "bgp";
    csc:cli-command "clear bgp instance <instance-name> version <afi-safi-name> rd <rd> <ipv4-prefix>";
  }
  rpc clear-bgp-instance-version-afi-safi-mp2mp-ipv4-prefix {
    description
      "Choose a particular BGP instance.
       clear BGP prefix version.
       Display routes for a specified Xconnect group:MP2MP.
      ";
    input {
      leaf instance-name {
        type instance-name;
        mandatory true;
        description
          "instance name or all";
      }
      leaf afi-safi-name {
        type afi-safi-type;
        mandatory true;
        description
          "AFI and SAFI";
      }
      leaf mp2mp {
        type string;
        mandatory true;
        description
          "Xconnect Group:mp2mp";
      }
      leaf ipv4-prefix {
        type inet:ipv4-prefix;
        mandatory true;
        description
          "L2VPN VPWS Prefix";
      }
    }
    csc:xr-task "bgp";
    csc:cli-command "clear bgp instance <instance-name> version <afi-safi-name> mp2mp <mp2mp> <ipv4-prefix>";
  }
  rpc clear-bgp-instance-version-afi-safi-vrf-ipv4-prefix {
    description
      "Choose a particular BGP instance.
       clear BGP prefix version.
       Display routes for a specified VRF.
      ";
    input {
      leaf instance-name {
        type instance-name;
        mandatory true;
        description
          "instance name or all";
      }
      leaf afi-safi-name {
        type afi-safi-type;
        mandatory true;
        description
          "AFI and SAFI";
      }
      leaf vrf-name {
        type string;
        mandatory true;
        description
          "VRF name";
      }
      leaf ipv4-prefix {
        type inet:ipv4-prefix;
        mandatory true;
        description
          "VPN Fspec Prefix";
      }
    }
    csc:xr-task "bgp";
    csc:cli-command "clear bgp instance <instance-name> version <afi-safi-name> vrf <vrf-name> <ipv4-prefix>";
  }
  rpc clear-bgp-instance-version-afi-safi-rd-ipv4-addr-ipv4-mask {
    description
      "Choose a particular BGP instance.
       clear BGP prefix version.
       Display routes with a specific route distinguisher.
      ";
    input {
      leaf instance-name {
        type instance-name;
        mandatory true;
        description
          "instance name or all";
      }
      leaf afi-safi-name {
        type afi-safi-type;
        mandatory true;
        description
          "AFI and SAFI";
      }
      leaf rd {
        type rd;
        mandatory true;
        description
          "Route distinguisher";
      }
      leaf ipv4-addr {
        type inet:ipv4-address;
        mandatory true;
        description
          "IPv4 network";
      }
      leaf ipv4-mask {
        type ipv4-netmask;
        mandatory true;
        description
          "IPv4 mask";
      }
    }
    csc:xr-task "bgp";
    csc:cli-command "clear bgp instance <instance-name> version <afi-safi-name> rd <rd> <ipv4-addr> <ipv4-mask>";
  }
  rpc clear-bgp-instance-version-afi-safi-vrf-ipv4-addr-ipv4-mask {
    description
      "Choose a particular BGP instance.
       clear BGP prefix version.
       Display routes for a specified VRF.
      ";
    input {
      leaf instance-name {
        type instance-name;
        mandatory true;
        description
          "instance name or all";
      }
      leaf afi-safi-name {
        type afi-safi-type;
        mandatory true;
        description
          "AFI and SAFI";
      }
      leaf vrf-name {
        type string;
        mandatory true;
        description
          "VRF name";
      }
      leaf ipv4-addr {
        type inet:ipv4-address;
        mandatory true;
        description
          "IPv4 network";
      }
      leaf ipv4-mask {
        type ipv4-netmask;
        mandatory true;
        description
          "IPv4 mask";
      }
    }
    csc:xr-task "bgp";
    csc:cli-command "clear bgp instance <instance-name> version <afi-safi-name> vrf <vrf-name> <ipv4-addr> <ipv4-mask>";
  }
  rpc clear-bgp-instance-version-afi-safi-rd-ipv6-addr-ipv6-netmask {
    description
      "Choose a particular BGP instance.
       clear BGP prefix version.
       Display routes with a specific route distinguisher.
      ";
    input {
      leaf instance-name {
        type instance-name;
        mandatory true;
        description
          "instance name or all";
      }
      leaf afi-safi-name {
        type afi-safi-type;
        mandatory true;
        description
          "AFI and SAFI";
      }
      leaf rd {
        type rd;
        mandatory true;
        description
          "Route distinguisher";
      }
      leaf ipv6-addr {
        type inet:ipv6-address;
        mandatory true;
        description
          "IPv6 network";
      }
      leaf ipv6-netmask {
        type ipv6-netmask;
        mandatory true;
        description
          "IPv6 mask";
      }
    }
    csc:xr-task "bgp";
    csc:cli-command "clear bgp instance <instance-name> version <afi-safi-name> rd <rd> <ipv6-addr> <ipv6-netmask>";
  }
  rpc clear-bgp-instance-version-afi-safi-rd-ipv6-addr {
    description
      "Choose a particular BGP instance.
       clear BGP prefix version.
       Display routes with a specific route distinguisher.
      ";
    input {
      leaf instance-name {
        type instance-name;
        mandatory true;
        description
          "instance name or all";
      }
      leaf afi-safi-name {
        type afi-safi-type;
        mandatory true;
        description
          "AFI and SAFI";
      }
      leaf rd {
        type rd;
        mandatory true;
        description
          "Route distinguisher";
      }
      leaf ipv6-addr {
        type inet:ipv6-address;
        mandatory true;
        description
          "IPv6 network";
      }
    }
    csc:xr-task "bgp";
    csc:cli-command "clear bgp instance <instance-name> version <afi-safi-name> rd <rd> <ipv6-addr>";
  }
  rpc clear-bgp-instance-version-afi-safi-rd-ipv6-prefix {
    description
      "Choose a particular BGP instance.
       clear BGP prefix version.
       Display routes with a specific route distinguisher.
      ";
    input {
      leaf instance-name {
        type instance-name;
        mandatory true;
        description
          "instance name or all";
      }
      leaf afi-safi-name {
        type afi-safi-type;
        mandatory true;
        description
          "AFI and SAFI";
      }
      leaf rd {
        type rd;
        mandatory true;
        description
          "Route distinguisher";
      }
      leaf ipv6-prefix {
        type inet:ipv6-prefix;
        mandatory true;
        description
          "IPv6 network and masklength";
      }
    }
    csc:xr-task "bgp";
    csc:cli-command "clear bgp instance <instance-name> version <afi-safi-name> rd <rd> <ipv6-prefix>";
  }
  rpc clear-bgp-instance-version-afi-safi-vrf-ipv6-addr-ipv6-netmask {
    description
      "Choose a particular BGP instance.
       clear BGP prefix version.
       Display routes for a specified VRF.
      ";
    input {
      leaf instance-name {
        type instance-name;
        mandatory true;
        description
          "instance name or all";
      }
      leaf afi-safi-name {
        type afi-safi-type;
        mandatory true;
        description
          "AFI and SAFI";
      }
      leaf vrf-name {
        type string;
        mandatory true;
        description
          "VRF name";
      }
      leaf ipv6-addr {
        type inet:ipv6-address;
        mandatory true;
        description
          "IPv6 network";
      }
      leaf ipv6-netmask {
        type ipv6-netmask;
        mandatory true;
        description
          "IPv6 mask";
      }
    }
    csc:xr-task "bgp";
    csc:cli-command "clear bgp instance <instance-name> version <afi-safi-name> vrf <vrf-name> <ipv6-addr> <ipv6-netmask>";
  }
  rpc clear-bgp-instance-version-afi-safi-vrf-ipv6-addr {
    description
      "Choose a particular BGP instance.
       clear BGP prefix version.
       Display routes for a specified VRF.
      ";
    input {
      leaf instance-name {
        type instance-name;
        mandatory true;
        description
          "instance name or all";
      }
      leaf afi-safi-name {
        type afi-safi-type;
        mandatory true;
        description
          "AFI and SAFI";
      }
      leaf vrf-name {
        type string;
        mandatory true;
        description
          "VRF name";
      }
      leaf ipv6-addr {
        type inet:ipv6-address;
        mandatory true;
        description
          "IPv6 network";
      }
    }
    csc:xr-task "bgp";
    csc:cli-command "clear bgp instance <instance-name> version <afi-safi-name> vrf <vrf-name> <ipv6-addr>";
  }
  rpc clear-bgp-instance-version-afi-safi-vrf-ipv6-prefix {
    description
      "Choose a particular BGP instance.
       clear BGP prefix version.
       Display routes for a specified VRF.
      ";
    input {
      leaf instance-name {
        type instance-name;
        mandatory true;
        description
          "instance name or all";
      }
      leaf afi-safi-name {
        type afi-safi-type;
        mandatory true;
        description
          "AFI and SAFI";
      }
      leaf vrf-name {
        type string;
        mandatory true;
        description
          "VRF name";
      }
      leaf ipv6-prefix {
        type inet:ipv6-prefix;
        mandatory true;
        description
          "IPv6 network and masklength";
      }
    }
    csc:xr-task "bgp";
    csc:cli-command "clear bgp instance <instance-name> version <afi-safi-name> vrf <vrf-name> <ipv6-prefix>";
  }
  rpc clear-bgp-instance-version-vrf-ip-addr-ip-netmask {
    description
      "Choose a particular BGP instance.
       clear BGP prefix version.
       Specify a VRF.
      ";
    input {
      leaf instance-name {
        type instance-name;
        mandatory true;
        description
          "instance name or all";
      }
      leaf vrf-all {
        type vrf-name;
        mandatory true;
        description
          "VRF name or all";
      }
      leaf ip-addr {
        type inet:ip-address;
        mandatory true;
        description
          "Network";
      }
      leaf ip-netmask {
        type ip-netmask;
        mandatory true;
        description
          "Mask";
      }
    }
    csc:xr-task "bgp";
    csc:cli-command "clear bgp instance <instance-name> version vrf <vrf-all> <ip-addr> <ip-netmask>";
  }
  rpc clear-bgp-instance-version-vrf-ip-addr {
    description
      "Choose a particular BGP instance.
       clear BGP prefix version.
       Specify a VRF.
      ";
    input {
      leaf instance-name {
        type instance-name;
        mandatory true;
        description
          "instance name or all";
      }
      leaf vrf-all {
        type vrf-name;
        mandatory true;
        description
          "VRF name or all";
      }
      leaf ip-addr {
        type inet:ip-address;
        mandatory true;
        description
          "Network";
      }
    }
    csc:xr-task "bgp";
    csc:cli-command "clear bgp instance <instance-name> version vrf <vrf-all> <ip-addr>";
  }
  rpc clear-bgp-instance-version-vrf-ip-prefix {
    description
      "Choose a particular BGP instance.
       clear BGP prefix version.
       Specify a VRF.
      ";
    input {
      leaf instance-name {
        type instance-name;
        mandatory true;
        description
          "instance name or all";
      }
      leaf vrf-all {
        type vrf-name;
        mandatory true;
        description
          "VRF name or all";
      }
      leaf ip-prefix {
        type inet:ip-prefix;
        mandatory true;
        description
          "Network and masklength";
      }
    }
    csc:xr-task "bgp";
    csc:cli-command "clear bgp instance <instance-name> version vrf <vrf-all> <ip-prefix>";
  }
  rpc clear-bgp-instance-version-vrf-afi-safi-ipv4-prefix {
    description
      "Choose a particular BGP instance.
       clear BGP prefix version.
       Specify a VRF.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
      leaf ipv4-prefix {
        type inet:ipv4-prefix;
        mandatory true;
        description
          "Fspec IPv4 Prefix";
      }
    }
    csc:xr-task "bgp";
    csc:cli-command "clear bgp instance <instance-name> version vrf <vrf-all> <afi-safi-name> <ipv4-prefix>";
  }
  rpc clear-bgp-instance-version-vrf-afi-safi-ipv4-addr-ipv4-mask {
    description
      "Choose a particular BGP instance.
       clear BGP prefix version.
       Specify a VRF.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
      leaf ipv4-addr {
        type inet:ipv4-address;
        mandatory true;
        description
          "IPv4 network";
      }
      leaf ipv4-mask {
        type ipv4-netmask;
        mandatory true;
        description
          "IPv4 mask";
      }
    }
    csc:xr-task "bgp";
    csc:cli-command "clear bgp instance <instance-name> version vrf <vrf-all> <afi-safi-name> <ipv4-addr> <ipv4-mask>";
  }
  rpc clear-bgp-instance-version-vrf-afi-safi-ipv4-addr {
    description
      "Choose a particular BGP instance.
       clear BGP prefix version.
       Specify a VRF.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
      leaf ipv4-addr {
        type inet:ipv4-address;
        mandatory true;
        description
          "IPv4 network";
      }
    }
    csc:xr-task "bgp";
    csc:cli-command "clear bgp instance <instance-name> version vrf <vrf-all> <afi-safi-name> <ipv4-addr>";
  }
  rpc clear-bgp-instance-version-vrf-afi-safi-network {
    description
      "Choose a particular BGP instance.
       clear BGP prefix version.
       Specify a VRF.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
      leaf network {
        type string;
        mandatory true;
        description
          "Address family modifier specific network";
      }
    }
    csc:xr-task "bgp";
    csc:cli-command "clear bgp instance <instance-name> version vrf <vrf-all> <afi-safi-name> <network>";
  }
  rpc clear-bgp-instance-version-vrf-afi-safi-rd-network {
    description
      "Choose a particular BGP instance.
       clear BGP prefix version.
       Specify a VRF.
       Display routes with a specific route distinguisher.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
      leaf rd {
        type rd;
        mandatory true;
        description
          "Route distinguisher";
      }
      leaf network {
        type string;
        mandatory true;
        description
          "Address family modifier specific network";
      }
    }
    csc:xr-task "bgp";
    csc:cli-command "clear bgp instance <instance-name> version vrf <vrf-all> <afi-safi-name> rd <rd> <network>";
  }
  rpc clear-bgp-instance-version-vrf-afi-safi-vrf-network {
    description
      "Choose a particular BGP instance.
       clear BGP prefix version.
       Specify a VRF.
       Display routes for a specified VRF.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
      leaf vrf-name {
        type string;
        mandatory true;
        description
          "VRF name";
      }
      leaf network {
        type string;
        mandatory true;
        description
          "Address family modifier specific network";
      }
    }
    csc:xr-task "bgp";
    csc:cli-command "clear bgp instance <instance-name> version vrf <vrf-all> <afi-safi-name> vrf <vrf-name> <network>";
  }
  rpc clear-bgp-instance-version-vrf-afi-safi-ipv6-addr-ipv6-netmask {
    description
      "Choose a particular BGP instance.
       clear BGP prefix version.
       Specify a VRF.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
      leaf ipv6-addr {
        type inet:ipv6-address;
        mandatory true;
        description
          "IPv6 network";
      }
      leaf ipv6-netmask {
        type ipv6-netmask;
        mandatory true;
        description
          "IPv6 mask";
      }
    }
    csc:xr-task "bgp";
    csc:cli-command "clear bgp instance <instance-name> version vrf <vrf-all> <afi-safi-name> <ipv6-addr> <ipv6-netmask>";
  }
  rpc clear-bgp-instance-version-vrf-afi-safi-ipv6-addr {
    description
      "Choose a particular BGP instance.
       clear BGP prefix version.
       Specify a VRF.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
      leaf ipv6-addr {
        type inet:ipv6-address;
        mandatory true;
        description
          "IPv6 network";
      }
    }
    csc:xr-task "bgp";
    csc:cli-command "clear bgp instance <instance-name> version vrf <vrf-all> <afi-safi-name> <ipv6-addr>";
  }
  rpc clear-bgp-instance-version-vrf-afi-safi-ipv6-prefix {
    description
      "Choose a particular BGP instance.
       clear BGP prefix version.
       Specify a VRF.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
      leaf ipv6-prefix {
        type inet:ipv6-prefix;
        mandatory true;
        description
          "IPv6 network and masklength";
      }
    }
    csc:xr-task "bgp";
    csc:cli-command "clear bgp instance <instance-name> version vrf <vrf-all> <afi-safi-name> <ipv6-prefix>";
  }
  rpc clear-bgp-instance-version-vrf-afi-safi-rd {
    description
      "Choose a particular BGP instance.
       clear BGP prefix version.
       Specify a VRF.
       Display routes with a specific route distinguisher.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
      leaf rd {
        type rd;
        mandatory true;
        description
          "Route distinguisher";
      }
    }
    csc:xr-task "bgp";
    csc:cli-command "clear bgp instance <instance-name> version vrf <vrf-all> <afi-safi-name> rd <rd>";
  }
  rpc clear-bgp-instance-version-vrf-afi-safi-vrf {
    description
      "Choose a particular BGP instance.
       clear BGP prefix version.
       Specify a VRF.
       Display routes for a specified VRF.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
      leaf vrf-name {
        type string;
        mandatory true;
        description
          "VRF name";
      }
    }
    csc:xr-task "bgp";
    csc:cli-command "clear bgp instance <instance-name> version vrf <vrf-all> <afi-safi-name> vrf <vrf-name>";
  }
  rpc clear-bgp-instance-version-vrf-afi-safi {
    description
      "Choose a particular BGP instance.
       clear BGP prefix version.
       Specify a VRF.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
    }
    csc:xr-task "bgp";
    csc:cli-command "clear bgp instance <instance-name> version vrf <vrf-all> <afi-safi-name>";
  }
  rpc clear-bgp-instance-vrf-all-graceful {
    description
      "Choose a particular BGP instance.
       Specify a VRF.
       Clear all peers and all routes from the BGP table.
       Clear with a hard reset and a graceful restart.
      ";
    input {
      leaf instance-name {
        type instance-name;
        mandatory true;
        description
          "instance name or all";
      }
      leaf vrf-all {
        type vrf-name;
        mandatory true;
        description
          "VRF name or all";
      }
    }
    csc:xr-task "bgp";
    csc:cli-command "clear bgp instance <instance-name> vrf <vrf-all> * graceful";
  }
  rpc clear-bgp-instance-vrf-all {
    description
      "Choose a particular BGP instance.
       Specify a VRF.
       Clear all peers and all routes from the BGP table.
      ";
    input {
      leaf instance-name {
        type instance-name;
        mandatory true;
        description
          "instance name or all";
      }
      leaf vrf-all {
        type vrf-name;
        mandatory true;
        description
          "VRF name or all";
      }
    }
    csc:xr-task "bgp";
    csc:cli-command "clear bgp instance <instance-name> vrf <vrf-all> *";
  }
  rpc clear-bgp-instance-vrf-ip-addr-graceful {
    description
      "Choose a particular BGP instance.
       Specify a VRF.
       Clear with a hard reset and a graceful restart.
      ";
    input {
      leaf instance-name {
        type instance-name;
        mandatory true;
        description
          "instance name or all";
      }
      leaf vrf-all {
        type vrf-name;
        mandatory true;
        description
          "VRF name or all";
      }
      leaf ip-addr {
        type inet:ip-address;
        mandatory true;
        description
          "BGP neighbor address to clear";
      }
    }
    csc:xr-task "bgp";
    csc:cli-command "clear bgp instance <instance-name> vrf <vrf-all> <ip-addr> graceful";
  }
  rpc clear-bgp-instance-vrf-ip-addr-long-lived-stale {
    description
      "Choose a particular BGP instance.
       Specify a VRF.
       Clear long-lived-stale routes.
      ";
    input {
      leaf instance-name {
        type instance-name;
        mandatory true;
        description
          "instance name or all";
      }
      leaf vrf-all {
        type vrf-name;
        mandatory true;
        description
          "VRF name or all";
      }
      leaf ip-addr {
        type inet:ip-address;
        mandatory true;
        description
          "BGP neighbor address to clear";
      }
    }
    csc:xr-task "bgp";
    csc:cli-command "clear bgp instance <instance-name> vrf <vrf-all> <ip-addr> long-lived-stale";
  }
  rpc clear-bgp-instance-vrf-ip-addr {
    description
      "Choose a particular BGP instance.
       Specify a VRF.
      ";
    input {
      leaf instance-name {
        type instance-name;
        mandatory true;
        description
          "instance name or all";
      }
      leaf vrf-all {
        type vrf-name;
        mandatory true;
        description
          "VRF name or all";
      }
      leaf ip-addr {
        type inet:ip-address;
        mandatory true;
        description
          "BGP neighbor address to clear";
      }
    }
    csc:xr-task "bgp";
    csc:cli-command "clear bgp instance <instance-name> vrf <vrf-all> <ip-addr>";
  }
  rpc clear-bgp-instance-vrf-as-graceful {
    description
      "Choose a particular BGP instance.
       Specify a VRF.
       Clear peers in a specific AS.
       Clear with a hard reset and a graceful restart.
      ";
    input {
      leaf instance-name {
        type instance-name;
        mandatory true;
        description
          "instance name or all";
      }
      leaf vrf-all {
        type vrf-name;
        mandatory true;
        description
          "VRF name or all";
      }
      leaf as-number {
        type as-number;
        mandatory true;
        description
          "AS number";
      }
    }
    csc:xr-task "bgp";
    csc:cli-command "clear bgp instance <instance-name> vrf <vrf-all> as <as-number> graceful";
  }
  rpc clear-bgp-instance-vrf-as {
    description
      "Choose a particular BGP instance.
       Specify a VRF.
       Clear peers in a specific AS.
      ";
    input {
      leaf instance-name {
        type instance-name;
        mandatory true;
        description
          "instance name or all";
      }
      leaf vrf-all {
        type vrf-name;
        mandatory true;
        description
          "VRF name or all";
      }
      leaf as-number {
        type as-number;
        mandatory true;
        description
          "AS number";
      }
    }
    csc:xr-task "bgp";
    csc:cli-command "clear bgp instance <instance-name> vrf <vrf-all> as <as-number>";
  }
  rpc clear-bgp-instance-vrf-external-graceful {
    description
      "Choose a particular BGP instance.
       Specify a VRF.
       Clear all external peers.
       Clear with a hard reset and a graceful restart.
      ";
    input {
      leaf instance-name {
        type instance-name;
        mandatory true;
        description
          "instance name or all";
      }
      leaf vrf-all {
        type vrf-name;
        mandatory true;
        description
          "VRF name or all";
      }
    }
    csc:xr-task "bgp";
    csc:cli-command "clear bgp instance <instance-name> vrf <vrf-all> external graceful";
  }
  rpc clear-bgp-instance-vrf-external {
    description
      "Choose a particular BGP instance.
       Specify a VRF.
       Clear all external peers.
      ";
    input {
      leaf instance-name {
        type instance-name;
        mandatory true;
        description
          "instance name or all";
      }
      leaf vrf-all {
        type vrf-name;
        mandatory true;
        description
          "VRF name or all";
      }
    }
    csc:xr-task "bgp";
    csc:cli-command "clear bgp instance <instance-name> vrf <vrf-all> external";
  }
  rpc clear-bgp-instance-vrf-afi-safi-all-soft-in-prefix-filter {
    description
      "Choose a particular BGP instance.
       Specify a VRF.
       Clear all peers and all routes from the BGP table.
       Soft reconfig.
       Soft reconfig inbound update.
       Push out prefix ORF and do inbound soft reconfig.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
    }
    csc:xr-task "bgp";
    csc:cli-command "clear bgp instance <instance-name> vrf <vrf-all> <afi-safi-name> * soft in prefix-filter";
  }
  rpc clear-bgp-instance-vrf-afi-safi-all-soft-in {
    description
      "Choose a particular BGP instance.
       Specify a VRF.
       Clear all peers and all routes from the BGP table.
       Soft reconfig.
       Soft reconfig inbound update.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
    }
    csc:xr-task "bgp";
    csc:cli-command "clear bgp instance <instance-name> vrf <vrf-all> <afi-safi-name> * soft in";
  }
  rpc clear-bgp-instance-vrf-afi-safi-all-soft-out {
    description
      "Choose a particular BGP instance.
       Specify a VRF.
       Clear all peers and all routes from the BGP table.
       Soft reconfig.
       Soft reconfig outbound update.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
    }
    csc:xr-task "bgp";
    csc:cli-command "clear bgp instance <instance-name> vrf <vrf-all> <afi-safi-name> * soft out";
  }
  rpc clear-bgp-instance-vrf-afi-safi-all-soft {
    description
      "Choose a particular BGP instance.
       Specify a VRF.
       Clear all peers and all routes from the BGP table.
       Soft reconfig.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
    }
    csc:xr-task "bgp";
    csc:cli-command "clear bgp instance <instance-name> vrf <vrf-all> <afi-safi-name> * soft";
  }
  rpc clear-bgp-instance-vrf-afi-safi-ip-addr-long-lived-stale {
    description
      "Choose a particular BGP instance.
       Specify a VRF.
       Clear long-lived-stale routes.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
      leaf ip-addr {
        type inet:ip-address;
        mandatory true;
        description
          "BGP neighbor address to clear";
      }
    }
    csc:xr-task "bgp";
    csc:cli-command "clear bgp instance <instance-name> vrf <vrf-all> <afi-safi-name> <ip-addr> long-lived-stale";
  }
  rpc clear-bgp-instance-vrf-afi-safi-ip-addr-soft-in-prefix-filter {
    description
      "Choose a particular BGP instance.
       Specify a VRF.
       Soft reconfig.
       Soft reconfig inbound update.
       Push out prefix ORF and do inbound soft reconfig.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
      leaf ip-addr {
        type inet:ip-address;
        mandatory true;
        description
          "BGP neighbor address to clear";
      }
    }
    csc:xr-task "bgp";
    csc:cli-command "clear bgp instance <instance-name> vrf <vrf-all> <afi-safi-name> <ip-addr> soft in prefix-filter";
  }
  rpc clear-bgp-instance-vrf-afi-safi-ip-addr-soft-in {
    description
      "Choose a particular BGP instance.
       Specify a VRF.
       Soft reconfig.
       Soft reconfig inbound update.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
      leaf ip-addr {
        type inet:ip-address;
        mandatory true;
        description
          "BGP neighbor address to clear";
      }
    }
    csc:xr-task "bgp";
    csc:cli-command "clear bgp instance <instance-name> vrf <vrf-all> <afi-safi-name> <ip-addr> soft in";
  }
  rpc clear-bgp-instance-vrf-afi-safi-ip-addr-soft-out {
    description
      "Choose a particular BGP instance.
       Specify a VRF.
       Soft reconfig.
       Soft reconfig outbound update.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
      leaf ip-addr {
        type inet:ip-address;
        mandatory true;
        description
          "BGP neighbor address to clear";
      }
    }
    csc:xr-task "bgp";
    csc:cli-command "clear bgp instance <instance-name> vrf <vrf-all> <afi-safi-name> <ip-addr> soft out";
  }
  rpc clear-bgp-instance-vrf-afi-safi-ip-addr-soft {
    description
      "Choose a particular BGP instance.
       Specify a VRF.
       Soft reconfig.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
      leaf ip-addr {
        type inet:ip-address;
        mandatory true;
        description
          "BGP neighbor address to clear";
      }
    }
    csc:xr-task "bgp";
    csc:cli-command "clear bgp instance <instance-name> vrf <vrf-all> <afi-safi-name> <ip-addr> soft";
  }
  rpc clear-bgp-instance-vrf-afi-safi-as-soft-in-prefix-filter {
    description
      "Choose a particular BGP instance.
       Specify a VRF.
       Clear peers in a specific AS.
       Soft reconfig.
       Soft reconfig inbound update.
       Push out prefix ORF and do inbound soft reconfig.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
      leaf as-number {
        type as-number;
        mandatory true;
        description
          "AS number";
      }
    }
    csc:xr-task "bgp";
    csc:cli-command "clear bgp instance <instance-name> vrf <vrf-all> <afi-safi-name> as <as-number> soft in prefix-filter";
  }
  rpc clear-bgp-instance-vrf-afi-safi-as-soft-in {
    description
      "Choose a particular BGP instance.
       Specify a VRF.
       Clear peers in a specific AS.
       Soft reconfig.
       Soft reconfig inbound update.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
      leaf as-number {
        type as-number;
        mandatory true;
        description
          "AS number";
      }
    }
    csc:xr-task "bgp";
    csc:cli-command "clear bgp instance <instance-name> vrf <vrf-all> <afi-safi-name> as <as-number> soft in";
  }
  rpc clear-bgp-instance-vrf-afi-safi-as-soft-out {
    description
      "Choose a particular BGP instance.
       Specify a VRF.
       Clear peers in a specific AS.
       Soft reconfig.
       Soft reconfig outbound update.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
      leaf as-number {
        type as-number;
        mandatory true;
        description
          "AS number";
      }
    }
    csc:xr-task "bgp";
    csc:cli-command "clear bgp instance <instance-name> vrf <vrf-all> <afi-safi-name> as <as-number> soft out";
  }
  rpc clear-bgp-instance-vrf-afi-safi-as-soft {
    description
      "Choose a particular BGP instance.
       Specify a VRF.
       Clear peers in a specific AS.
       Soft reconfig.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
      leaf as-number {
        type as-number;
        mandatory true;
        description
          "AS number";
      }
    }
    csc:xr-task "bgp";
    csc:cli-command "clear bgp instance <instance-name> vrf <vrf-all> <afi-safi-name> as <as-number> soft";
  }
  rpc clear-bgp-instance-vrf-afi-safi-dampening-ipv4-prefix {
    description
      "Choose a particular BGP instance.
       Specify a VRF.
       Clear route flap dampening information.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
      leaf ipv4-prefix {
        type inet:ipv4-prefix;
        mandatory true;
        description
          "IPv4 Network and mask or masklength to clear dampening information";
      }
    }
    csc:xr-task "bgp";
    csc:cli-command "clear bgp instance <instance-name> vrf <vrf-all> <afi-safi-name> dampening <ipv4-prefix>";
  }
  rpc clear-bgp-instance-vrf-afi-safi-dampening {
    description
      "Choose a particular BGP instance.
       Specify a VRF.
       Clear route flap dampening information.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
    }
    csc:xr-task "bgp";
    csc:cli-command "clear bgp instance <instance-name> vrf <vrf-all> <afi-safi-name> dampening";
  }
  rpc clear-bgp-instance-vrf-afi-safi-external-soft-in-prefix-filter {
    description
      "Choose a particular BGP instance.
       Specify a VRF.
       Clear all external peers.
       Soft reconfig.
       Soft reconfig inbound update.
       Push out prefix ORF and do inbound soft reconfig.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
    }
    csc:xr-task "bgp";
    csc:cli-command "clear bgp instance <instance-name> vrf <vrf-all> <afi-safi-name> external soft in prefix-filter";
  }
  rpc clear-bgp-instance-vrf-afi-safi-external-soft-in {
    description
      "Choose a particular BGP instance.
       Specify a VRF.
       Clear all external peers.
       Soft reconfig.
       Soft reconfig inbound update.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
    }
    csc:xr-task "bgp";
    csc:cli-command "clear bgp instance <instance-name> vrf <vrf-all> <afi-safi-name> external soft in";
  }
  rpc clear-bgp-instance-vrf-afi-safi-external-soft-out {
    description
      "Choose a particular BGP instance.
       Specify a VRF.
       Clear all external peers.
       Soft reconfig.
       Soft reconfig outbound update.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
    }
    csc:xr-task "bgp";
    csc:cli-command "clear bgp instance <instance-name> vrf <vrf-all> <afi-safi-name> external soft out";
  }
  rpc clear-bgp-instance-vrf-afi-safi-external-soft {
    description
      "Choose a particular BGP instance.
       Specify a VRF.
       Clear all external peers.
       Soft reconfig.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
    }
    csc:xr-task "bgp";
    csc:cli-command "clear bgp instance <instance-name> vrf <vrf-all> <afi-safi-name> external soft";
  }
  rpc clear-bgp-instance-vrf-afi-safi-flap-statistics-ip-addr-ipv4-mask {
    description
      "Choose a particular BGP instance.
       Specify a VRF.
       Clear flap statistics.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
      leaf ip-addr {
        type inet:ip-address;
        mandatory true;
        description
          "BGP neighbor address to clear";
      }
      leaf ipv4-mask {
        type ipv4-netmask;
        mandatory true;
        description
          "IPv4 Network and mask or masklength to clear flap statistics";
      }
    }
    csc:xr-task "bgp";
    csc:cli-command "clear bgp instance <instance-name> vrf <vrf-all> <afi-safi-name> flap-statistics <ip-addr> <ipv4-mask>";
  }
  rpc clear-bgp-instance-vrf-afi-safi-flap-statistics-ip-addr {
    description
      "Choose a particular BGP instance.
       Specify a VRF.
       Clear flap statistics.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
      leaf ip-addr {
        type inet:ip-address;
        mandatory true;
        description
          "BGP neighbor address to clear";
      }
    }
    csc:xr-task "bgp";
    csc:cli-command "clear bgp instance <instance-name> vrf <vrf-all> <afi-safi-name> flap-statistics <ip-addr>";
  }
  rpc clear-bgp-instance-vrf-afi-safi-flap-statistics-ipv4-prefix {
    description
      "Choose a particular BGP instance.
       Specify a VRF.
       Clear flap statistics.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
      leaf ipv4-prefix {
        type inet:ipv4-prefix;
        mandatory true;
        description
          "IPv4 Network and mask or masklength to clear flap statistics";
      }
    }
    csc:xr-task "bgp";
    csc:cli-command "clear bgp instance <instance-name> vrf <vrf-all> <afi-safi-name> flap-statistics <ipv4-prefix>";
  }
  rpc clear-bgp-instance-vrf-afi-safi-flap-statistics-regexp {
    description
      "Choose a particular BGP instance.
       Specify a VRF.
       Clear flap statistics.
       Clear flap statistics for routes matching the regular expression.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
      leaf regexp-pattern {
        type string;
        mandatory true;
        description
          "A regular expression to match the BGP AS paths.  Use 'ctrl-v ?' to enter '?'";
      }
    }
    csc:xr-task "bgp";
    csc:cli-command "clear bgp instance <instance-name> vrf <vrf-all> <afi-safi-name> flap-statistics regexp <regexp-pattern>";
  }
  rpc clear-bgp-instance-vrf-afi-safi-flap-statistics-route-policy {
    description
      "Choose a particular BGP instance.
       Specify a VRF.
       Clear flap statistics.
       Clear flap statistics for routes matching the route policy.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
      leaf route-policy-name {
        type string;
        mandatory true;
        description
          "Route Policy name";
      }
    }
    csc:xr-task "bgp";
    csc:cli-command "clear bgp instance <instance-name> vrf <vrf-all> <afi-safi-name> flap-statistics route-policy <route-policy-name>";
  }
  rpc clear-bgp-instance-vrf-afi-safi-flap-statistics {
    description
      "Choose a particular BGP instance.
       Specify a VRF.
       Clear flap statistics.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
    }
    csc:xr-task "bgp";
    csc:cli-command "clear bgp instance <instance-name> vrf <vrf-all> <afi-safi-name> flap-statistics";
  }
  rpc clear-bgp-instance-vrf-afi-safi-nexthop-performance-statistics {
    description
      "Choose a particular BGP instance.
       Specify a VRF.
       Clear nexthop.
       Performance statistics information related to processing.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
    }
    csc:xr-task "bgp";
    csc:cli-command "clear bgp instance <instance-name> vrf <vrf-all> <afi-safi-name> nexthop performance-statistics";
  }
  rpc clear-bgp-instance-vrf-afi-safi-nexthop-registration-ip-addr {
    description
      "Choose a particular BGP instance.
       Specify a VRF.
       Clear nexthop.
       Registration with RIB and reregister.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
      leaf ip-addr {
        type inet:ip-address;
        mandatory true;
        description
          "Nexthop address";
      }
    }
    csc:xr-task "bgp";
    csc:cli-command "clear bgp instance <instance-name> vrf <vrf-all> <afi-safi-name> nexthop registration <ip-addr>";
  }
  rpc clear-bgp-instance-vrf-afi-safi-self-originated {
    description
      "Choose a particular BGP instance.
       Specify a VRF.
       Clear redistributed, network and aggregate routes originated here.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
    }
    csc:xr-task "bgp";
    csc:cli-command "clear bgp instance <instance-name> vrf <vrf-all> <afi-safi-name> self-originated";
  }
  rpc clear-bgp-instance-vrf-afi-safi-shutdown {
    description
      "Choose a particular BGP instance.
       Specify a VRF.
       Clear all peers which were shut down due to low memory.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
    }
    csc:xr-task "bgp";
    csc:cli-command "clear bgp instance <instance-name> vrf <vrf-all> <afi-safi-name> shutdown";
  }
  rpc clear-bgp-instance-vrf-afi-safi-update-outq-address-family-update-parent {
    description
      "Choose a particular BGP instance.
       Specify a VRF.
       Clear Update information (Do NOT execute without cisco support)(cisco-support).
       Clear Update generation OutQ counters (Do NOT execute without cisco support)(cisco-support).
       Address-family.
       Update parents' OutQ counters too.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
    }
    csc:xr-task "bgp";
    csc:cli-command "clear bgp instance <instance-name> vrf <vrf-all> <afi-safi-name> update outq address-family update-parent";
  }
  rpc clear-bgp-instance-vrf-afi-safi-update-outq-address-family {
    description
      "Choose a particular BGP instance.
       Specify a VRF.
       Clear Update information (Do NOT execute without cisco support)(cisco-support).
       Clear Update generation OutQ counters (Do NOT execute without cisco support)(cisco-support).
       Address-family.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
    }
    csc:xr-task "bgp";
    csc:cli-command "clear bgp instance <instance-name> vrf <vrf-all> <afi-safi-name> update outq address-family";
  }
  rpc clear-bgp-instance-vrf-afi-safi-update-outq-neighbor-ip-addr-refresh-update-parent {
    description
      "Choose a particular BGP instance.
       Specify a VRF.
       Clear Update information (Do NOT execute without cisco support)(cisco-support).
       Clear Update generation OutQ counters (Do NOT execute without cisco support)(cisco-support).
       Neighbor.
       Refresh OutQ.
       Update parents' OutQ counters too.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
      leaf ip-addr {
        type inet:ip-address;
        mandatory true;
        description
          "Neighbor address";
      }
    }
    csc:xr-task "bgp";
    csc:cli-command "clear bgp instance <instance-name> vrf <vrf-all> <afi-safi-name> update outq neighbor <ip-addr> refresh update-parent";
  }
  rpc clear-bgp-instance-vrf-afi-safi-update-outq-neighbor-ip-addr-refresh {
    description
      "Choose a particular BGP instance.
       Specify a VRF.
       Clear Update information (Do NOT execute without cisco support)(cisco-support).
       Clear Update generation OutQ counters (Do NOT execute without cisco support)(cisco-support).
       Neighbor.
       Refresh OutQ.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
      leaf ip-addr {
        type inet:ip-address;
        mandatory true;
        description
          "Neighbor address";
      }
    }
    csc:xr-task "bgp";
    csc:cli-command "clear bgp instance <instance-name> vrf <vrf-all> <afi-safi-name> update outq neighbor <ip-addr> refresh";
  }
  rpc clear-bgp-instance-vrf-afi-safi-update-outq-neighbor-ip-addr-update-parent {
    description
      "Choose a particular BGP instance.
       Specify a VRF.
       Clear Update information (Do NOT execute without cisco support)(cisco-support).
       Clear Update generation OutQ counters (Do NOT execute without cisco support)(cisco-support).
       Neighbor.
       Update parents' OutQ counters too.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
      leaf ip-addr {
        type inet:ip-address;
        mandatory true;
        description
          "Neighbor address";
      }
    }
    csc:xr-task "bgp";
    csc:cli-command "clear bgp instance <instance-name> vrf <vrf-all> <afi-safi-name> update outq neighbor <ip-addr> update-parent";
  }
  rpc clear-bgp-instance-vrf-afi-safi-update-outq-neighbor-ip-addr {
    description
      "Choose a particular BGP instance.
       Specify a VRF.
       Clear Update information (Do NOT execute without cisco support)(cisco-support).
       Clear Update generation OutQ counters (Do NOT execute without cisco support)(cisco-support).
       Neighbor.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
      leaf ip-addr {
        type inet:ip-address;
        mandatory true;
        description
          "Neighbor address";
      }
    }
    csc:xr-task "bgp";
    csc:cli-command "clear bgp instance <instance-name> vrf <vrf-all> <afi-safi-name> update outq neighbor <ip-addr>";
  }
  rpc clear-bgp-instance-vrf-afi-safi-update-outq-update-group-sub-group-update-parent {
    description
      "Choose a particular BGP instance.
       Specify a VRF.
       Clear Update information (Do NOT execute without cisco support)(cisco-support).
       Clear Update generation OutQ counters (Do NOT execute without cisco support)(cisco-support).
       Update-group.
       Sub-group.
       Update parents' OutQ counters too.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
      leaf update-group {
        type update-group-id;
        mandatory true;
        description
          "Update-group process ID <x.y>";
      }
      leaf sub-group {
        type update-group-id;
        mandatory true;
        description
          "Sub-group process ID <x.y>";
      }
    }
    csc:xr-task "bgp";
    csc:cli-command "clear bgp instance <instance-name> vrf <vrf-all> <afi-safi-name> update outq update-group <update-group> sub-group <sub-group> update-parent";
  }
  rpc clear-bgp-instance-vrf-afi-safi-update-outq-update-group-sub-group {
    description
      "Choose a particular BGP instance.
       Specify a VRF.
       Clear Update information (Do NOT execute without cisco support)(cisco-support).
       Clear Update generation OutQ counters (Do NOT execute without cisco support)(cisco-support).
       Update-group.
       Sub-group.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
      leaf update-group {
        type update-group-id;
        mandatory true;
        description
          "Update-group process ID <x.y>";
      }
      leaf sub-group {
        type update-group-id;
        mandatory true;
        description
          "Sub-group process ID <x.y>";
      }
    }
    csc:xr-task "bgp";
    csc:cli-command "clear bgp instance <instance-name> vrf <vrf-all> <afi-safi-name> update outq update-group <update-group> sub-group <sub-group>";
  }
  rpc clear-bgp-instance-vrf-afi-safi-update-outq-update-group-sub-group-refresh-sub-group-update-parent {
    description
      "Choose a particular BGP instance.
       Specify a VRF.
       Clear Update information (Do NOT execute without cisco support)(cisco-support).
       Clear Update generation OutQ counters (Do NOT execute without cisco support)(cisco-support).
       Update-group.
       Sub-group.
       Update parents' OutQ counters too.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
      leaf update-group {
        type update-group-id;
        mandatory true;
        description
          "Update-group process ID <x.y>";
      }
      leaf refresh-sub-group {
        type refresh-sub-group-id;
        mandatory true;
        description
          "Refresh Sub-group process ID <x.y:z>";
      }
    }
    csc:xr-task "bgp";
    csc:cli-command "clear bgp instance <instance-name> vrf <vrf-all> <afi-safi-name> update outq update-group <update-group> sub-group <refresh-sub-group> update-parent";
  }
  rpc clear-bgp-instance-vrf-afi-safi-update-outq-update-group-sub-group-refresh-sub-group {
    description
      "Choose a particular BGP instance.
       Specify a VRF.
       Clear Update information (Do NOT execute without cisco support)(cisco-support).
       Clear Update generation OutQ counters (Do NOT execute without cisco support)(cisco-support).
       Update-group.
       Sub-group.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
      leaf update-group {
        type update-group-id;
        mandatory true;
        description
          "Update-group process ID <x.y>";
      }
      leaf refresh-sub-group {
        type refresh-sub-group-id;
        mandatory true;
        description
          "Refresh Sub-group process ID <x.y:z>";
      }
    }
    csc:xr-task "bgp";
    csc:cli-command "clear bgp instance <instance-name> vrf <vrf-all> <afi-safi-name> update outq update-group <update-group> sub-group <refresh-sub-group>";
  }
  rpc clear-bgp-instance-vrf-afi-safi-update-outq-update-group-update-parent {
    description
      "Choose a particular BGP instance.
       Specify a VRF.
       Clear Update information (Do NOT execute without cisco support)(cisco-support).
       Clear Update generation OutQ counters (Do NOT execute without cisco support)(cisco-support).
       Update-group.
       Update parents' OutQ counters too.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
      leaf update-group {
        type update-group-id;
        mandatory true;
        description
          "Update-group process ID <x.y>";
      }
    }
    csc:xr-task "bgp";
    csc:cli-command "clear bgp instance <instance-name> vrf <vrf-all> <afi-safi-name> update outq update-group <update-group> update-parent";
  }
  rpc clear-bgp-instance-vrf-afi-safi-update-outq-update-group {
    description
      "Choose a particular BGP instance.
       Specify a VRF.
       Clear Update information (Do NOT execute without cisco support)(cisco-support).
       Clear Update generation OutQ counters (Do NOT execute without cisco support)(cisco-support).
       Update-group.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
      leaf update-group {
        type update-group-id;
        mandatory true;
        description
          "Update-group process ID <x.y>";
      }
    }
    csc:xr-task "bgp";
    csc:cli-command "clear bgp instance <instance-name> vrf <vrf-all> <afi-safi-name> update outq update-group <update-group>";
  }
  rpc clear-bgp-instance-vrf-afi-safi-dampening-ipv6-prefix {
    description
      "Choose a particular BGP instance.
       Specify a VRF.
       Clear route flap dampening information.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
      leaf ipv6-prefix {
        type inet:ipv6-prefix;
        mandatory true;
        description
          "IPv6 Network and mask or masklength to clear dampening information";
      }
    }
    csc:xr-task "bgp";
    csc:cli-command "clear bgp instance <instance-name> vrf <vrf-all> <afi-safi-name> dampening <ipv6-prefix>";
  }
  rpc clear-bgp-instance-vrf-afi-safi-flap-statistics-ipv6-prefix {
    description
      "Choose a particular BGP instance.
       Specify a VRF.
       Clear flap statistics.
      ";
    input {
      leaf instance-name {
        type instance-name;
        mandatory true;
        description
          "instance name or all";
      }
      leaf vrf-all {
        type vrf-name;
        mandatory true;
        description
          "VRF name or all";
      }
      leaf afi-safi-name {
        type afi-safi-type;
        mandatory true;
        description
          "AFI and SAFI";
      }
      leaf ipv6-prefix {
        type inet:ipv6-prefix;
        mandatory true;
        description
          "IPv6 Network and mask or masklength to clear flap statistics";
      }
    }
    csc:xr-task "bgp";
    csc:cli-command "clear bgp instance <instance-name> vrf <vrf-all> <afi-safi-name> flap-statistics <ipv6-prefix>";
  }
  rpc clear-bgp-instance-vrf-nexthop-performance-statistics {
    description
      "Choose a particular BGP instance.
       Specify a VRF.
       Clear nexthop.
       Performance statistics information related to processing.
      ";
    input {
      leaf instance-name {
        type instance-name;
        mandatory true;
        description
          "instance name or all";
      }
      leaf vrf-all {
        type vrf-name;
        mandatory true;
        description
          "VRF name or all";
      }
    }
    csc:xr-task "bgp";
    csc:cli-command "clear bgp instance <instance-name> vrf <vrf-all> nexthop performance-statistics";
  }
  rpc clear-bgp-instance-vrf-nexthop-registration-ip-addr {
    description
      "Choose a particular BGP instance.
       Specify a VRF.
       Clear nexthop.
       Registration with RIB and reregister.
      ";
    input {
      leaf instance-name {
        type instance-name;
        mandatory true;
        description
          "instance name or all";
      }
      leaf vrf-all {
        type vrf-name;
        mandatory true;
        description
          "VRF name or all";
      }
      leaf ip-addr {
        type inet:ip-address;
        mandatory true;
        description
          "Nexthop address";
      }
    }
    csc:xr-task "bgp";
    csc:cli-command "clear bgp instance <instance-name> vrf <vrf-all> nexthop registration <ip-addr>";
  }
  rpc clear-bgp-instance-vrf-peer-drops-all {
    description
      "Choose a particular BGP instance.
       Specify a VRF.
       Clear established/dropped counters for a peer.
       All Neighbors.
      ";
    input {
      leaf instance-name {
        type instance-name;
        mandatory true;
        description
          "instance name or all";
      }
      leaf vrf-all {
        type vrf-name;
        mandatory true;
        description
          "VRF name or all";
      }
    }
    csc:xr-task "bgp";
    csc:cli-command "clear bgp instance <instance-name> vrf <vrf-all> peer-drops *";
  }
  rpc clear-bgp-instance-vrf-peer-drops-ip-addr {
    description
      "Choose a particular BGP instance.
       Specify a VRF.
       Clear established/dropped counters for a peer.
      ";
    input {
      leaf instance-name {
        type instance-name;
        mandatory true;
        description
          "instance name or all";
      }
      leaf vrf-all {
        type vrf-name;
        mandatory true;
        description
          "VRF name or all";
      }
      leaf ip-addr {
        type inet:ip-address;
        mandatory true;
        description
          "BGP neighbor IP address";
      }
    }
    csc:xr-task "bgp";
    csc:cli-command "clear bgp instance <instance-name> vrf <vrf-all> peer-drops <ip-addr>";
  }
  rpc clear-bgp-instance-vrf-performance-statistics {
    description
      "Choose a particular BGP instance.
       Specify a VRF.
       Clear performance statistics.
      ";
    input {
      leaf instance-name {
        type instance-name;
        mandatory true;
        description
          "instance name or all";
      }
      leaf vrf-all {
        type vrf-name;
        mandatory true;
        description
          "VRF name or all";
      }
    }
    csc:xr-task "bgp";
    csc:cli-command "clear bgp instance <instance-name> vrf <vrf-all> performance-statistics";
  }
  rpc clear-bgp-instance-vrf-shutdown {
    description
      "Choose a particular BGP instance.
       Specify a VRF.
       Clear all peers which were shut down due to low memory.
      ";
    input {
      leaf instance-name {
        type instance-name;
        mandatory true;
        description
          "instance name or all";
      }
      leaf vrf-all {
        type vrf-name;
        mandatory true;
        description
          "VRF name or all";
      }
    }
    csc:xr-task "bgp";
    csc:cli-command "clear bgp instance <instance-name> vrf <vrf-all> shutdown";
  }
  rpc clear-bgp-instance-vrf-update-outq-address-family-update-parent {
    description
      "Choose a particular BGP instance.
       Specify a VRF.
       Clear Update information (Do NOT execute without cisco support)(cisco-support).
       Clear Update generation OutQ counters (Do NOT execute without cisco support)(cisco-support).
       Address-family.
       Update parents' OutQ counters too.
      ";
    input {
      leaf instance-name {
        type instance-name;
        mandatory true;
        description
          "instance name or all";
      }
      leaf vrf-all {
        type vrf-name;
        mandatory true;
        description
          "VRF name or all";
      }
    }
    csc:xr-task "bgp";
    csc:cli-command "clear bgp instance <instance-name> vrf <vrf-all> update outq address-family update-parent";
  }
  rpc clear-bgp-instance-vrf-update-outq-address-family {
    description
      "Choose a particular BGP instance.
       Specify a VRF.
       Clear Update information (Do NOT execute without cisco support)(cisco-support).
       Clear Update generation OutQ counters (Do NOT execute without cisco support)(cisco-support).
       Address-family.
      ";
    input {
      leaf instance-name {
        type instance-name;
        mandatory true;
        description
          "instance name or all";
      }
      leaf vrf-all {
        type vrf-name;
        mandatory true;
        description
          "VRF name or all";
      }
    }
    csc:xr-task "bgp";
    csc:cli-command "clear bgp instance <instance-name> vrf <vrf-all> update outq address-family";
  }
  rpc clear-bgp-instance-vrf-update-outq-neighbor-ip-addr-refresh-update-parent {
    description
      "Choose a particular BGP instance.
       Specify a VRF.
       Clear Update information (Do NOT execute without cisco support)(cisco-support).
       Clear Update generation OutQ counters (Do NOT execute without cisco support)(cisco-support).
       Neighbor.
       Refresh OutQ.
       Update parents' OutQ counters too.
      ";
    input {
      leaf instance-name {
        type instance-name;
        mandatory true;
        description
          "instance name or all";
      }
      leaf vrf-all {
        type vrf-name;
        mandatory true;
        description
          "VRF name or all";
      }
      leaf ip-addr {
        type inet:ip-address;
        mandatory true;
        description
          "Neighbor address";
      }
    }
    csc:xr-task "bgp";
    csc:cli-command "clear bgp instance <instance-name> vrf <vrf-all> update outq neighbor <ip-addr> refresh update-parent";
  }
  rpc clear-bgp-instance-vrf-update-outq-neighbor-ip-addr-refresh {
    description
      "Choose a particular BGP instance.
       Specify a VRF.
       Clear Update information (Do NOT execute without cisco support)(cisco-support).
       Clear Update generation OutQ counters (Do NOT execute without cisco support)(cisco-support).
       Neighbor.
       Refresh OutQ.
      ";
    input {
      leaf instance-name {
        type instance-name;
        mandatory true;
        description
          "instance name or all";
      }
      leaf vrf-all {
        type vrf-name;
        mandatory true;
        description
          "VRF name or all";
      }
      leaf ip-addr {
        type inet:ip-address;
        mandatory true;
        description
          "Neighbor address";
      }
    }
    csc:xr-task "bgp";
    csc:cli-command "clear bgp instance <instance-name> vrf <vrf-all> update outq neighbor <ip-addr> refresh";
  }
  rpc clear-bgp-instance-vrf-update-outq-neighbor-ip-addr-update-parent {
    description
      "Choose a particular BGP instance.
       Specify a VRF.
       Clear Update information (Do NOT execute without cisco support)(cisco-support).
       Clear Update generation OutQ counters (Do NOT execute without cisco support)(cisco-support).
       Neighbor.
       Update parents' OutQ counters too.
      ";
    input {
      leaf instance-name {
        type instance-name;
        mandatory true;
        description
          "instance name or all";
      }
      leaf vrf-all {
        type vrf-name;
        mandatory true;
        description
          "VRF name or all";
      }
      leaf ip-addr {
        type inet:ip-address;
        mandatory true;
        description
          "Neighbor address";
      }
    }
    csc:xr-task "bgp";
    csc:cli-command "clear bgp instance <instance-name> vrf <vrf-all> update outq neighbor <ip-addr> update-parent";
  }
  rpc clear-bgp-instance-vrf-update-outq-neighbor-ip-addr {
    description
      "Choose a particular BGP instance.
       Specify a VRF.
       Clear Update information (Do NOT execute without cisco support)(cisco-support).
       Clear Update generation OutQ counters (Do NOT execute without cisco support)(cisco-support).
       Neighbor.
      ";
    input {
      leaf instance-name {
        type instance-name;
        mandatory true;
        description
          "instance name or all";
      }
      leaf vrf-all {
        type vrf-name;
        mandatory true;
        description
          "VRF name or all";
      }
      leaf ip-addr {
        type inet:ip-address;
        mandatory true;
        description
          "Neighbor address";
      }
    }
    csc:xr-task "bgp";
    csc:cli-command "clear bgp instance <instance-name> vrf <vrf-all> update outq neighbor <ip-addr>";
  }
  rpc clear-bgp-instance-vrf-update-outq-update-group-sub-group-update-parent {
    description
      "Choose a particular BGP instance.
       Specify a VRF.
       Clear Update information (Do NOT execute without cisco support)(cisco-support).
       Clear Update generation OutQ counters (Do NOT execute without cisco support)(cisco-support).
       Update-group.
       Sub-group.
       Update parents' OutQ counters too.
      ";
    input {
      leaf instance-name {
        type instance-name;
        mandatory true;
        description
          "instance name or all";
      }
      leaf vrf-all {
        type vrf-name;
        mandatory true;
        description
          "VRF name or all";
      }
      leaf update-group {
        type update-group-id;
        mandatory true;
        description
          "Update-group process ID <x.y>";
      }
      leaf sub-group {
        type update-group-id;
        mandatory true;
        description
          "Sub-group process ID <x.y>";
      }
    }
    csc:xr-task "bgp";
    csc:cli-command "clear bgp instance <instance-name> vrf <vrf-all> update outq update-group <update-group> sub-group <sub-group> update-parent";
  }
  rpc clear-bgp-instance-vrf-update-outq-update-group-sub-group {
    description
      "Choose a particular BGP instance.
       Specify a VRF.
       Clear Update information (Do NOT execute without cisco support)(cisco-support).
       Clear Update generation OutQ counters (Do NOT execute without cisco support)(cisco-support).
       Update-group.
       Sub-group.
      ";
    input {
      leaf instance-name {
        type instance-name;
        mandatory true;
        description
          "instance name or all";
      }
      leaf vrf-all {
        type vrf-name;
        mandatory true;
        description
          "VRF name or all";
      }
      leaf update-group {
        type update-group-id;
        mandatory true;
        description
          "Update-group process ID <x.y>";
      }
      leaf sub-group {
        type update-group-id;
        mandatory true;
        description
          "Sub-group process ID <x.y>";
      }
    }
    csc:xr-task "bgp";
    csc:cli-command "clear bgp instance <instance-name> vrf <vrf-all> update outq update-group <update-group> sub-group <sub-group>";
  }
  rpc clear-bgp-instance-vrf-update-outq-update-group-sub-group-refresh-sub-group-update-parent {
    description
      "Choose a particular BGP instance.
       Specify a VRF.
       Clear Update information (Do NOT execute without cisco support)(cisco-support).
       Clear Update generation OutQ counters (Do NOT execute without cisco support)(cisco-support).
       Update-group.
       Sub-group.
       Update parents' OutQ counters too.
      ";
    input {
      leaf instance-name {
        type instance-name;
        mandatory true;
        description
          "instance name or all";
      }
      leaf vrf-all {
        type vrf-name;
        mandatory true;
        description
          "VRF name or all";
      }
      leaf update-group {
        type update-group-id;
        mandatory true;
        description
          "Update-group process ID <x.y>";
      }
      leaf refresh-sub-group {
        type refresh-sub-group-id;
        mandatory true;
        description
          "Refresh Sub-group process ID <x.y:z>";
      }
    }
    csc:xr-task "bgp";
    csc:cli-command "clear bgp instance <instance-name> vrf <vrf-all> update outq update-group <update-group> sub-group <refresh-sub-group> update-parent";
  }
  rpc clear-bgp-instance-vrf-update-outq-update-group-sub-group-refresh-sub-group {
    description
      "Choose a particular BGP instance.
       Specify a VRF.
       Clear Update information (Do NOT execute without cisco support)(cisco-support).
       Clear Update generation OutQ counters (Do NOT execute without cisco support)(cisco-support).
       Update-group.
       Sub-group.
      ";
    input {
      leaf instance-name {
        type instance-name;
        mandatory true;
        description
          "instance name or all";
      }
      leaf vrf-all {
        type vrf-name;
        mandatory true;
        description
          "VRF name or all";
      }
      leaf update-group {
        type update-group-id;
        mandatory true;
        description
          "Update-group process ID <x.y>";
      }
      leaf refresh-sub-group {
        type refresh-sub-group-id;
        mandatory true;
        description
          "Refresh Sub-group process ID <x.y:z>";
      }
    }
    csc:xr-task "bgp";
    csc:cli-command "clear bgp instance <instance-name> vrf <vrf-all> update outq update-group <update-group> sub-group <refresh-sub-group>";
  }
  rpc clear-bgp-instance-vrf-update-outq-update-group-update-parent {
    description
      "Choose a particular BGP instance.
       Specify a VRF.
       Clear Update information (Do NOT execute without cisco support)(cisco-support).
       Clear Update generation OutQ counters (Do NOT execute without cisco support)(cisco-support).
       Update-group.
       Update parents' OutQ counters too.
      ";
    input {
      leaf instance-name {
        type instance-name;
        mandatory true;
        description
          "instance name or all";
      }
      leaf vrf-all {
        type vrf-name;
        mandatory true;
        description
          "VRF name or all";
      }
      leaf update-group {
        type update-group-id;
        mandatory true;
        description
          "Update-group process ID <x.y>";
      }
    }
    csc:xr-task "bgp";
    csc:cli-command "clear bgp instance <instance-name> vrf <vrf-all> update outq update-group <update-group> update-parent";
  }
  rpc clear-bgp-instance-vrf-update-outq-update-group {
    description
      "Choose a particular BGP instance.
       Specify a VRF.
       Clear Update information (Do NOT execute without cisco support)(cisco-support).
       Clear Update generation OutQ counters (Do NOT execute without cisco support)(cisco-support).
       Update-group.
      ";
    input {
      leaf instance-name {
        type instance-name;
        mandatory true;
        description
          "instance name or all";
      }
      leaf vrf-all {
        type vrf-name;
        mandatory true;
        description
          "VRF name or all";
      }
      leaf update-group {
        type update-group-id;
        mandatory true;
        description
          "Update-group process ID <x.y>";
      }
    }
    csc:xr-task "bgp";
    csc:cli-command "clear bgp instance <instance-name> vrf <vrf-all> update outq update-group <update-group>";
  }
  rpc clear-bgp-afi-safi-dampening-ipv4-prefix {
    description
      "Clear route flap dampening information.\n";
    input {
      leaf afi-safi-name {
        type afi-safi-type;
        mandatory true;
        description
          "AFI and SAFI";
      }
      leaf ipv4-prefix {
        type inet:ipv4-prefix;
        mandatory true;
        description
          "IPv4 Network and mask or masklength to clear dampening information";
      }
    }
    csc:xr-task "bgp";
    csc:cli-command "clear bgp <afi-safi-name> dampening <ipv4-prefix>";
  }
  rpc clear-bgp-afi-safi-flap-statistics-ipv4-prefix {
    description
      "Clear flap statistics.\n";
    input {
      leaf afi-safi-name {
        type afi-safi-type;
        mandatory true;
        description
          "AFI and SAFI";
      }
      leaf ipv4-prefix {
        type inet:ipv4-prefix;
        mandatory true;
        description
          "IPv4 Network and mask or masklength to clear flap statistics";
      }
    }
    csc:xr-task "bgp";
    csc:cli-command "clear bgp <afi-safi-name> flap-statistics <ipv4-prefix>";
  }
  rpc clear-bgp-afi-safi-dampening-ipv6-prefix {
    description
      "Clear route flap dampening information.\n";
    input {
      leaf afi-safi-name {
        type afi-safi-type;
        mandatory true;
        description
          "AFI and SAFI";
      }
      leaf ipv6-prefix {
        type inet:ipv6-prefix;
        mandatory true;
        description
          "IPv6 Network and mask or masklength to clear dampening information";
      }
    }
    csc:xr-task "bgp";
    csc:cli-command "clear bgp <afi-safi-name> dampening <ipv6-prefix>";
  }
  rpc clear-bgp-afi-safi-flap-statistics-ipv6-prefix {
    description
      "Clear flap statistics.\n";
    input {
      leaf afi-safi-name {
        type afi-safi-type;
        mandatory true;
        description
          "AFI and SAFI";
      }
      leaf ipv6-prefix {
        type inet:ipv6-prefix;
        mandatory true;
        description
          "IPv6 Network and mask or masklength to clear flap statistics";
      }
    }
    csc:xr-task "bgp";
    csc:cli-command "clear bgp <afi-safi-name> flap-statistics <ipv6-prefix>";
  }
  rpc clear-bgp-nexthop-performance-statistics {
    description
      "Clear nexthop.
       Performance statistics information related to processing.
      ";
    csc:xr-task "bgp";
    csc:cli-command "clear bgp nexthop performance-statistics";
  }
  rpc clear-bgp-nexthop-registration-ip-addr {
    description
      "Clear nexthop.
       Registration with RIB and reregister.
      ";
    input {
      leaf ip-addr {
        type inet:ip-address;
        mandatory true;
        description
          "Nexthop address";
      }
    }
    csc:xr-task "bgp";
    csc:cli-command "clear bgp nexthop registration <ip-addr>";
  }
  rpc clear-bgp-peer-drops-all {
    description
      "Clear established/dropped counters for a peer.
       All Neighbors.
      ";
    csc:xr-task "bgp";
    csc:cli-command "clear bgp peer-drops *";
  }
  rpc clear-bgp-peer-drops-ip-addr {
    description
      "Clear established/dropped counters for a peer.\n";
    input {
      leaf ip-addr {
        type inet:ip-address;
        mandatory true;
        description
          "BGP neighbor IP address";
      }
    }
    csc:xr-task "bgp";
    csc:cli-command "clear bgp peer-drops <ip-addr>";
  }
  rpc clear-bgp-performance-statistics {
    description
      "Clear performance statistics.\n";
    csc:xr-task "bgp";
    csc:cli-command "clear bgp performance-statistics";
  }
  rpc clear-bgp-rpki-server-all-serial-query {
    description
      "RPKI clear command.
       clear RPKI cache-server.
       clear all RPKI cache-servers.
       send serial-queries to all cache-servers (with latest serial numbers).
      ";
    csc:xr-task "bgp";
    csc:cli-command "clear bgp rpki server * serial-query";
  }
  rpc clear-bgp-rpki-server-all {
    description
      "RPKI clear command.
       clear RPKI cache-server.
       clear all RPKI cache-servers.
      ";
    csc:xr-task "bgp";
    csc:cli-command "clear bgp rpki server *";
  }
  rpc clear-bgp-rpki-server-rpki-server {
    description
      "RPKI clear command.
       clear RPKI cache-server.
      ";
    input {
      leaf rpki-server {
        type string;
        mandatory true;
        description
          "clear a specific RPKI cache-server (hostname or IP address)";
      }
    }
    csc:xr-task "bgp";
    csc:cli-command "clear bgp rpki server <rpki-server>";
  }
  rpc clear-bgp-rpki-validation-ipv4 {
    description
      "RPKI clear command.
       clear RPKI origin-validation (trigger origin validation).
       trigger origin validation walk for the IPv4 table.
      ";
    csc:xr-task "bgp";
    csc:cli-command "clear bgp rpki validation ipv4";
  }
  rpc clear-bgp-rpki-validation-ipv6 {
    description
      "RPKI clear command.
       clear RPKI origin-validation (trigger origin validation).
       trigger origin validation walk for the IPv6 table.
      ";
    csc:xr-task "bgp";
    csc:cli-command "clear bgp rpki validation ipv6";
  }
  rpc clear-bgp-rpki-validation {
    description
      "RPKI clear command.
       clear RPKI origin-validation (trigger origin validation).
      ";
    csc:xr-task "bgp";
    csc:cli-command "clear bgp rpki validation";
  }
  rpc clear-bgp-shutdown {
    description
      "Clear all peers which were shut down due to low memory.\n";
    csc:xr-task "bgp";
    csc:cli-command "clear bgp shutdown";
  }
  rpc clear-bgp-update-outq-address-family-update-parent {
    description
      "Clear Update information (Do NOT execute without cisco support)(cisco-support).
       Clear Update generation OutQ counters (Do NOT execute without cisco support)(cisco-support).
       Address-family.
       Update parents' OutQ counters too.
      ";
    csc:xr-task "bgp";
    csc:cli-command "clear bgp update outq address-family update-parent";
  }
  rpc clear-bgp-update-outq-address-family {
    description
      "Clear Update information (Do NOT execute without cisco support)(cisco-support).
       Clear Update generation OutQ counters (Do NOT execute without cisco support)(cisco-support).
       Address-family.
      ";
    csc:xr-task "bgp";
    csc:cli-command "clear bgp update outq address-family";
  }
  rpc clear-bgp-update-outq-neighbor-ip-addr-refresh-update-parent {
    description
      "Clear Update information (Do NOT execute without cisco support)(cisco-support).
       Clear Update generation OutQ counters (Do NOT execute without cisco support)(cisco-support).
       Neighbor.
       Refresh OutQ.
       Update parents' OutQ counters too.
      ";
    input {
      leaf ip-addr {
        type inet:ip-address;
        mandatory true;
        description
          "Neighbor address";
      }
    }
    csc:xr-task "bgp";
    csc:cli-command "clear bgp update outq neighbor <ip-addr> refresh update-parent";
  }
  rpc clear-bgp-update-outq-neighbor-ip-addr-refresh {
    description
      "Clear Update information (Do NOT execute without cisco support)(cisco-support).
       Clear Update generation OutQ counters (Do NOT execute without cisco support)(cisco-support).
       Neighbor.
       Refresh OutQ.
      ";
    input {
      leaf ip-addr {
        type inet:ip-address;
        mandatory true;
        description
          "Neighbor address";
      }
    }
    csc:xr-task "bgp";
    csc:cli-command "clear bgp update outq neighbor <ip-addr> refresh";
  }
  rpc clear-bgp-update-outq-neighbor-ip-addr-update-parent {
    description
      "Clear Update information (Do NOT execute without cisco support)(cisco-support).
       Clear Update generation OutQ counters (Do NOT execute without cisco support)(cisco-support).
       Neighbor.
       Update parents' OutQ counters too.
      ";
    input {
      leaf ip-addr {
        type inet:ip-address;
        mandatory true;
        description
          "Neighbor address";
      }
    }
    csc:xr-task "bgp";
    csc:cli-command "clear bgp update outq neighbor <ip-addr> update-parent";
  }
  rpc clear-bgp-update-outq-neighbor-ip-addr {
    description
      "Clear Update information (Do NOT execute without cisco support)(cisco-support).
       Clear Update generation OutQ counters (Do NOT execute without cisco support)(cisco-support).
       Neighbor.
      ";
    input {
      leaf ip-addr {
        type inet:ip-address;
        mandatory true;
        description
          "Neighbor address";
      }
    }
    csc:xr-task "bgp";
    csc:cli-command "clear bgp update outq neighbor <ip-addr>";
  }
  rpc clear-bgp-update-outq-process {
    description
      "Clear Update information (Do NOT execute without cisco support)(cisco-support).
       Clear Update generation OutQ counters (Do NOT execute without cisco support)(cisco-support).
       Process.
      ";
    csc:xr-task "bgp";
    csc:cli-command "clear bgp update outq process";
  }
  rpc clear-bgp-update-outq-update-group-sub-group-update-parent {
    description
      "Clear Update information (Do NOT execute without cisco support)(cisco-support).
       Clear Update generation OutQ counters (Do NOT execute without cisco support)(cisco-support).
       Update-group.
       Sub-group.
       Update parents' OutQ counters too.
      ";
    input {
      leaf update-group {
        type update-group-id;
        mandatory true;
        description
          "Update-group process ID <x.y>";
      }
      leaf sub-group {
        type update-group-id;
        mandatory true;
        description
          "Sub-group process ID <x.y>";
      }
    }
    csc:xr-task "bgp";
    csc:cli-command "clear bgp update outq update-group <update-group> sub-group <sub-group> update-parent";
  }
  rpc clear-bgp-update-outq-update-group-sub-group {
    description
      "Clear Update information (Do NOT execute without cisco support)(cisco-support).
       Clear Update generation OutQ counters (Do NOT execute without cisco support)(cisco-support).
       Update-group.
       Sub-group.
      ";
    input {
      leaf update-group {
        type update-group-id;
        mandatory true;
        description
          "Update-group process ID <x.y>";
      }
      leaf sub-group {
        type update-group-id;
        mandatory true;
        description
          "Sub-group process ID <x.y>";
      }
    }
    csc:xr-task "bgp";
    csc:cli-command "clear bgp update outq update-group <update-group> sub-group <sub-group>";
  }
  rpc clear-bgp-update-outq-update-group-sub-group-refresh-sub-group-update-parent {
    description
      "Clear Update information (Do NOT execute without cisco support)(cisco-support).
       Clear Update generation OutQ counters (Do NOT execute without cisco support)(cisco-support).
       Update-group.
       Sub-group.
       Update parents' OutQ counters too.
      ";
    input {
      leaf update-group {
        type update-group-id;
        mandatory true;
        description
          "Update-group process ID <x.y>";
      }
      leaf refresh-sub-group {
        type refresh-sub-group-id;
        mandatory true;
        description
          "Refresh Sub-group process ID <x.y:z>";
      }
    }
    csc:xr-task "bgp";
    csc:cli-command "clear bgp update outq update-group <update-group> sub-group <refresh-sub-group> update-parent";
  }
  rpc clear-bgp-update-outq-update-group-sub-group-refresh-sub-group {
    description
      "Clear Update information (Do NOT execute without cisco support)(cisco-support).
       Clear Update generation OutQ counters (Do NOT execute without cisco support)(cisco-support).
       Update-group.
       Sub-group.
      ";
    input {
      leaf update-group {
        type update-group-id;
        mandatory true;
        description
          "Update-group process ID <x.y>";
      }
      leaf refresh-sub-group {
        type refresh-sub-group-id;
        mandatory true;
        description
          "Refresh Sub-group process ID <x.y:z>";
      }
    }
    csc:xr-task "bgp";
    csc:cli-command "clear bgp update outq update-group <update-group> sub-group <refresh-sub-group>";
  }
  rpc clear-bgp-update-outq-update-group-update-parent {
    description
      "Clear Update information (Do NOT execute without cisco support)(cisco-support).
       Clear Update generation OutQ counters (Do NOT execute without cisco support)(cisco-support).
       Update-group.
       Update parents' OutQ counters too.
      ";
    input {
      leaf update-group {
        type update-group-id;
        mandatory true;
        description
          "Update-group process ID <x.y>";
      }
    }
    csc:xr-task "bgp";
    csc:cli-command "clear bgp update outq update-group <update-group> update-parent";
  }
  rpc clear-bgp-update-outq-update-group {
    description
      "Clear Update information (Do NOT execute without cisco support)(cisco-support).
       Clear Update generation OutQ counters (Do NOT execute without cisco support)(cisco-support).
       Update-group.
      ";
    input {
      leaf update-group {
        type update-group-id;
        mandatory true;
        description
          "Update-group process ID <x.y>";
      }
    }
    csc:xr-task "bgp";
    csc:cli-command "clear bgp update outq update-group <update-group>";
  }
  rpc clear-bgp-version-ip-addr-ip-netmask {
    description
      "clear BGP prefix version.\n";
    input {
      leaf ip-addr {
        type inet:ip-address;
        mandatory true;
        description
          "Network";
      }
      leaf ip-netmask {
        type ip-netmask;
        mandatory true;
        description
          "Mask";
      }
    }
    csc:xr-task "bgp";
    csc:cli-command "clear bgp version <ip-addr> <ip-netmask>";
  }
  rpc clear-bgp-version-ip-addr {
    description
      "clear BGP prefix version.\n";
    input {
      leaf ip-addr {
        type inet:ip-address;
        mandatory true;
        description
          "Network";
      }
    }
    csc:xr-task "bgp";
    csc:cli-command "clear bgp version <ip-addr>";
  }
  rpc clear-bgp-version-ip-prefix {
    description
      "clear BGP prefix version.\n";
    input {
      leaf ip-prefix {
        type inet:ip-prefix;
        mandatory true;
        description
          "Network and masklength";
      }
    }
    csc:xr-task "bgp";
    csc:cli-command "clear bgp version <ip-prefix>";
  }
  rpc clear-bgp-version-afi-safi-ip-addr-ip-netmask {
    description
      "clear BGP prefix version.\n";
    input {
      leaf afi-safi-name {
        type afi-safi-type;
        mandatory true;
        description
          "AFI and SAFI";
      }
      leaf ip-addr {
        type inet:ip-address;
        mandatory true;
        description
          "Network";
      }
      leaf ip-netmask {
        type ip-netmask;
        mandatory true;
        description
          "Mask";
      }
    }
    csc:xr-task "bgp";
    csc:cli-command "clear bgp version <afi-safi-name> <ip-addr> <ip-netmask>";
  }
  rpc clear-bgp-version-afi-safi-ip-addr {
    description
      "clear BGP prefix version.\n";
    input {
      leaf afi-safi-name {
        type afi-safi-type;
        mandatory true;
        description
          "AFI and SAFI";
      }
      leaf ip-addr {
        type inet:ip-address;
        mandatory true;
        description
          "Network";
      }
    }
    csc:xr-task "bgp";
    csc:cli-command "clear bgp version <afi-safi-name> <ip-addr>";
  }
  rpc clear-bgp-version-afi-safi-ip-prefix {
    description
      "clear BGP prefix version.\n";
    input {
      leaf afi-safi-name {
        type afi-safi-type;
        mandatory true;
        description
          "AFI and SAFI";
      }
      leaf ip-prefix {
        type inet:ip-prefix;
        mandatory true;
        description
          "Network and masklength";
      }
    }
    csc:xr-task "bgp";
    csc:cli-command "clear bgp version <afi-safi-name> <ip-prefix>";
  }
  rpc clear-bgp-version-afi-safi-bridge-domain-ip-addr-ip-netmask {
    description
      "clear BGP prefix version.
       Display routes for a specified Bridge Domain.
      ";
    input {
      leaf afi-safi-name {
        type afi-safi-type;
        mandatory true;
        description
          "AFI and SAFI";
      }
      leaf bridge-domain-name {
        type string;
        mandatory true;
        description
          "Bridge Domain";
      }
      leaf ip-addr {
        type inet:ip-address;
        mandatory true;
        description
          "Network";
      }
      leaf ip-netmask {
        type ip-netmask;
        mandatory true;
        description
          "Mask";
      }
    }
    csc:xr-task "bgp";
    csc:cli-command "clear bgp version <afi-safi-name> bridge-domain <bridge-domain-name> <ip-addr> <ip-netmask>";
  }
  rpc clear-bgp-version-afi-safi-bridge-domain-ip-addr {
    description
      "clear BGP prefix version.
       Display routes for a specified Bridge Domain.
      ";
    input {
      leaf afi-safi-name {
        type afi-safi-type;
        mandatory true;
        description
          "AFI and SAFI";
      }
      leaf bridge-domain-name {
        type string;
        mandatory true;
        description
          "Bridge Domain";
      }
      leaf ip-addr {
        type inet:ip-address;
        mandatory true;
        description
          "Network";
      }
    }
    csc:xr-task "bgp";
    csc:cli-command "clear bgp version <afi-safi-name> bridge-domain <bridge-domain-name> <ip-addr>";
  }
  rpc clear-bgp-version-afi-safi-bridge-domain-ip-prefix {
    description
      "clear BGP prefix version.
       Display routes for a specified Bridge Domain.
      ";
    input {
      leaf afi-safi-name {
        type afi-safi-type;
        mandatory true;
        description
          "AFI and SAFI";
      }
      leaf bridge-domain-name {
        type string;
        mandatory true;
        description
          "Bridge Domain";
      }
      leaf ip-prefix {
        type inet:ip-prefix;
        mandatory true;
        description
          "Network and masklength";
      }
    }
    csc:xr-task "bgp";
    csc:cli-command "clear bgp version <afi-safi-name> bridge-domain <bridge-domain-name> <ip-prefix>";
  }
  rpc clear-bgp-version-afi-safi-rd-ip-addr-ip-netmask {
    description
      "clear BGP prefix version.
       Display routes with a specific route distinguisher.
      ";
    input {
      leaf afi-safi-name {
        type afi-safi-type;
        mandatory true;
        description
          "AFI and SAFI";
      }
      leaf rd {
        type rd;
        mandatory true;
        description
          "Route distinguisher";
      }
      leaf ip-addr {
        type inet:ip-address;
        mandatory true;
        description
          "Network";
      }
      leaf ip-netmask {
        type ip-netmask;
        mandatory true;
        description
          "Mask";
      }
    }
    csc:xr-task "bgp";
    csc:cli-command "clear bgp version <afi-safi-name> rd <rd> <ip-addr> <ip-netmask>";
  }
  rpc clear-bgp-version-afi-safi-rd-ip-addr {
    description
      "clear BGP prefix version.
       Display routes with a specific route distinguisher.
      ";
    input {
      leaf afi-safi-name {
        type afi-safi-type;
        mandatory true;
        description
          "AFI and SAFI";
      }
      leaf rd {
        type rd;
        mandatory true;
        description
          "Route distinguisher";
      }
      leaf ip-addr {
        type inet:ip-address;
        mandatory true;
        description
          "Network";
      }
    }
    csc:xr-task "bgp";
    csc:cli-command "clear bgp version <afi-safi-name> rd <rd> <ip-addr>";
  }
  rpc clear-bgp-version-afi-safi-rd-ip-prefix {
    description
      "clear BGP prefix version.
       Display routes with a specific route distinguisher.
      ";
    input {
      leaf afi-safi-name {
        type afi-safi-type;
        mandatory true;
        description
          "AFI and SAFI";
      }
      leaf rd {
        type rd;
        mandatory true;
        description
          "Route distinguisher";
      }
      leaf ip-prefix {
        type inet:ip-prefix;
        mandatory true;
        description
          "Network and masklength";
      }
    }
    csc:xr-task "bgp";
    csc:cli-command "clear bgp version <afi-safi-name> rd <rd> <ip-prefix>";
  }
  rpc clear-bgp-version-afi-safi-ipv4-addr-ipv4-mask {
    description
      "clear BGP prefix version.\n";
    input {
      leaf afi-safi-name {
        type afi-safi-type;
        mandatory true;
        description
          "AFI and SAFI";
      }
      leaf ipv4-addr {
        type inet:ipv4-address;
        mandatory true;
        description
          "IPv4 network";
      }
      leaf ipv4-mask {
        type ipv4-netmask;
        mandatory true;
        description
          "IPv4 mask";
      }
    }
    csc:xr-task "bgp";
    csc:cli-command "clear bgp version <afi-safi-name> <ipv4-addr> <ipv4-mask>";
  }
  rpc clear-bgp-version-afi-safi-ipv4-addr {
    description
      "clear BGP prefix version.\n";
    input {
      leaf afi-safi-name {
        type afi-safi-type;
        mandatory true;
        description
          "AFI and SAFI";
      }
      leaf ipv4-addr {
        type inet:ipv4-address;
        mandatory true;
        description
          "IPv4 network";
      }
    }
    csc:xr-task "bgp";
    csc:cli-command "clear bgp version <afi-safi-name> <ipv4-addr>";
  }
  rpc clear-bgp-version-afi-safi-ipv4-prefix {
    description
      "clear BGP prefix version.\n";
    input {
      leaf afi-safi-name {
        type afi-safi-type;
        mandatory true;
        description
          "AFI and SAFI";
      }
      leaf ipv4-prefix {
        type inet:ipv4-prefix;
        mandatory true;
        description
          "IPv4 network and masklength";
      }
    }
    csc:xr-task "bgp";
    csc:cli-command "clear bgp version <afi-safi-name> <ipv4-prefix>";
  }
  rpc clear-bgp-version-afi-safi-rd-ipv4-addr {
    description
      "clear BGP prefix version.
       Display routes with a specific route distinguisher.
      ";
    input {
      leaf afi-safi-name {
        type afi-safi-type;
        mandatory true;
        description
          "AFI and SAFI";
      }
      leaf rd {
        type rd;
        mandatory true;
        description
          "Route distinguisher";
      }
      leaf ipv4-addr {
        type inet:ipv4-address;
        mandatory true;
        description
          "IPv4 MDT network";
      }
    }
    csc:xr-task "bgp";
    csc:cli-command "clear bgp version <afi-safi-name> rd <rd> <ipv4-addr>";
  }
  rpc clear-bgp-version-afi-safi-vrf-ipv4-addr {
    description
      "clear BGP prefix version.
       Display routes for a specified VRF.
      ";
    input {
      leaf afi-safi-name {
        type afi-safi-type;
        mandatory true;
        description
          "AFI and SAFI";
      }
      leaf vrf-name {
        type string;
        mandatory true;
        description
          "VRF name";
      }
      leaf ipv4-addr {
        type inet:ipv4-address;
        mandatory true;
        description
          "IPv4 MDT network";
      }
    }
    csc:xr-task "bgp";
    csc:cli-command "clear bgp version <afi-safi-name> vrf <vrf-name> <ipv4-addr>";
  }
  rpc clear-bgp-version-afi-safi-network {
    description
      "clear BGP prefix version.\n";
    input {
      leaf afi-safi-name {
        type afi-safi-type;
        mandatory true;
        description
          "AFI and SAFI";
      }
      leaf network {
        type string;
        mandatory true;
        description
          "Address family modifier specific network";
      }
    }
    csc:xr-task "bgp";
    csc:cli-command "clear bgp version <afi-safi-name> <network>";
  }
  rpc clear-bgp-version-afi-safi-rd-network {
    description
      "clear BGP prefix version.
       Display routes with a specific route distinguisher.
      ";
    input {
      leaf afi-safi-name {
        type afi-safi-type;
        mandatory true;
        description
          "AFI and SAFI";
      }
      leaf rd {
        type rd;
        mandatory true;
        description
          "Route distinguisher";
      }
      leaf network {
        type string;
        mandatory true;
        description
          "Address family modifier specific network";
      }
    }
    csc:xr-task "bgp";
    csc:cli-command "clear bgp version <afi-safi-name> rd <rd> <network>";
  }
  rpc clear-bgp-version-afi-safi-vrf-network {
    description
      "clear BGP prefix version.
       Display routes for a specified VRF.
      ";
    input {
      leaf afi-safi-name {
        type afi-safi-type;
        mandatory true;
        description
          "AFI and SAFI";
      }
      leaf vrf-name {
        type string;
        mandatory true;
        description
          "VRF name";
      }
      leaf network {
        type string;
        mandatory true;
        description
          "Address family modifier specific network";
      }
    }
    csc:xr-task "bgp";
    csc:cli-command "clear bgp version <afi-safi-name> vrf <vrf-name> <network>";
  }
  rpc clear-bgp-version-afi-safi-rt-constraint-network {
    description
      "clear BGP prefix version.\n";
    input {
      leaf afi-safi-name {
        type afi-safi-type;
        mandatory true;
        description
          "AFI and SAFI";
      }
      leaf rt-constraint-network {
        type string;
        mandatory true;
        description
          "RT-Constraint network";
      }
    }
    csc:xr-task "bgp";
    csc:cli-command "clear bgp version <afi-safi-name> <rt-constraint-network>";
  }
  rpc clear-bgp-version-afi-safi-ipv4-tunnel-network {
    description
      "clear BGP prefix version.\n";
    input {
      leaf afi-safi-name {
        type afi-safi-type;
        mandatory true;
        description
          "AFI and SAFI";
      }
      leaf ipv4-tunnel-network {
        type string;
        mandatory true;
        description
          "IPv4 Tunnel network <Tunnel-ID>:<IPv4 Address>";
      }
    }
    csc:xr-task "bgp";
    csc:cli-command "clear bgp version <afi-safi-name> <ipv4-tunnel-network>";
  }
  rpc clear-bgp-version-afi-safi-ipv6-addr-ipv6-netmask {
    description
      "clear BGP prefix version.\n";
    input {
      leaf afi-safi-name {
        type afi-safi-type;
        mandatory true;
        description
          "AFI and SAFI";
      }
      leaf ipv6-addr {
        type inet:ipv6-address;
        mandatory true;
        description
          "IPv6 network";
      }
      leaf ipv6-netmask {
        type ipv6-netmask;
        mandatory true;
        description
          "IPv6 mask";
      }
    }
    csc:xr-task "bgp";
    csc:cli-command "clear bgp version <afi-safi-name> <ipv6-addr> <ipv6-netmask>";
  }
  rpc clear-bgp-version-afi-safi-ipv6-addr {
    description
      "clear BGP prefix version.\n";
    input {
      leaf afi-safi-name {
        type afi-safi-type;
        mandatory true;
        description
          "AFI and SAFI";
      }
      leaf ipv6-addr {
        type inet:ipv6-address;
        mandatory true;
        description
          "IPv6 network";
      }
    }
    csc:xr-task "bgp";
    csc:cli-command "clear bgp version <afi-safi-name> <ipv6-addr>";
  }
  rpc clear-bgp-version-afi-safi-ipv6-prefix {
    description
      "clear BGP prefix version.\n";
    input {
      leaf afi-safi-name {
        type afi-safi-type;
        mandatory true;
        description
          "AFI and SAFI";
      }
      leaf ipv6-prefix {
        type inet:ipv6-prefix;
        mandatory true;
        description
          "IPv6 network and masklength";
      }
    }
    csc:xr-task "bgp";
    csc:cli-command "clear bgp version <afi-safi-name> <ipv6-prefix>";
  }
  rpc clear-bgp-version-afi-safi-rd {
    description
      "clear BGP prefix version.
       Display routes with a specific route distinguisher.
      ";
    input {
      leaf afi-safi-name {
        type afi-safi-type;
        mandatory true;
        description
          "AFI and SAFI";
      }
      leaf rd {
        type rd;
        mandatory true;
        description
          "Route distinguisher";
      }
    }
    csc:xr-task "bgp";
    csc:cli-command "clear bgp version <afi-safi-name> rd <rd>";
  }
  rpc clear-bgp-version-afi-safi-vrf {
    description
      "clear BGP prefix version.
       Display routes for a specified VRF.
      ";
    input {
      leaf afi-safi-name {
        type afi-safi-type;
        mandatory true;
        description
          "AFI and SAFI";
      }
      leaf vrf-name {
        type string;
        mandatory true;
        description
          "VRF name";
      }
    }
    csc:xr-task "bgp";
    csc:cli-command "clear bgp version <afi-safi-name> vrf <vrf-name>";
  }
  rpc clear-bgp-version-afi-safi {
    description
      "clear BGP prefix version.\n";
    input {
      leaf afi-safi-name {
        type afi-safi-type;
        mandatory true;
        description
          "AFI and SAFI";
      }
    }
    csc:xr-task "bgp";
    csc:cli-command "clear bgp version <afi-safi-name>";
  }
  rpc clear-bgp-version-afi-safi-sr-policy-prefix {
    description
      "clear BGP prefix version.\n";
    input {
      leaf afi-safi-name {
        type afi-safi-type;
        mandatory true;
        description
          "AFI and SAFI";
      }
      leaf sr-policy-prefix {
        type string;
        mandatory true;
        description
          "SR Policy prefix";
      }
    }
    csc:xr-task "bgp";
    csc:cli-command "clear bgp version <afi-safi-name> <sr-policy-prefix>";
  }
  rpc clear-bgp-version-afi-safi-bridge-domain-ipv4-prefix {
    description
      "clear BGP prefix version.
       Display routes for a specified Bridge Domain.
      ";
    input {
      leaf afi-safi-name {
        type afi-safi-type;
        mandatory true;
        description
          "AFI and SAFI";
      }
      leaf bridge-domain-name {
        type string;
        mandatory true;
        description
          "Bridge Domain";
      }
      leaf ipv4-prefix {
        type inet:ipv4-prefix;
        mandatory true;
        description
          "L2VPN EVPN Prefix";
      }
    }
    csc:xr-task "bgp";
    csc:cli-command "clear bgp version <afi-safi-name> bridge-domain <bridge-domain-name> <ipv4-prefix>";
  }
  rpc clear-bgp-version-afi-safi-rd-ipv4-prefix {
    description
      "clear BGP prefix version.
       Display routes with a specific route distinguisher.
      ";
    input {
      leaf afi-safi-name {
        type afi-safi-type;
        mandatory true;
        description
          "AFI and SAFI";
      }
      leaf rd {
        type rd;
        mandatory true;
        description
          "Route distinguisher";
      }
      leaf ipv4-prefix {
        type inet:ipv4-prefix;
        mandatory true;
        description
          "L2VPN EVPN Prefix";
      }
    }
    csc:xr-task "bgp";
    csc:cli-command "clear bgp version <afi-safi-name> rd <rd> <ipv4-prefix>";
  }
  rpc clear-bgp-version-afi-safi-mp2mp-ipv4-prefix {
    description
      "clear BGP prefix version.
       Display routes for a specified Xconnect group:MP2MP.
      ";
    input {
      leaf afi-safi-name {
        type afi-safi-type;
        mandatory true;
        description
          "AFI and SAFI";
      }
      leaf mp2mp {
        type string;
        mandatory true;
        description
          "Xconnect Group:mp2mp";
      }
      leaf ipv4-prefix {
        type inet:ipv4-prefix;
        mandatory true;
        description
          "L2VPN VPWS Prefix";
      }
    }
    csc:xr-task "bgp";
    csc:cli-command "clear bgp version <afi-safi-name> mp2mp <mp2mp> <ipv4-prefix>";
  }
  rpc clear-bgp-version-afi-safi-vrf-ipv4-prefix {
    description
      "clear BGP prefix version.
       Display routes for a specified VRF.
      ";
    input {
      leaf afi-safi-name {
        type afi-safi-type;
        mandatory true;
        description
          "AFI and SAFI";
      }
      leaf vrf-name {
        type string;
        mandatory true;
        description
          "VRF name";
      }
      leaf ipv4-prefix {
        type inet:ipv4-prefix;
        mandatory true;
        description
          "VPN Fspec Prefix";
      }
    }
    csc:xr-task "bgp";
    csc:cli-command "clear bgp version <afi-safi-name> vrf <vrf-name> <ipv4-prefix>";
  }
  rpc clear-bgp-version-afi-safi-rd-ipv4-addr-ipv4-mask {
    description
      "clear BGP prefix version.
       Display routes with a specific route distinguisher.
      ";
    input {
      leaf afi-safi-name {
        type afi-safi-type;
        mandatory true;
        description
          "AFI and SAFI";
      }
      leaf rd {
        type rd;
        mandatory true;
        description
          "Route distinguisher";
      }
      leaf ipv4-addr {
        type inet:ipv4-address;
        mandatory true;
        description
          "IPv4 network";
      }
      leaf ipv4-mask {
        type ipv4-netmask;
        mandatory true;
        description
          "IPv4 mask";
      }
    }
    csc:xr-task "bgp";
    csc:cli-command "clear bgp version <afi-safi-name> rd <rd> <ipv4-addr> <ipv4-mask>";
  }
  rpc clear-bgp-version-afi-safi-vrf-ipv4-addr-ipv4-mask {
    description
      "clear BGP prefix version.
       Display routes for a specified VRF.
      ";
    input {
      leaf afi-safi-name {
        type afi-safi-type;
        mandatory true;
        description
          "AFI and SAFI";
      }
      leaf vrf-name {
        type string;
        mandatory true;
        description
          "VRF name";
      }
      leaf ipv4-addr {
        type inet:ipv4-address;
        mandatory true;
        description
          "IPv4 network";
      }
      leaf ipv4-mask {
        type ipv4-netmask;
        mandatory true;
        description
          "IPv4 mask";
      }
    }
    csc:xr-task "bgp";
    csc:cli-command "clear bgp version <afi-safi-name> vrf <vrf-name> <ipv4-addr> <ipv4-mask>";
  }
  rpc clear-bgp-version-afi-safi-rd-ipv6-addr-ipv6-netmask {
    description
      "clear BGP prefix version.
       Display routes with a specific route distinguisher.
      ";
    input {
      leaf afi-safi-name {
        type afi-safi-type;
        mandatory true;
        description
          "AFI and SAFI";
      }
      leaf rd {
        type rd;
        mandatory true;
        description
          "Route distinguisher";
      }
      leaf ipv6-addr {
        type inet:ipv6-address;
        mandatory true;
        description
          "IPv6 network";
      }
      leaf ipv6-netmask {
        type ipv6-netmask;
        mandatory true;
        description
          "IPv6 mask";
      }
    }
    csc:xr-task "bgp";
    csc:cli-command "clear bgp version <afi-safi-name> rd <rd> <ipv6-addr> <ipv6-netmask>";
  }
  rpc clear-bgp-version-afi-safi-rd-ipv6-addr {
    description
      "clear BGP prefix version.
       Display routes with a specific route distinguisher.
      ";
    input {
      leaf afi-safi-name {
        type afi-safi-type;
        mandatory true;
        description
          "AFI and SAFI";
      }
      leaf rd {
        type rd;
        mandatory true;
        description
          "Route distinguisher";
      }
      leaf ipv6-addr {
        type inet:ipv6-address;
        mandatory true;
        description
          "IPv6 network";
      }
    }
    csc:xr-task "bgp";
    csc:cli-command "clear bgp version <afi-safi-name> rd <rd> <ipv6-addr>";
  }
  rpc clear-bgp-version-afi-safi-rd-ipv6-prefix {
    description
      "clear BGP prefix version.
       Display routes with a specific route distinguisher.
      ";
    input {
      leaf afi-safi-name {
        type afi-safi-type;
        mandatory true;
        description
          "AFI and SAFI";
      }
      leaf rd {
        type rd;
        mandatory true;
        description
          "Route distinguisher";
      }
      leaf ipv6-prefix {
        type inet:ipv6-prefix;
        mandatory true;
        description
          "IPv6 network and masklength";
      }
    }
    csc:xr-task "bgp";
    csc:cli-command "clear bgp version <afi-safi-name> rd <rd> <ipv6-prefix>";
  }
  rpc clear-bgp-version-afi-safi-vrf-ipv6-addr-ipv6-netmask {
    description
      "clear BGP prefix version.
       Display routes for a specified VRF.
      ";
    input {
      leaf afi-safi-name {
        type afi-safi-type;
        mandatory true;
        description
          "AFI and SAFI";
      }
      leaf vrf-name {
        type string;
        mandatory true;
        description
          "VRF name";
      }
      leaf ipv6-addr {
        type inet:ipv6-address;
        mandatory true;
        description
          "IPv6 network";
      }
      leaf ipv6-netmask {
        type ipv6-netmask;
        mandatory true;
        description
          "IPv6 mask";
      }
    }
    csc:xr-task "bgp";
    csc:cli-command "clear bgp version <afi-safi-name> vrf <vrf-name> <ipv6-addr> <ipv6-netmask>";
  }
  rpc clear-bgp-version-afi-safi-vrf-ipv6-addr {
    description
      "clear BGP prefix version.
       Display routes for a specified VRF.
      ";
    input {
      leaf afi-safi-name {
        type afi-safi-type;
        mandatory true;
        description
          "AFI and SAFI";
      }
      leaf vrf-name {
        type string;
        mandatory true;
        description
          "VRF name";
      }
      leaf ipv6-addr {
        type inet:ipv6-address;
        mandatory true;
        description
          "IPv6 network";
      }
    }
    csc:xr-task "bgp";
    csc:cli-command "clear bgp version <afi-safi-name> vrf <vrf-name> <ipv6-addr>";
  }
  rpc clear-bgp-version-afi-safi-vrf-ipv6-prefix {
    description
      "clear BGP prefix version.
       Display routes for a specified VRF.
      ";
    input {
      leaf afi-safi-name {
        type afi-safi-type;
        mandatory true;
        description
          "AFI and SAFI";
      }
      leaf vrf-name {
        type string;
        mandatory true;
        description
          "VRF name";
      }
      leaf ipv6-prefix {
        type inet:ipv6-prefix;
        mandatory true;
        description
          "IPv6 network and masklength";
      }
    }
    csc:xr-task "bgp";
    csc:cli-command "clear bgp version <afi-safi-name> vrf <vrf-name> <ipv6-prefix>";
  }
  rpc clear-bgp-version-vrf-ip-addr-ip-netmask {
    description
      "clear BGP prefix version.
       Specify a VRF.
      ";
    input {
      leaf vrf-all {
        type vrf-name;
        mandatory true;
        description
          "VRF name or all";
      }
      leaf ip-addr {
        type inet:ip-address;
        mandatory true;
        description
          "Network";
      }
      leaf ip-netmask {
        type ip-netmask;
        mandatory true;
        description
          "Mask";
      }
    }
    csc:xr-task "bgp";
    csc:cli-command "clear bgp version vrf <vrf-all> <ip-addr> <ip-netmask>";
  }
  rpc clear-bgp-version-vrf-ip-addr {
    description
      "clear BGP prefix version.
       Specify a VRF.
      ";
    input {
      leaf vrf-all {
        type vrf-name;
        mandatory true;
        description
          "VRF name or all";
      }
      leaf ip-addr {
        type inet:ip-address;
        mandatory true;
        description
          "Network";
      }
    }
    csc:xr-task "bgp";
    csc:cli-command "clear bgp version vrf <vrf-all> <ip-addr>";
  }
  rpc clear-bgp-version-vrf-ip-prefix {
    description
      "clear BGP prefix version.
       Specify a VRF.
      ";
    input {
      leaf vrf-all {
        type vrf-name;
        mandatory true;
        description
          "VRF name or all";
      }
      leaf ip-prefix {
        type inet:ip-prefix;
        mandatory true;
        description
          "Network and masklength";
      }
    }
    csc:xr-task "bgp";
    csc:cli-command "clear bgp version vrf <vrf-all> <ip-prefix>";
  }
  rpc clear-bgp-version-vrf-afi-safi-ipv4-prefix {
    description
      "clear BGP prefix version.
       Specify a VRF.
      ";
    input {
      leaf vrf-all {
        type vrf-name;
        mandatory true;
        description
          "VRF name or all";
      }
      leaf afi-safi-name {
        type afi-safi-type;
        mandatory true;
        description
          "AFI and SAFI";
      }
      leaf ipv4-prefix {
        type inet:ipv4-prefix;
        mandatory true;
        description
          "Fspec IPv4 Prefix";
      }
    }
    csc:xr-task "bgp";
    csc:cli-command "clear bgp version vrf <vrf-all> <afi-safi-name> <ipv4-prefix>";
  }
  rpc clear-bgp-version-vrf-afi-safi-ipv4-addr-ipv4-mask {
    description
      "clear BGP prefix version.
       Specify a VRF.
      ";
    input {
      leaf vrf-all {
        type vrf-name;
        mandatory true;
        description
          "VRF name or all";
      }
      leaf afi-safi-name {
        type afi-safi-type;
        mandatory true;
        description
          "AFI and SAFI";
      }
      leaf ipv4-addr {
        type inet:ipv4-address;
        mandatory true;
        description
          "IPv4 network";
      }
      leaf ipv4-mask {
        type ipv4-netmask;
        mandatory true;
        description
          "IPv4 mask";
      }
    }
    csc:xr-task "bgp";
    csc:cli-command "clear bgp version vrf <vrf-all> <afi-safi-name> <ipv4-addr> <ipv4-mask>";
  }
  rpc clear-bgp-version-vrf-afi-safi-ipv4-addr {
    description
      "clear BGP prefix version.
       Specify a VRF.
      ";
    input {
      leaf vrf-all {
        type vrf-name;
        mandatory true;
        description
          "VRF name or all";
      }
      leaf afi-safi-name {
        type afi-safi-type;
        mandatory true;
        description
          "AFI and SAFI";
      }
      leaf ipv4-addr {
        type inet:ipv4-address;
        mandatory true;
        description
          "IPv4 network";
      }
    }
    csc:xr-task "bgp";
    csc:cli-command "clear bgp version vrf <vrf-all> <afi-safi-name> <ipv4-addr>";
  }
  rpc clear-bgp-version-vrf-afi-safi-network {
    description
      "clear BGP prefix version.
       Specify a VRF.
      ";
    input {
      leaf vrf-all {
        type vrf-name;
        mandatory true;
        description
          "VRF name or all";
      }
      leaf afi-safi-name {
        type afi-safi-type;
        mandatory true;
        description
          "AFI and SAFI";
      }
      leaf network {
        type string;
        mandatory true;
        description
          "Address family modifier specific network";
      }
    }
    csc:xr-task "bgp";
    csc:cli-command "clear bgp version vrf <vrf-all> <afi-safi-name> <network>";
  }
  rpc clear-bgp-version-vrf-afi-safi-rd-network {
    description
      "clear BGP prefix version.
       Specify a VRF.
       Display routes with a specific route distinguisher.
      ";
    input {
      leaf vrf-all {
        type vrf-name;
        mandatory true;
        description
          "VRF name or all";
      }
      leaf afi-safi-name {
        type afi-safi-type;
        mandatory true;
        description
          "AFI and SAFI";
      }
      leaf rd {
        type rd;
        mandatory true;
        description
          "Route distinguisher";
      }
      leaf network {
        type string;
        mandatory true;
        description
          "Address family modifier specific network";
      }
    }
    csc:xr-task "bgp";
    csc:cli-command "clear bgp version vrf <vrf-all> <afi-safi-name> rd <rd> <network>";
  }
  rpc clear-bgp-version-vrf-afi-safi-vrf-network {
    description
      "clear BGP prefix version.
       Specify a VRF.
       Display routes for a specified VRF.
      ";
    input {
      leaf vrf-all {
        type vrf-name;
        mandatory true;
        description
          "VRF name or all";
      }
      leaf afi-safi-name {
        type afi-safi-type;
        mandatory true;
        description
          "AFI and SAFI";
      }
      leaf vrf-name {
        type string;
        mandatory true;
        description
          "VRF name";
      }
      leaf network {
        type string;
        mandatory true;
        description
          "Address family modifier specific network";
      }
    }
    csc:xr-task "bgp";
    csc:cli-command "clear bgp version vrf <vrf-all> <afi-safi-name> vrf <vrf-name> <network>";
  }
  rpc clear-bgp-version-vrf-afi-safi-ipv6-addr-ipv6-netmask {
    description
      "clear BGP prefix version.
       Specify a VRF.
      ";
    input {
      leaf vrf-all {
        type vrf-name;
        mandatory true;
        description
          "VRF name or all";
      }
      leaf afi-safi-name {
        type afi-safi-type;
        mandatory true;
        description
          "AFI and SAFI";
      }
      leaf ipv6-addr {
        type inet:ipv6-address;
        mandatory true;
        description
          "IPv6 network";
      }
      leaf ipv6-netmask {
        type ipv6-netmask;
        mandatory true;
        description
          "IPv6 mask";
      }
    }
    csc:xr-task "bgp";
    csc:cli-command "clear bgp version vrf <vrf-all> <afi-safi-name> <ipv6-addr> <ipv6-netmask>";
  }
  rpc clear-bgp-version-vrf-afi-safi-ipv6-addr {
    description
      "clear BGP prefix version.
       Specify a VRF.
      ";
    input {
      leaf vrf-all {
        type vrf-name;
        mandatory true;
        description
          "VRF name or all";
      }
      leaf afi-safi-name {
        type afi-safi-type;
        mandatory true;
        description
          "AFI and SAFI";
      }
      leaf ipv6-addr {
        type inet:ipv6-address;
        mandatory true;
        description
          "IPv6 network";
      }
    }
    csc:xr-task "bgp";
    csc:cli-command "clear bgp version vrf <vrf-all> <afi-safi-name> <ipv6-addr>";
  }
  rpc clear-bgp-version-vrf-afi-safi-ipv6-prefix {
    description
      "clear BGP prefix version.
       Specify a VRF.
      ";
    input {
      leaf vrf-all {
        type vrf-name;
        mandatory true;
        description
          "VRF name or all";
      }
      leaf afi-safi-name {
        type afi-safi-type;
        mandatory true;
        description
          "AFI and SAFI";
      }
      leaf ipv6-prefix {
        type inet:ipv6-prefix;
        mandatory true;
        description
          "IPv6 network and masklength";
      }
    }
    csc:xr-task "bgp";
    csc:cli-command "clear bgp version vrf <vrf-all> <afi-safi-name> <ipv6-prefix>";
  }
  rpc clear-bgp-version-vrf-afi-safi-rd {
    description
      "clear BGP prefix version.
       Specify a VRF.
       Display routes with a specific route distinguisher.
      ";
    input {
      leaf vrf-all {
        type vrf-name;
        mandatory true;
        description
          "VRF name or all";
      }
      leaf afi-safi-name {
        type afi-safi-type;
        mandatory true;
        description
          "AFI and SAFI";
      }
      leaf rd {
        type rd;
        mandatory true;
        description
          "Route distinguisher";
      }
    }
    csc:xr-task "bgp";
    csc:cli-command "clear bgp version vrf <vrf-all> <afi-safi-name> rd <rd>";
  }
  rpc clear-bgp-version-vrf-afi-safi-vrf {
    description
      "clear BGP prefix version.
       Specify a VRF.
       Display routes for a specified VRF.
      ";
    input {
      leaf vrf-all {
        type vrf-name;
        mandatory true;
        description
          "VRF name or all";
      }
      leaf afi-safi-name {
        type afi-safi-type;
        mandatory true;
        description
          "AFI and SAFI";
      }
      leaf vrf-name {
        type string;
        mandatory true;
        description
          "VRF name";
      }
    }
    csc:xr-task "bgp";
    csc:cli-command "clear bgp version vrf <vrf-all> <afi-safi-name> vrf <vrf-name>";
  }
  rpc clear-bgp-version-vrf-afi-safi {
    description
      "clear BGP prefix version.
       Specify a VRF.
      ";
    input {
      leaf vrf-all {
        type vrf-name;
        mandatory true;
        description
          "VRF name or all";
      }
      leaf afi-safi-name {
        type afi-safi-type;
        mandatory true;
        description
          "AFI and SAFI";
      }
    }
    csc:xr-task "bgp";
    csc:cli-command "clear bgp version vrf <vrf-all> <afi-safi-name>";
  }
  rpc clear-bgp-vrf-all-graceful {
    description
      "Specify a VRF.
       Clear all peers and all routes from the BGP table.
       Clear with a hard reset and a graceful restart.
      ";
    input {
      leaf vrf-all {
        type vrf-name;
        mandatory true;
        description
          "VRF name or all";
      }
    }
    csc:xr-task "bgp";
    csc:cli-command "clear bgp vrf <vrf-all> * graceful";
  }
  rpc clear-bgp-vrf-all {
    description
      "Specify a VRF.
       Clear all peers and all routes from the BGP table.
      ";
    input {
      leaf vrf-all {
        type vrf-name;
        mandatory true;
        description
          "VRF name or all";
      }
    }
    csc:xr-task "bgp";
    csc:cli-command "clear bgp vrf <vrf-all> *";
  }
  rpc clear-bgp-vrf-ip-addr-graceful {
    description
      "Specify a VRF.
       Clear with a hard reset and a graceful restart.
      ";
    input {
      leaf vrf-all {
        type vrf-name;
        mandatory true;
        description
          "VRF name or all";
      }
      leaf ip-addr {
        type inet:ip-address;
        mandatory true;
        description
          "BGP neighbor address to clear";
      }
    }
    csc:xr-task "bgp";
    csc:cli-command "clear bgp vrf <vrf-all> <ip-addr> graceful";
  }
  rpc clear-bgp-vrf-ip-addr-long-lived-stale {
    description
      "Specify a VRF.
       Clear long-lived-stale routes.
      ";
    input {
      leaf vrf-all {
        type vrf-name;
        mandatory true;
        description
          "VRF name or all";
      }
      leaf ip-addr {
        type inet:ip-address;
        mandatory true;
        description
          "BGP neighbor address to clear";
      }
    }
    csc:xr-task "bgp";
    csc:cli-command "clear bgp vrf <vrf-all> <ip-addr> long-lived-stale";
  }
  rpc clear-bgp-vrf-ip-addr {
    description
      "Specify a VRF.\n";
    input {
      leaf vrf-all {
        type vrf-name;
        mandatory true;
        description
          "VRF name or all";
      }
      leaf ip-addr {
        type inet:ip-address;
        mandatory true;
        description
          "BGP neighbor address to clear";
      }
    }
    csc:xr-task "bgp";
    csc:cli-command "clear bgp vrf <vrf-all> <ip-addr>";
  }
  rpc clear-bgp-vrf-as-graceful {
    description
      "Specify a VRF.
       Clear peers in a specific AS.
       Clear with a hard reset and a graceful restart.
      ";
    input {
      leaf vrf-all {
        type vrf-name;
        mandatory true;
        description
          "VRF name or all";
      }
      leaf as-number {
        type as-number;
        mandatory true;
        description
          "AS number";
      }
    }
    csc:xr-task "bgp";
    csc:cli-command "clear bgp vrf <vrf-all> as <as-number> graceful";
  }
  rpc clear-bgp-vrf-as {
    description
      "Specify a VRF.
       Clear peers in a specific AS.
      ";
    input {
      leaf vrf-all {
        type vrf-name;
        mandatory true;
        description
          "VRF name or all";
      }
      leaf as-number {
        type as-number;
        mandatory true;
        description
          "AS number";
      }
    }
    csc:xr-task "bgp";
    csc:cli-command "clear bgp vrf <vrf-all> as <as-number>";
  }
  rpc clear-bgp-vrf-external-graceful {
    description
      "Specify a VRF.
       Clear all external peers.
       Clear with a hard reset and a graceful restart.
      ";
    input {
      leaf vrf-all {
        type vrf-name;
        mandatory true;
        description
          "VRF name or all";
      }
    }
    csc:xr-task "bgp";
    csc:cli-command "clear bgp vrf <vrf-all> external graceful";
  }
  rpc clear-bgp-vrf-external {
    description
      "Specify a VRF.
       Clear all external peers.
      ";
    input {
      leaf vrf-all {
        type vrf-name;
        mandatory true;
        description
          "VRF name or all";
      }
    }
    csc:xr-task "bgp";
    csc:cli-command "clear bgp vrf <vrf-all> external";
  }
  rpc clear-bgp-vrf-afi-safi-all-soft-in-prefix-filter {
    description
      "Specify a VRF.
       Clear all peers and all routes from the BGP table.
       Soft reconfig.
       Soft reconfig inbound update.
       Push out prefix ORF and do inbound soft reconfig.
      ";
    input {
      leaf vrf-all {
        type vrf-name;
        mandatory true;
        description
          "VRF name or all";
      }
      leaf afi-safi-name {
        type afi-safi-type;
        mandatory true;
        description
          "AFI and SAFI";
      }
    }
    csc:xr-task "bgp";
    csc:cli-command "clear bgp vrf <vrf-all> <afi-safi-name> * soft in prefix-filter";
  }
  rpc clear-bgp-vrf-afi-safi-all-soft-in {
    description
      "Specify a VRF.
       Clear all peers and all routes from the BGP table.
       Soft reconfig.
       Soft reconfig inbound update.
      ";
    input {
      leaf vrf-all {
        type vrf-name;
        mandatory true;
        description
          "VRF name or all";
      }
      leaf afi-safi-name {
        type afi-safi-type;
        mandatory true;
        description
          "AFI and SAFI";
      }
    }
    csc:xr-task "bgp";
    csc:cli-command "clear bgp vrf <vrf-all> <afi-safi-name> * soft in";
  }
  rpc clear-bgp-vrf-afi-safi-all-soft-out {
    description
      "Specify a VRF.
       Clear all peers and all routes from the BGP table.
       Soft reconfig.
       Soft reconfig outbound update.
      ";
    input {
      leaf vrf-all {
        type vrf-name;
        mandatory true;
        description
          "VRF name or all";
      }
      leaf afi-safi-name {
        type afi-safi-type;
        mandatory true;
        description
          "AFI and SAFI";
      }
    }
    csc:xr-task "bgp";
    csc:cli-command "clear bgp vrf <vrf-all> <afi-safi-name> * soft out";
  }
  rpc clear-bgp-vrf-afi-safi-all-soft {
    description
      "Specify a VRF.
       Clear all peers and all routes from the BGP table.
       Soft reconfig.
      ";
    input {
      leaf vrf-all {
        type vrf-name;
        mandatory true;
        description
          "VRF name or all";
      }
      leaf afi-safi-name {
        type afi-safi-type;
        mandatory true;
        description
          "AFI and SAFI";
      }
    }
    csc:xr-task "bgp";
    csc:cli-command "clear bgp vrf <vrf-all> <afi-safi-name> * soft";
  }
  rpc clear-bgp-vrf-afi-safi-ip-addr-long-lived-stale {
    description
      "Specify a VRF.
       Clear long-lived-stale routes.
      ";
    input {
      leaf vrf-all {
        type vrf-name;
        mandatory true;
        description
          "VRF name or all";
      }
      leaf afi-safi-name {
        type afi-safi-type;
        mandatory true;
        description
          "AFI and SAFI";
      }
      leaf ip-addr {
        type inet:ip-address;
        mandatory true;
        description
          "BGP neighbor address to clear";
      }
    }
    csc:xr-task "bgp";
    csc:cli-command "clear bgp vrf <vrf-all> <afi-safi-name> <ip-addr> long-lived-stale";
  }
  rpc clear-bgp-vrf-afi-safi-ip-addr-soft-in-prefix-filter {
    description
      "Specify a VRF.
       Soft reconfig.
       Soft reconfig inbound update.
       Push out prefix ORF and do inbound soft reconfig.
      ";
    input {
      leaf vrf-all {
        type vrf-name;
        mandatory true;
        description
          "VRF name or all";
      }
      leaf afi-safi-name {
        type afi-safi-type;
        mandatory true;
        description
          "AFI and SAFI";
      }
      leaf ip-addr {
        type inet:ip-address;
        mandatory true;
        description
          "BGP neighbor address to clear";
      }
    }
    csc:xr-task "bgp";
    csc:cli-command "clear bgp vrf <vrf-all> <afi-safi-name> <ip-addr> soft in prefix-filter";
  }
  rpc clear-bgp-vrf-afi-safi-ip-addr-soft-in {
    description
      "Specify a VRF.
       Soft reconfig.
       Soft reconfig inbound update.
      ";
    input {
      leaf vrf-all {
        type vrf-name;
        mandatory true;
        description
          "VRF name or all";
      }
      leaf afi-safi-name {
        type afi-safi-type;
        mandatory true;
        description
          "AFI and SAFI";
      }
      leaf ip-addr {
        type inet:ip-address;
        mandatory true;
        description
          "BGP neighbor address to clear";
      }
    }
    csc:xr-task "bgp";
    csc:cli-command "clear bgp vrf <vrf-all> <afi-safi-name> <ip-addr> soft in";
  }
  rpc clear-bgp-vrf-afi-safi-ip-addr-soft-out {
    description
      "Specify a VRF.
       Soft reconfig.
       Soft reconfig outbound update.
      ";
    input {
      leaf vrf-all {
        type vrf-name;
        mandatory true;
        description
          "VRF name or all";
      }
      leaf afi-safi-name {
        type afi-safi-type;
        mandatory true;
        description
          "AFI and SAFI";
      }
      leaf ip-addr {
        type inet:ip-address;
        mandatory true;
        description
          "BGP neighbor address to clear";
      }
    }
    csc:xr-task "bgp";
    csc:cli-command "clear bgp vrf <vrf-all> <afi-safi-name> <ip-addr> soft out";
  }
  rpc clear-bgp-vrf-afi-safi-ip-addr-soft {
    description
      "Specify a VRF.
       Soft reconfig.
      ";
    input {
      leaf vrf-all {
        type vrf-name;
        mandatory true;
        description
          "VRF name or all";
      }
      leaf afi-safi-name {
        type afi-safi-type;
        mandatory true;
        description
          "AFI and SAFI";
      }
      leaf ip-addr {
        type inet:ip-address;
        mandatory true;
        description
          "BGP neighbor address to clear";
      }
    }
    csc:xr-task "bgp";
    csc:cli-command "clear bgp vrf <vrf-all> <afi-safi-name> <ip-addr> soft";
  }
  rpc clear-bgp-vrf-afi-safi-as-soft-in-prefix-filter {
    description
      "Specify a VRF.
       Clear peers in a specific AS.
       Soft reconfig.
       Soft reconfig inbound update.
       Push out prefix ORF and do inbound soft reconfig.
      ";
    input {
      leaf vrf-all {
        type vrf-name;
        mandatory true;
        description
          "VRF name or all";
      }
      leaf afi-safi-name {
        type afi-safi-type;
        mandatory true;
        description
          "AFI and SAFI";
      }
      leaf as-number {
        type as-number;
        mandatory true;
        description
          "AS number";
      }
    }
    csc:xr-task "bgp";
    csc:cli-command "clear bgp vrf <vrf-all> <afi-safi-name> as <as-number> soft in prefix-filter";
  }
  rpc clear-bgp-vrf-afi-safi-as-soft-in {
    description
      "Specify a VRF.
       Clear peers in a specific AS.
       Soft reconfig.
       Soft reconfig inbound update.
      ";
    input {
      leaf vrf-all {
        type vrf-name;
        mandatory true;
        description
          "VRF name or all";
      }
      leaf afi-safi-name {
        type afi-safi-type;
        mandatory true;
        description
          "AFI and SAFI";
      }
      leaf as-number {
        type as-number;
        mandatory true;
        description
          "AS number";
      }
    }
    csc:xr-task "bgp";
    csc:cli-command "clear bgp vrf <vrf-all> <afi-safi-name> as <as-number> soft in";
  }
  rpc clear-bgp-vrf-afi-safi-as-soft-out {
    description
      "Specify a VRF.
       Clear peers in a specific AS.
       Soft reconfig.
       Soft reconfig outbound update.
      ";
    input {
      leaf vrf-all {
        type vrf-name;
        mandatory true;
        description
          "VRF name or all";
      }
      leaf afi-safi-name {
        type afi-safi-type;
        mandatory true;
        description
          "AFI and SAFI";
      }
      leaf as-number {
        type as-number;
        mandatory true;
        description
          "AS number";
      }
    }
    csc:xr-task "bgp";
    csc:cli-command "clear bgp vrf <vrf-all> <afi-safi-name> as <as-number> soft out";
  }
  rpc clear-bgp-vrf-afi-safi-as-soft {
    description
      "Specify a VRF.
       Clear peers in a specific AS.
       Soft reconfig.
      ";
    input {
      leaf vrf-all {
        type vrf-name;
        mandatory true;
        description
          "VRF name or all";
      }
      leaf afi-safi-name {
        type afi-safi-type;
        mandatory true;
        description
          "AFI and SAFI";
      }
      leaf as-number {
        type as-number;
        mandatory true;
        description
          "AS number";
      }
    }
    csc:xr-task "bgp";
    csc:cli-command "clear bgp vrf <vrf-all> <afi-safi-name> as <as-number> soft";
  }
  rpc clear-bgp-vrf-afi-safi-dampening-ipv4-prefix {
    description
      "Specify a VRF.
       Clear route flap dampening information.
      ";
    input {
      leaf vrf-all {
        type vrf-name;
        mandatory true;
        description
          "VRF name or all";
      }
      leaf afi-safi-name {
        type afi-safi-type;
        mandatory true;
        description
          "AFI and SAFI";
      }
      leaf ipv4-prefix {
        type inet:ipv4-prefix;
        mandatory true;
        description
          "IPv4 Network and mask or masklength to clear dampening information";
      }
    }
    csc:xr-task "bgp";
    csc:cli-command "clear bgp vrf <vrf-all> <afi-safi-name> dampening <ipv4-prefix>";
  }
  rpc clear-bgp-vrf-afi-safi-dampening {
    description
      "Specify a VRF.
       Clear route flap dampening information.
      ";
    input {
      leaf vrf-all {
        type vrf-name;
        mandatory true;
        description
          "VRF name or all";
      }
      leaf afi-safi-name {
        type afi-safi-type;
        mandatory true;
        description
          "AFI and SAFI";
      }
    }
    csc:xr-task "bgp";
    csc:cli-command "clear bgp vrf <vrf-all> <afi-safi-name> dampening";
  }
  rpc clear-bgp-vrf-afi-safi-external-soft-in-prefix-filter {
    description
      "Specify a VRF.
       Clear all external peers.
       Soft reconfig.
       Soft reconfig inbound update.
       Push out prefix ORF and do inbound soft reconfig.
      ";
    input {
      leaf vrf-all {
        type vrf-name;
        mandatory true;
        description
          "VRF name or all";
      }
      leaf afi-safi-name {
        type afi-safi-type;
        mandatory true;
        description
          "AFI and SAFI";
      }
    }
    csc:xr-task "bgp";
    csc:cli-command "clear bgp vrf <vrf-all> <afi-safi-name> external soft in prefix-filter";
  }
  rpc clear-bgp-vrf-afi-safi-external-soft-in {
    description
      "Specify a VRF.
       Clear all external peers.
       Soft reconfig.
       Soft reconfig inbound update.
      ";
    input {
      leaf vrf-all {
        type vrf-name;
        mandatory true;
        description
          "VRF name or all";
      }
      leaf afi-safi-name {
        type afi-safi-type;
        mandatory true;
        description
          "AFI and SAFI";
      }
    }
    csc:xr-task "bgp";
    csc:cli-command "clear bgp vrf <vrf-all> <afi-safi-name> external soft in";
  }
  rpc clear-bgp-vrf-afi-safi-external-soft-out {
    description
      "Specify a VRF.
       Clear all external peers.
       Soft reconfig.
       Soft reconfig outbound update.
      ";
    input {
      leaf vrf-all {
        type vrf-name;
        mandatory true;
        description
          "VRF name or all";
      }
      leaf afi-safi-name {
        type afi-safi-type;
        mandatory true;
        description
          "AFI and SAFI";
      }
    }
    csc:xr-task "bgp";
    csc:cli-command "clear bgp vrf <vrf-all> <afi-safi-name> external soft out";
  }
  rpc clear-bgp-vrf-afi-safi-external-soft {
    description
      "Specify a VRF.
       Clear all external peers.
       Soft reconfig.
      ";
    input {
      leaf vrf-all {
        type vrf-name;
        mandatory true;
        description
          "VRF name or all";
      }
      leaf afi-safi-name {
        type afi-safi-type;
        mandatory true;
        description
          "AFI and SAFI";
      }
    }
    csc:xr-task "bgp";
    csc:cli-command "clear bgp vrf <vrf-all> <afi-safi-name> external soft";
  }
  rpc clear-bgp-vrf-afi-safi-flap-statistics-ip-addr-ipv4-mask {
    description
      "Specify a VRF.
       Clear flap statistics.
      ";
    input {
      leaf vrf-all {
        type vrf-name;
        mandatory true;
        description
          "VRF name or all";
      }
      leaf afi-safi-name {
        type afi-safi-type;
        mandatory true;
        description
          "AFI and SAFI";
      }
      leaf ip-addr {
        type inet:ip-address;
        mandatory true;
        description
          "BGP neighbor address to clear";
      }
      leaf ipv4-mask {
        type ipv4-netmask;
        mandatory true;
        description
          "IPv4 Network and mask or masklength to clear flap statistics";
      }
    }
    csc:xr-task "bgp";
    csc:cli-command "clear bgp vrf <vrf-all> <afi-safi-name> flap-statistics <ip-addr> <ipv4-mask>";
  }
  rpc clear-bgp-vrf-afi-safi-flap-statistics-ip-addr {
    description
      "Specify a VRF.
       Clear flap statistics.
      ";
    input {
      leaf vrf-all {
        type vrf-name;
        mandatory true;
        description
          "VRF name or all";
      }
      leaf afi-safi-name {
        type afi-safi-type;
        mandatory true;
        description
          "AFI and SAFI";
      }
      leaf ip-addr {
        type inet:ip-address;
        mandatory true;
        description
          "BGP neighbor address to clear";
      }
    }
    csc:xr-task "bgp";
    csc:cli-command "clear bgp vrf <vrf-all> <afi-safi-name> flap-statistics <ip-addr>";
  }
  rpc clear-bgp-vrf-afi-safi-flap-statistics-ipv4-prefix {
    description
      "Specify a VRF.
       Clear flap statistics.
      ";
    input {
      leaf vrf-all {
        type vrf-name;
        mandatory true;
        description
          "VRF name or all";
      }
      leaf afi-safi-name {
        type afi-safi-type;
        mandatory true;
        description
          "AFI and SAFI";
      }
      leaf ipv4-prefix {
        type inet:ipv4-prefix;
        mandatory true;
        description
          "IPv4 Network and mask or masklength to clear flap statistics";
      }
    }
    csc:xr-task "bgp";
    csc:cli-command "clear bgp vrf <vrf-all> <afi-safi-name> flap-statistics <ipv4-prefix>";
  }
  rpc clear-bgp-vrf-afi-safi-flap-statistics-regexp {
    description
      "Specify a VRF.
       Clear flap statistics.
       Clear flap statistics for routes matching the regular expression.
      ";
    input {
      leaf vrf-all {
        type vrf-name;
        mandatory true;
        description
          "VRF name or all";
      }
      leaf afi-safi-name {
        type afi-safi-type;
        mandatory true;
        description
          "AFI and SAFI";
      }
      leaf regexp-pattern {
        type string;
        mandatory true;
        description
          "A regular expression to match the BGP AS paths.  Use 'ctrl-v ?' to enter '?'";
      }
    }
    csc:xr-task "bgp";
    csc:cli-command "clear bgp vrf <vrf-all> <afi-safi-name> flap-statistics regexp <regexp-pattern>";
  }
  rpc clear-bgp-vrf-afi-safi-flap-statistics-route-policy {
    description
      "Specify a VRF.
       Clear flap statistics.
       Clear flap statistics for routes matching the route policy.
      ";
    input {
      leaf vrf-all {
        type vrf-name;
        mandatory true;
        description
          "VRF name or all";
      }
      leaf afi-safi-name {
        type afi-safi-type;
        mandatory true;
        description
          "AFI and SAFI";
      }
      leaf route-policy-name {
        type string;
        mandatory true;
        description
          "Route Policy name";
      }
    }
    csc:xr-task "bgp";
    csc:cli-command "clear bgp vrf <vrf-all> <afi-safi-name> flap-statistics route-policy <route-policy-name>";
  }
  rpc clear-bgp-vrf-afi-safi-flap-statistics {
    description
      "Specify a VRF.
       Clear flap statistics.
      ";
    input {
      leaf vrf-all {
        type vrf-name;
        mandatory true;
        description
          "VRF name or all";
      }
      leaf afi-safi-name {
        type afi-safi-type;
        mandatory true;
        description
          "AFI and SAFI";
      }
    }
    csc:xr-task "bgp";
    csc:cli-command "clear bgp vrf <vrf-all> <afi-safi-name> flap-statistics";
  }
  rpc clear-bgp-vrf-afi-safi-nexthop-performance-statistics {
    description
      "Specify a VRF.
       Clear nexthop.
       Performance statistics information related to processing.
      ";
    input {
      leaf vrf-all {
        type vrf-name;
        mandatory true;
        description
          "VRF name or all";
      }
      leaf afi-safi-name {
        type afi-safi-type;
        mandatory true;
        description
          "AFI and SAFI";
      }
    }
    csc:xr-task "bgp";
    csc:cli-command "clear bgp vrf <vrf-all> <afi-safi-name> nexthop performance-statistics";
  }
  rpc clear-bgp-vrf-afi-safi-nexthop-registration-ip-addr {
    description
      "Specify a VRF.
       Clear nexthop.
       Registration with RIB and reregister.
      ";
    input {
      leaf vrf-all {
        type vrf-name;
        mandatory true;
        description
          "VRF name or all";
      }
      leaf afi-safi-name {
        type afi-safi-type;
        mandatory true;
        description
          "AFI and SAFI";
      }
      leaf ip-addr {
        type inet:ip-address;
        mandatory true;
        description
          "Nexthop address";
      }
    }
    csc:xr-task "bgp";
    csc:cli-command "clear bgp vrf <vrf-all> <afi-safi-name> nexthop registration <ip-addr>";
  }
  rpc clear-bgp-vrf-afi-safi-self-originated {
    description
      "Specify a VRF.
       Clear redistributed, network and aggregate routes originated here.
      ";
    input {
      leaf vrf-all {
        type vrf-name;
        mandatory true;
        description
          "VRF name or all";
      }
      leaf afi-safi-name {
        type afi-safi-type;
        mandatory true;
        description
          "AFI and SAFI";
      }
    }
    csc:xr-task "bgp";
    csc:cli-command "clear bgp vrf <vrf-all> <afi-safi-name> self-originated";
  }
  rpc clear-bgp-vrf-afi-safi-shutdown {
    description
      "Specify a VRF.
       Clear all peers which were shut down due to low memory.
      ";
    input {
      leaf vrf-all {
        type vrf-name;
        mandatory true;
        description
          "VRF name or all";
      }
      leaf afi-safi-name {
        type afi-safi-type;
        mandatory true;
        description
          "AFI and SAFI";
      }
    }
    csc:xr-task "bgp";
    csc:cli-command "clear bgp vrf <vrf-all> <afi-safi-name> shutdown";
  }
  rpc clear-bgp-vrf-afi-safi-update-outq-address-family-update-parent {
    description
      "Specify a VRF.
       Clear Update information (Do NOT execute without cisco support)(cisco-support).
       Clear Update generation OutQ counters (Do NOT execute without cisco support)(cisco-support).
       Address-family.
       Update parents' OutQ counters too.
      ";
    input {
      leaf vrf-all {
        type vrf-name;
        mandatory true;
        description
          "VRF name or all";
      }
      leaf afi-safi-name {
        type afi-safi-type;
        mandatory true;
        description
          "AFI and SAFI";
      }
    }
    csc:xr-task "bgp";
    csc:cli-command "clear bgp vrf <vrf-all> <afi-safi-name> update outq address-family update-parent";
  }
  rpc clear-bgp-vrf-afi-safi-update-outq-address-family {
    description
      "Specify a VRF.
       Clear Update information (Do NOT execute without cisco support)(cisco-support).
       Clear Update generation OutQ counters (Do NOT execute without cisco support)(cisco-support).
       Address-family.
      ";
    input {
      leaf vrf-all {
        type vrf-name;
        mandatory true;
        description
          "VRF name or all";
      }
      leaf afi-safi-name {
        type afi-safi-type;
        mandatory true;
        description
          "AFI and SAFI";
      }
    }
    csc:xr-task "bgp";
    csc:cli-command "clear bgp vrf <vrf-all> <afi-safi-name> update outq address-family";
  }
  rpc clear-bgp-vrf-afi-safi-update-outq-neighbor-ip-addr-refresh-update-parent {
    description
      "Specify a VRF.
       Clear Update information (Do NOT execute without cisco support)(cisco-support).
       Clear Update generation OutQ counters (Do NOT execute without cisco support)(cisco-support).
       Neighbor.
       Refresh OutQ.
       Update parents' OutQ counters too.
      ";
    input {
      leaf vrf-all {
        type vrf-name;
        mandatory true;
        description
          "VRF name or all";
      }
      leaf afi-safi-name {
        type afi-safi-type;
        mandatory true;
        description
          "AFI and SAFI";
      }
      leaf ip-addr {
        type inet:ip-address;
        mandatory true;
        description
          "Neighbor address";
      }
    }
    csc:xr-task "bgp";
    csc:cli-command "clear bgp vrf <vrf-all> <afi-safi-name> update outq neighbor <ip-addr> refresh update-parent";
  }
  rpc clear-bgp-vrf-afi-safi-update-outq-neighbor-ip-addr-refresh {
    description
      "Specify a VRF.
       Clear Update information (Do NOT execute without cisco support)(cisco-support).
       Clear Update generation OutQ counters (Do NOT execute without cisco support)(cisco-support).
       Neighbor.
       Refresh OutQ.
      ";
    input {
      leaf vrf-all {
        type vrf-name;
        mandatory true;
        description
          "VRF name or all";
      }
      leaf afi-safi-name {
        type afi-safi-type;
        mandatory true;
        description
          "AFI and SAFI";
      }
      leaf ip-addr {
        type inet:ip-address;
        mandatory true;
        description
          "Neighbor address";
      }
    }
    csc:xr-task "bgp";
    csc:cli-command "clear bgp vrf <vrf-all> <afi-safi-name> update outq neighbor <ip-addr> refresh";
  }
  rpc clear-bgp-vrf-afi-safi-update-outq-neighbor-ip-addr-update-parent {
    description
      "Specify a VRF.
       Clear Update information (Do NOT execute without cisco support)(cisco-support).
       Clear Update generation OutQ counters (Do NOT execute without cisco support)(cisco-support).
       Neighbor.
       Update parents' OutQ counters too.
      ";
    input {
      leaf vrf-all {
        type vrf-name;
        mandatory true;
        description
          "VRF name or all";
      }
      leaf afi-safi-name {
        type afi-safi-type;
        mandatory true;
        description
          "AFI and SAFI";
      }
      leaf ip-addr {
        type inet:ip-address;
        mandatory true;
        description
          "Neighbor address";
      }
    }
    csc:xr-task "bgp";
    csc:cli-command "clear bgp vrf <vrf-all> <afi-safi-name> update outq neighbor <ip-addr> update-parent";
  }
  rpc clear-bgp-vrf-afi-safi-update-outq-neighbor-ip-addr {
    description
      "Specify a VRF.
       Clear Update information (Do NOT execute without cisco support)(cisco-support).
       Clear Update generation OutQ counters (Do NOT execute without cisco support)(cisco-support).
       Neighbor.
      ";
    input {
      leaf vrf-all {
        type vrf-name;
        mandatory true;
        description
          "VRF name or all";
      }
      leaf afi-safi-name {
        type afi-safi-type;
        mandatory true;
        description
          "AFI and SAFI";
      }
      leaf ip-addr {
        type inet:ip-address;
        mandatory true;
        description
          "Neighbor address";
      }
    }
    csc:xr-task "bgp";
    csc:cli-command "clear bgp vrf <vrf-all> <afi-safi-name> update outq neighbor <ip-addr>";
  }
  rpc clear-bgp-vrf-afi-safi-update-outq-update-group-sub-group-update-parent {
    description
      "Specify a VRF.
       Clear Update information (Do NOT execute without cisco support)(cisco-support).
       Clear Update generation OutQ counters (Do NOT execute without cisco support)(cisco-support).
       Update-group.
       Sub-group.
       Update parents' OutQ counters too.
      ";
    input {
      leaf vrf-all {
        type vrf-name;
        mandatory true;
        description
          "VRF name or all";
      }
      leaf afi-safi-name {
        type afi-safi-type;
        mandatory true;
        description
          "AFI and SAFI";
      }
      leaf update-group {
        type update-group-id;
        mandatory true;
        description
          "Update-group process ID <x.y>";
      }
      leaf sub-group {
        type update-group-id;
        mandatory true;
        description
          "Sub-group process ID <x.y>";
      }
    }
    csc:xr-task "bgp";
    csc:cli-command "clear bgp vrf <vrf-all> <afi-safi-name> update outq update-group <update-group> sub-group <sub-group> update-parent";
  }
  rpc clear-bgp-vrf-afi-safi-update-outq-update-group-sub-group {
    description
      "Specify a VRF.
       Clear Update information (Do NOT execute without cisco support)(cisco-support).
       Clear Update generation OutQ counters (Do NOT execute without cisco support)(cisco-support).
       Update-group.
       Sub-group.
      ";
    input {
      leaf vrf-all {
        type vrf-name;
        mandatory true;
        description
          "VRF name or all";
      }
      leaf afi-safi-name {
        type afi-safi-type;
        mandatory true;
        description
          "AFI and SAFI";
      }
      leaf update-group {
        type update-group-id;
        mandatory true;
        description
          "Update-group process ID <x.y>";
      }
      leaf sub-group {
        type update-group-id;
        mandatory true;
        description
          "Sub-group process ID <x.y>";
      }
    }
    csc:xr-task "bgp";
    csc:cli-command "clear bgp vrf <vrf-all> <afi-safi-name> update outq update-group <update-group> sub-group <sub-group>";
  }
  rpc clear-bgp-vrf-afi-safi-update-outq-update-group-sub-group-refresh-sub-group-update-parent {
    description
      "Specify a VRF.
       Clear Update information (Do NOT execute without cisco support)(cisco-support).
       Clear Update generation OutQ counters (Do NOT execute without cisco support)(cisco-support).
       Update-group.
       Sub-group.
       Update parents' OutQ counters too.
      ";
    input {
      leaf vrf-all {
        type vrf-name;
        mandatory true;
        description
          "VRF name or all";
      }
      leaf afi-safi-name {
        type afi-safi-type;
        mandatory true;
        description
          "AFI and SAFI";
      }
      leaf update-group {
        type update-group-id;
        mandatory true;
        description
          "Update-group process ID <x.y>";
      }
      leaf refresh-sub-group {
        type refresh-sub-group-id;
        mandatory true;
        description
          "Refresh Sub-group process ID <x.y:z>";
      }
    }
    csc:xr-task "bgp";
    csc:cli-command "clear bgp vrf <vrf-all> <afi-safi-name> update outq update-group <update-group> sub-group <refresh-sub-group> update-parent";
  }
  rpc clear-bgp-vrf-afi-safi-update-outq-update-group-sub-group-refresh-sub-group {
    description
      "Specify a VRF.
       Clear Update information (Do NOT execute without cisco support)(cisco-support).
       Clear Update generation OutQ counters (Do NOT execute without cisco support)(cisco-support).
       Update-group.
       Sub-group.
      ";
    input {
      leaf vrf-all {
        type vrf-name;
        mandatory true;
        description
          "VRF name or all";
      }
      leaf afi-safi-name {
        type afi-safi-type;
        mandatory true;
        description
          "AFI and SAFI";
      }
      leaf update-group {
        type update-group-id;
        mandatory true;
        description
          "Update-group process ID <x.y>";
      }
      leaf refresh-sub-group {
        type refresh-sub-group-id;
        mandatory true;
        description
          "Refresh Sub-group process ID <x.y:z>";
      }
    }
    csc:xr-task "bgp";
    csc:cli-command "clear bgp vrf <vrf-all> <afi-safi-name> update outq update-group <update-group> sub-group <refresh-sub-group>";
  }
  rpc clear-bgp-vrf-afi-safi-update-outq-update-group-update-parent {
    description
      "Specify a VRF.
       Clear Update information (Do NOT execute without cisco support)(cisco-support).
       Clear Update generation OutQ counters (Do NOT execute without cisco support)(cisco-support).
       Update-group.
       Update parents' OutQ counters too.
      ";
    input {
      leaf vrf-all {
        type vrf-name;
        mandatory true;
        description
          "VRF name or all";
      }
      leaf afi-safi-name {
        type afi-safi-type;
        mandatory true;
        description
          "AFI and SAFI";
      }
      leaf update-group {
        type update-group-id;
        mandatory true;
        description
          "Update-group process ID <x.y>";
      }
    }
    csc:xr-task "bgp";
    csc:cli-command "clear bgp vrf <vrf-all> <afi-safi-name> update outq update-group <update-group> update-parent";
  }
  rpc clear-bgp-vrf-afi-safi-update-outq-update-group {
    description
      "Specify a VRF.
       Clear Update information (Do NOT execute without cisco support)(cisco-support).
       Clear Update generation OutQ counters (Do NOT execute without cisco support)(cisco-support).
       Update-group.
      ";
    input {
      leaf vrf-all {
        type vrf-name;
        mandatory true;
        description
          "VRF name or all";
      }
      leaf afi-safi-name {
        type afi-safi-type;
        mandatory true;
        description
          "AFI and SAFI";
      }
      leaf update-group {
        type update-group-id;
        mandatory true;
        description
          "Update-group process ID <x.y>";
      }
    }
    csc:xr-task "bgp";
    csc:cli-command "clear bgp vrf <vrf-all> <afi-safi-name> update outq update-group <update-group>";
  }
  rpc clear-bgp-vrf-afi-safi-dampening-ipv6-prefix {
    description
      "Specify a VRF.
       Clear route flap dampening information.
      ";
    input {
      leaf vrf-all {
        type vrf-name;
        mandatory true;
        description
          "VRF name or all";
      }
      leaf afi-safi-name {
        type afi-safi-type;
        mandatory true;
        description
          "AFI and SAFI";
      }
      leaf ipv6-prefix {
        type inet:ipv6-prefix;
        mandatory true;
        description
          "IPv6 Network and mask or masklength to clear dampening information";
      }
    }
    csc:xr-task "bgp";
    csc:cli-command "clear bgp vrf <vrf-all> <afi-safi-name> dampening <ipv6-prefix>";
  }
  rpc clear-bgp-vrf-afi-safi-flap-statistics-ipv6-prefix {
    description
      "Specify a VRF.
       Clear flap statistics.
      ";
    input {
      leaf vrf-all {
        type vrf-name;
        mandatory true;
        description
          "VRF name or all";
      }
      leaf afi-safi-name {
        type afi-safi-type;
        mandatory true;
        description
          "AFI and SAFI";
      }
      leaf ipv6-prefix {
        type inet:ipv6-prefix;
        mandatory true;
        description
          "IPv6 Network and mask or masklength to clear flap statistics";
      }
    }
    csc:xr-task "bgp";
    csc:cli-command "clear bgp vrf <vrf-all> <afi-safi-name> flap-statistics <ipv6-prefix>";
  }
  rpc clear-bgp-vrf-nexthop-performance-statistics {
    description
      "Specify a VRF.
       Clear nexthop.
       Performance statistics information related to processing.
      ";
    input {
      leaf vrf-all {
        type vrf-name;
        mandatory true;
        description
          "VRF name or all";
      }
    }
    csc:xr-task "bgp";
    csc:cli-command "clear bgp vrf <vrf-all> nexthop performance-statistics";
  }
  rpc clear-bgp-vrf-nexthop-registration-ip-addr {
    description
      "Specify a VRF.
       Clear nexthop.
       Registration with RIB and reregister.
      ";
    input {
      leaf vrf-all {
        type vrf-name;
        mandatory true;
        description
          "VRF name or all";
      }
      leaf ip-addr {
        type inet:ip-address;
        mandatory true;
        description
          "Nexthop address";
      }
    }
    csc:xr-task "bgp";
    csc:cli-command "clear bgp vrf <vrf-all> nexthop registration <ip-addr>";
  }
  rpc clear-bgp-vrf-peer-drops-all {
    description
      "Specify a VRF.
       Clear established/dropped counters for a peer.
       All Neighbors.
      ";
    input {
      leaf vrf-all {
        type vrf-name;
        mandatory true;
        description
          "VRF name or all";
      }
    }
    csc:xr-task "bgp";
    csc:cli-command "clear bgp vrf <vrf-all> peer-drops *";
  }
  rpc clear-bgp-vrf-peer-drops-ip-addr {
    description
      "Specify a VRF.
       Clear established/dropped counters for a peer.
      ";
    input {
      leaf vrf-all {
        type vrf-name;
        mandatory true;
        description
          "VRF name or all";
      }
      leaf ip-addr {
        type inet:ip-address;
        mandatory true;
        description
          "BGP neighbor IP address";
      }
    }
    csc:xr-task "bgp";
    csc:cli-command "clear bgp vrf <vrf-all> peer-drops <ip-addr>";
  }
  rpc clear-bgp-vrf-performance-statistics {
    description
      "Specify a VRF.
       Clear performance statistics.
      ";
    input {
      leaf vrf-all {
        type vrf-name;
        mandatory true;
        description
          "VRF name or all";
      }
    }
    csc:xr-task "bgp";
    csc:cli-command "clear bgp vrf <vrf-all> performance-statistics";
  }
  rpc clear-bgp-vrf-shutdown {
    description
      "Specify a VRF.
       Clear all peers which were shut down due to low memory.
      ";
    input {
      leaf vrf-all {
        type vrf-name;
        mandatory true;
        description
          "VRF name or all";
      }
    }
    csc:xr-task "bgp";
    csc:cli-command "clear bgp vrf <vrf-all> shutdown";
  }
  rpc clear-bgp-vrf-update-outq-address-family-update-parent {
    description
      "Specify a VRF.
       Clear Update information (Do NOT execute without cisco support)(cisco-support).
       Clear Update generation OutQ counters (Do NOT execute without cisco support)(cisco-support).
       Address-family.
       Update parents' OutQ counters too.
      ";
    input {
      leaf vrf-all {
        type vrf-name;
        mandatory true;
        description
          "VRF name or all";
      }
    }
    csc:xr-task "bgp";
    csc:cli-command "clear bgp vrf <vrf-all> update outq address-family update-parent";
  }
  rpc clear-bgp-vrf-update-outq-address-family {
    description
      "Specify a VRF.
       Clear Update information (Do NOT execute without cisco support)(cisco-support).
       Clear Update generation OutQ counters (Do NOT execute without cisco support)(cisco-support).
       Address-family.
      ";
    input {
      leaf vrf-all {
        type vrf-name;
        mandatory true;
        description
          "VRF name or all";
      }
    }
    csc:xr-task "bgp";
    csc:cli-command "clear bgp vrf <vrf-all> update outq address-family";
  }
  rpc clear-bgp-vrf-update-outq-neighbor-ip-addr-refresh-update-parent {
    description
      "Specify a VRF.
       Clear Update information (Do NOT execute without cisco support)(cisco-support).
       Clear Update generation OutQ counters (Do NOT execute without cisco support)(cisco-support).
       Neighbor.
       Refresh OutQ.
       Update parents' OutQ counters too.
      ";
    input {
      leaf vrf-all {
        type vrf-name;
        mandatory true;
        description
          "VRF name or all";
      }
      leaf ip-addr {
        type inet:ip-address;
        mandatory true;
        description
          "Neighbor address";
      }
    }
    csc:xr-task "bgp";
    csc:cli-command "clear bgp vrf <vrf-all> update outq neighbor <ip-addr> refresh update-parent";
  }
  rpc clear-bgp-vrf-update-outq-neighbor-ip-addr-refresh {
    description
      "Specify a VRF.
       Clear Update information (Do NOT execute without cisco support)(cisco-support).
       Clear Update generation OutQ counters (Do NOT execute without cisco support)(cisco-support).
       Neighbor.
       Refresh OutQ.
      ";
    input {
      leaf vrf-all {
        type vrf-name;
        mandatory true;
        description
          "VRF name or all";
      }
      leaf ip-addr {
        type inet:ip-address;
        mandatory true;
        description
          "Neighbor address";
      }
    }
    csc:xr-task "bgp";
    csc:cli-command "clear bgp vrf <vrf-all> update outq neighbor <ip-addr> refresh";
  }
  rpc clear-bgp-vrf-update-outq-neighbor-ip-addr-update-parent {
    description
      "Specify a VRF.
       Clear Update information (Do NOT execute without cisco support)(cisco-support).
       Clear Update generation OutQ counters (Do NOT execute without cisco support)(cisco-support).
       Neighbor.
       Update parents' OutQ counters too.
      ";
    input {
      leaf vrf-all {
        type vrf-name;
        mandatory true;
        description
          "VRF name or all";
      }
      leaf ip-addr {
        type inet:ip-address;
        mandatory true;
        description
          "Neighbor address";
      }
    }
    csc:xr-task "bgp";
    csc:cli-command "clear bgp vrf <vrf-all> update outq neighbor <ip-addr> update-parent";
  }
  rpc clear-bgp-vrf-update-outq-neighbor-ip-addr {
    description
      "Specify a VRF.
       Clear Update information (Do NOT execute without cisco support)(cisco-support).
       Clear Update generation OutQ counters (Do NOT execute without cisco support)(cisco-support).
       Neighbor.
      ";
    input {
      leaf vrf-all {
        type vrf-name;
        mandatory true;
        description
          "VRF name or all";
      }
      leaf ip-addr {
        type inet:ip-address;
        mandatory true;
        description
          "Neighbor address";
      }
    }
    csc:xr-task "bgp";
    csc:cli-command "clear bgp vrf <vrf-all> update outq neighbor <ip-addr>";
  }
  rpc clear-bgp-vrf-update-outq-update-group-sub-group-update-parent {
    description
      "Specify a VRF.
       Clear Update information (Do NOT execute without cisco support)(cisco-support).
       Clear Update generation OutQ counters (Do NOT execute without cisco support)(cisco-support).
       Update-group.
       Sub-group.
       Update parents' OutQ counters too.
      ";
    input {
      leaf vrf-all {
        type vrf-name;
        mandatory true;
        description
          "VRF name or all";
      }
      leaf update-group {
        type update-group-id;
        mandatory true;
        description
          "Update-group process ID <x.y>";
      }
      leaf sub-group {
        type update-group-id;
        mandatory true;
        description
          "Sub-group process ID <x.y>";
      }
    }
    csc:xr-task "bgp";
    csc:cli-command "clear bgp vrf <vrf-all> update outq update-group <update-group> sub-group <sub-group> update-parent";
  }
  rpc clear-bgp-vrf-update-outq-update-group-sub-group {
    description
      "Specify a VRF.
       Clear Update information (Do NOT execute without cisco support)(cisco-support).
       Clear Update generation OutQ counters (Do NOT execute without cisco support)(cisco-support).
       Update-group.
       Sub-group.
      ";
    input {
      leaf vrf-all {
        type vrf-name;
        mandatory true;
        description
          "VRF name or all";
      }
      leaf update-group {
        type update-group-id;
        mandatory true;
        description
          "Update-group process ID <x.y>";
      }
      leaf sub-group {
        type update-group-id;
        mandatory true;
        description
          "Sub-group process ID <x.y>";
      }
    }
    csc:xr-task "bgp";
    csc:cli-command "clear bgp vrf <vrf-all> update outq update-group <update-group> sub-group <sub-group>";
  }
  rpc clear-bgp-vrf-update-outq-update-group-sub-group-refresh-sub-group-update-parent {
    description
      "Specify a VRF.
       Clear Update information (Do NOT execute without cisco support)(cisco-support).
       Clear Update generation OutQ counters (Do NOT execute without cisco support)(cisco-support).
       Update-group.
       Sub-group.
       Update parents' OutQ counters too.
      ";
    input {
      leaf vrf-all {
        type vrf-name;
        mandatory true;
        description
          "VRF name or all";
      }
      leaf update-group {
        type update-group-id;
        mandatory true;
        description
          "Update-group process ID <x.y>";
      }
      leaf refresh-sub-group {
        type refresh-sub-group-id;
        mandatory true;
        description
          "Refresh Sub-group process ID <x.y:z>";
      }
    }
    csc:xr-task "bgp";
    csc:cli-command "clear bgp vrf <vrf-all> update outq update-group <update-group> sub-group <refresh-sub-group> update-parent";
  }
  rpc clear-bgp-vrf-update-outq-update-group-sub-group-refresh-sub-group {
    description
      "Specify a VRF.
       Clear Update information (Do NOT execute without cisco support)(cisco-support).
       Clear Update generation OutQ counters (Do NOT execute without cisco support)(cisco-support).
       Update-group.
       Sub-group.
      ";
    input {
      leaf vrf-all {
        type vrf-name;
        mandatory true;
        description
          "VRF name or all";
      }
      leaf update-group {
        type update-group-id;
        mandatory true;
        description
          "Update-group process ID <x.y>";
      }
      leaf refresh-sub-group {
        type refresh-sub-group-id;
        mandatory true;
        description
          "Refresh Sub-group process ID <x.y:z>";
      }
    }
    csc:xr-task "bgp";
    csc:cli-command "clear bgp vrf <vrf-all> update outq update-group <update-group> sub-group <refresh-sub-group>";
  }
  rpc clear-bgp-vrf-update-outq-update-group-update-parent {
    description
      "Specify a VRF.
       Clear Update information (Do NOT execute without cisco support)(cisco-support).
       Clear Update generation OutQ counters (Do NOT execute without cisco support)(cisco-support).
       Update-group.
       Update parents' OutQ counters too.
      ";
    input {
      leaf vrf-all {
        type vrf-name;
        mandatory true;
        description
          "VRF name or all";
      }
      leaf update-group {
        type update-group-id;
        mandatory true;
        description
          "Update-group process ID <x.y>";
      }
    }
    csc:xr-task "bgp";
    csc:cli-command "clear bgp vrf <vrf-all> update outq update-group <update-group> update-parent";
  }
  rpc clear-bgp-vrf-update-outq-update-group {
    description
      "Specify a VRF.
       Clear Update information (Do NOT execute without cisco support)(cisco-support).
       Clear Update generation OutQ counters (Do NOT execute without cisco support)(cisco-support).
       Update-group.
      ";
    input {
      leaf vrf-all {
        type vrf-name;
        mandatory true;
        description
          "VRF name or all";
      }
      leaf update-group {
        type update-group-id;
        mandatory true;
        description
          "Update-group process ID <x.y>";
      }
    }
    csc:xr-task "bgp";
    csc:cli-command "clear bgp vrf <vrf-all> update outq update-group <update-group>";
  }
}
