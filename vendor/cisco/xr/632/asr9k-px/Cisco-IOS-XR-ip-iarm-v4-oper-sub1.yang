submodule Cisco-IOS-XR-ip-iarm-v4-oper-sub1 {
  belongs-to Cisco-IOS-XR-ip-iarm-v4-oper {
    prefix Cisco-IOS-XR-ip-iarm-v4-oper;
  }

  import ietf-inet-types {
    prefix inet;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR ip-iarm-v4 package operational data.
     
     Copyright (c) 2013-2017 by Cisco Systems, Inc.
     All rights reserved.";

  revision 2017-05-01 {
    description
      "Fixing backward compatibility error in module.";
  }
  revision 2016-12-19 {
    description
      "IOS XR 6.2.1 revision.";
  }
  revision 2015-11-09 {
    description
      "IOS XR 6.0 revision.";
  }

  typedef String1 {
    type string;
    description
      "String1";
  }

  typedef Ipv6-address {
    type inet:ipv6-address;
    description
      "IPV6 Address type";
  }

  grouping IP-ARM-EDM-DB-RTRID-BAG-TYPE {
    description
      "Router-id information by VRF";
    leaf vrf-id {
      type uint32;
      description
        "VRF ID";
    }
    leaf vrf-name {
      type string;
      description
        "VRF Name";
    }
    leaf interface-name {
      type string;
      description
        "Interface name";
    }
    leaf router-id {
      type inet:ipv4-address;
      description
        "Router ID";
    }
  }

  grouping IP-ARM-EDM-DB-VRF-BAG-TYPE {
    description
      "VRF summary information";
    leaf vrf-id {
      type uint32;
      description
        "VRF ID";
    }
    leaf vrf-name-xr {
      type string;
      description
        "VRF Name";
    }
  }

  grouping IP-ARM-EDM-SUMMARY-BAG-TYPE {
    description
      "IP-ARM summary information";
    leaf producer-count {
      type int32;
      description
        "Number of producers";
    }
    leaf address-conflict-count {
      type int32;
      description
        "Number of address conflicts";
    }
    leaf unnumbered-conflict-count {
      type int32;
      description
        "Number of unnumbered interface conflicts";
    }
    leaf db-master-version {
      type uint32;
      description
        "IP-ARM DB master version";
    }
    leaf vrf-count {
      type int32;
      description
        "Number of known VRFs";
    }
  }

  grouping IP-ARM-EDM-DB-IF-BAG-TYPE {
    description
      "Database information by interface";
    leaf referenced-interface {
      type String1;
      description
        "Referenced Interface - only valid for an
         unnumbered interface";
    }
    leaf vrf-name {
      type string;
      description
        "VRF Name";
    }
    list address {
      description
        "Address info";
      uses IP-ARM-EDM-ADDR-TYPE;
    }
  }

  grouping ARM-ADDRTYPE {
    description
      "ARM ADDRTYPE";
    leaf afi {
      type int32;
      description
        "AFI";
    }
    leaf ipv4-address {
      when "../afi = '2'" {
        description
          "../AFI = '2'";
      }
      type inet:ipv4-address;
      description
        "IPV4 Address";
    }
    leaf ipv6-address {
      when "../afi = '26'" {
        description
          "../AFI = '26'";
      }
      type Ipv6-address;
      description
        "IPV6 Address";
    }
  }

  grouping IP-ARM-EDM-ADDR-TYPE {
    description
      "IP ARM EDM ADDR TYPE";
    container address {
      description
        "Address";
      uses ARM-ADDRTYPE;
    }
    leaf prefix-length {
      type uint32;
      description
        "Prefix length";
    }
    leaf route-tag {
      type uint32;
      description
        "Route Tag of the address";
    }
    leaf is-primary {
      type boolean;
      description
        "Is address primary - valid only for IPv4
         addresses";
    }
    leaf is-tentative {
      type boolean;
      description
        "Is address valid/tentative - valid only for IPV6
         addresses";
    }
    leaf is-prefix-sid {
      type boolean;
      description
        "Is prefix_sid valid - valid only for IPV6
         addresses";
    }
    leaf producer {
      type string;
      description
        "Producer Name";
    }
  }

  grouping IP-ARM-EDM-DB-NET-BAG-TYPE {
    description
      "Database information by network";
    container address-xr {
      description
        "Address info";
      uses IP-ARM-EDM-ADDR-TYPE;
    }
    leaf interface-name {
      type string;
      description
        "Interface name";
    }
    leaf referenced-interface {
      type String1;
      description
        "Referenced Interface - only valid for an
         unnumbered interface";
    }
    leaf vrf-name {
      type string;
      description
        "VRF Name";
    }
  }
}
