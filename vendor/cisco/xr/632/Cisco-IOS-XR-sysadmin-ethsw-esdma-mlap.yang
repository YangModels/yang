module Cisco-IOS-XR-sysadmin-ethsw-esdma-mlap {
  namespace "http://www.cisco.com/ns/yang/Cisco-IOS-XR-sysadmin-ethsw-esdma-mlap";
  prefix esdma_mlap;

  import tailf-common {
    prefix tailf;
  }
  import ietf-yang-types {
    prefix ietf;
  }
  import Cisco-IOS-XR-sysadmin-ethsw-esdma-types {
    prefix esdma_types;
  }
  import Cisco-IOS-XR-sysadmin-show-trace {
    prefix show_trace;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains the YANG definitions
     for the Cisco IOS-XR SysAdmin
     'show controller switch mlap' commands.
     
     Copyright(c) 2011-2017 by Cisco Systems, Inc.
     All rights reserved.";

  revision 2017-05-01 {
    description
      "Namespace change to comply with Cisco guidelines on namespace";
  }
  revision 2016-10-12 {
    description
      "Unhide commands and configs. Moved to advanced-grp";
  }
  revision 2016-07-06 {
    description
      "Initial revision with content extracted from esdma_cli.yang.";
  }

  grouping mlap-endpoint-state-info {
    leaf valid {
      type boolean;
      description
        "Indicates whether this endpoint information contains valid data.";
      tailf:alt-name "Endpoint information valid:";
    }
    leaf chassis-type {
      when "../valid = 'true'";
      type esdma_types:esdma-rack-type-enum;
      description
        "The chassis type of this endpoint is in";
      tailf:display-when "../valid = 'true'";
      tailf:alt-name "Chassis type:";
    }
    leaf endpoint-type {
      when "../valid = 'true'";
      type esdma_types:esdma-switch-type-enum;
      description
        "The type of endpoint this endpoint switch is on";
      tailf:display-when "../valid = 'true'";
      tailf:alt-name "Endpoint type:";
    }
    leaf endpoint-slot-number {
      when "../valid = 'true'";
      type uint32;
      description
        "Slot number of this endpoint";
      tailf:display-when "../valid = 'true'";
      tailf:alt-name "Endpoint slot number:";
    }
    leaf endpoint-switch-number {
      when "../valid = 'true'";
      type uint32;
      description
        "Switch number for the endpoint";
      tailf:display-when "../valid = 'true'";
      tailf:alt-name "Endpoint switch number:";
    }
    leaf endpoint-switch-port-number {
      when "../valid = 'true'";
      type uint32;
      description
        "Port number on the switch for the endpoint";
      tailf:display-when "../valid = 'true'";
      tailf:alt-name "Endpoint switch port:";
    }
    leaf endpoint-chassis-serial-number {
      when "../valid = 'true'";
      type string;
      description
        "Serial number for the endpoint";
      tailf:display-when "../valid = 'true'";
      tailf:alt-name "Endpoint chassis serial number:";
    }
    leaf mlap-state {
      when "../valid = 'true'";
      type esdma_types:mlap-state-enum;
      description
        "Protocol invoked port state";
      tailf:display-when "../valid = 'true'";
      tailf:cli-preformatted;
      tailf:alt-name "Protocol state:";
    }
    leaf inter-fcc_sw-port {
      when "../valid = 'true'";
      type boolean;
      description
        "Indicates whether this port is used for an inter-F-SW connection";
      tailf:display-when "../valid = 'true'";
      tailf:alt-name "Inter F-SW port:";
    }
    leaf fcc_sw-indirectly-reachable {
      when "../valid = 'true'";
      type boolean;
      description
        "Indicates whether this port can indirectly reach an F-SW";
      tailf:display-when "../valid = 'true'";
      tailf:alt-name "F-SW indirectly reachable:";
    }
  }

  grouping mlap-internal-details {
    container mlap-internal-details {
      tailf:cli-drop-node-name;
      tailf:cli-full-show-path;
      tailf:cli-show-template
        "MLAP Detailed Information For Internal Endpoint
         $(info|show:indent=4)";
      container info {
        tailf:cli-drop-node-name;
        leaf port-owner {
          type esdma_types:esdma-cpu;
          description
            "Indicates which switch data path the port belongs to";
          tailf:alt-name "Port MLAP owner:";
        }
        leaf current-active-owner {
          type esdma_types:esdma-cpu;
          description
            "Indicates which switch is currently mastering chassis data";
          tailf:alt-name "Card controlling packet path:";
        }
        leaf mlap-peer-flags {
          type bits {
            bit Valid {
              position 0;
            }
            bit FCC-Active {
              position 1;
            }
            bit Force-Active {
              position 2;
            }
            bit Ignore-Data {
              position 31;
            }
          }
          description
            "Peer's port MLAP protocol flags";
          tailf:alt-name "Peer MLAP protocol flags:";
          tailf:cli-preformatted;
        }
        leaf mlap-peer-idle-count {
          type uint32;
          description
            "Time intervals peer has not updated information";
          tailf:alt-name "Peer idle count to endpoint:";
        }
        leaf my-connection-active-mask {
          type uint64;
          description
            "My port active mask view";
          tailf:alt-name "This active connection mask:";
          tailf:cli-value-display-template "0x$(.|hex:16)";
        }
        leaf peer-connection-active-mask {
          type uint64;
          description
            "Peer's port active mask view";
          tailf:alt-name "Peer active connection mask:";
          tailf:cli-value-display-template "0x$(.|hex:16)";
        }
        leaf endpoint-card-type {
          type esdma_types:mlap-ep-type;
          description
            "Indicates the high-level card type this switch port is peering with";
          tailf:alt-name "Connected endpoint card type:";
        }
        leaf endpoint-mac-address {
          type ietf:mac-address;
          description
            "MAC addess of device of the protocol peer for this switch port";
          tailf:alt-name "MAC address of protocol endpoint:";
        }
      }
    }
  }

  grouping mlap-external-details {
    container mlap-external-details {
      tailf:cli-drop-node-name;
      tailf:cli-column-stats;
      tailf:cli-full-show-path;
      tailf:cli-show-template
        "MLAP Detailed Information For External Endpoint
             Local State Information:$(local-state-information|show:indent=7)    Peer State Information:$(peer-state-information|show:indent=7)    Peer's Other Peer State Information:$(peer-other-link-state-information|show:indent=7)";
      container local-state-information {
        description
          "MLAP state information from this port's perspective";
        tailf:cli-drop-node-name;
        tailf:cli-column-stats;
        uses mlap-endpoint-state-info;
      }
      container peer-state-information {
        description
          "MLAP state information from peer port's perspective";
        tailf:cli-drop-node-name;
        tailf:cli-column-stats;
        uses mlap-endpoint-state-info;
      }
      container peer-other-link-state-information {
        description
          "MLAP state information for peer's other uplink perspective (RP/SC only)";
        tailf:cli-drop-node-name;
        tailf:cli-column-stats;
        uses mlap-endpoint-state-info;
      }
    }
  }

  grouping mlap-detail-data {
    container detail {
      tailf:info "Detailed MLAP information for a single switch port";
      tailf:callpoint "esdma_mlap_detail_data";
      tailf:cli-incomplete-show-path;
      list location {
        key "rack card switch-id";
        tailf:info "Location information for detailed MLAP switch port";
        tailf:cli-incomplete-command;
        tailf:cli-incomplete-show-path;
        tailf:cli-suppress-table;
        tailf:cli-key-format "$(1)/$(2)/$(3)";
        leaf rack {
          type esdma_types:esdma-rack-num-enum;
        }
        leaf card {
          type esdma_types:esdma-cpu;
        }
        leaf switch-id {
          type esdma_types:esdma-switch-type-enum;
          description
            "Switch type";
        }
        list port-iter {
          key "port";
          tailf:cli-drop-node-name;
          tailf:cli-full-command;
          tailf:cli-suppress-table;
          tailf:info "Switch port";
          tailf:cli-show-template-enter "MLAP Summary Information For $(gen-data/mlap-protocol) Switch Port $(port) ($(../../rack)/$(../../card)/$(../../switch-id))\n";
          tailf:cli-show-template "$(gen-data|show:indent=4)$($(gen-data/mlap-protocol)==Internal?$(mlap-internal-details|show):$(mlap-external-details|show))";
          leaf port {
            type esdma_types:esdma-switch-port-type;
            description
              "Switch port";
          }
          container gen-data {
            tailf:cli-drop-node-name;
            leaf serial-num {
              type string;
              description
                "Rack serial number";
              tailf:cli-suppress-show-path;
              tailf:cli-suppress-show-match;
              tailf:alt-name "Rack serial number:";
            }
            leaf connects-to {
              type string;
              description
                "Indicates what this port connects to";
              tailf:cli-suppress-show-path;
              tailf:cli-suppress-show-match;
              tailf:cli-preformatted;
              tailf:alt-name "Connects to:";
            }
            leaf phys-state {
              type esdma_types:esdma-switch-port-state;
              description
                "Physical port state";
              tailf:cli-suppress-show-path;
              tailf:cli-suppress-show-match;
              tailf:alt-name "Physical port state:";
            }
            leaf admin-state {
              type esdma_types:esdma-switch-port-state;
              description
                "Administrative port state";
              tailf:cli-suppress-show-path;
              tailf:cli-suppress-show-match;
              tailf:alt-name "Administrative port state:";
            }
            leaf protocol-state {
              type esdma_types:mlap-state-enum;
              description
                "Protocol invoked port state";
              tailf:cli-suppress-show-path;
              tailf:cli-suppress-show-match;
              tailf:cli-preformatted;
              tailf:alt-name "Port protocol state:";
            }
            leaf forwarding {
              type esdma_types:switch-forwarding-state;
              description
                "Indicates whether this port is allowed to forward traffic";
              tailf:cli-suppress-show-path;
              tailf:cli-suppress-show-match;
              tailf:alt-name "Forwarding state:";
            }
            leaf mlap-protocol {
              type esdma_types:mlap-protocol-enum;
              description
                "Indicates whether the internal or external MLAP protocol is active on this port";
              tailf:cli-suppress-show-path;
              tailf:cli-suppress-show-match;
              tailf:alt-name "Protocol type:";
            }
            leaf protocol-pkt-sent {
              type uint64;
              description
                "Number of protocol packets sent";
              tailf:cli-suppress-show-path;
              tailf:cli-suppress-show-match;
              tailf:alt-name "Good protocol packets sent:";
            }
            leaf protocol-pkt-recv {
              type uint64;
              description
                "Number of protocol packets received";
              tailf:cli-suppress-show-path;
              tailf:cli-suppress-show-match;
              tailf:alt-name "Good protocol packets received:";
            }
            leaf protocol-set-color-pkts-sent {
              type uint64;
              description
                "Number of set-active-VLAN requests";
              tailf:cli-suppress-show-path;
              tailf:cli-suppress-show-match;
              tailf:display-column-name "Set VLAN Requests";
              tailf:alt-name "Set VLAN requests:";
            }
            leaf protocol-set-color-pkts-recv {
              type uint64;
              description
                "Number of set-active-VLAN responses";
              tailf:cli-suppress-show-path;
              tailf:cli-suppress-show-match;
              tailf:display-column-name "Set VLAN Responses";
              tailf:alt-name "Set VLAN responses:";
            }
            leaf protocol-send-error {
              type uint64;
              description
                "Number of protocol packet send errors";
              tailf:cli-suppress-show-path;
              tailf:cli-suppress-show-match;
              tailf:alt-name "Protocol packet send errors:";
            }
            leaf protocol-recv-error {
              type uint64;
              description
                "Number of protocol packet receive errors";
              tailf:cli-suppress-show-path;
              tailf:cli-suppress-show-match;
              tailf:alt-name "Protocol packet receive errors:";
            }
            leaf protocol-state-changes {
              type uint32;
              description
                "Number of state changes";
              tailf:cli-suppress-show-path;
              tailf:cli-suppress-show-match;
              tailf:alt-name "Protocol state changes:";
            }
          }
          choice detail-type {
            case internal-detail {
              uses mlap-internal-details;
            }
            case external-detail {
              uses mlap-external-details;
            }
          }
        }
      }
    }
  }

  grouping mlap-summary-data {
    container summary-data {
      tailf:cli-drop-node-name;
      tailf:callpoint "esdma_mlap_summary_data";
      list location {
        key "rack card switch-id";
        tailf:info "Location information for MLAP switch summary data";
        tailf:cli-full-command;
        tailf:cli-suppress-table;
        tailf:cli-key-format "$(1)/$(2)/$(3)";
        tailf:cli-show-template "$(port-iter|show)";
        tailf:cli-no-match-completion;
        leaf rack {
          type esdma_types:esdma-rack-num-enum;
        }
        leaf card {
          type esdma_types:esdma-cpu;
          description
            "Card that owns a switch of interest";
        }
        leaf switch-id {
          type esdma_types:esdma-switch-type-enum;
          description
            "Switch type";
        }
        leaf serial-num {
          type string;
          description
            "Rack serial number";
          tailf:cli-suppress-show-path;
          tailf:cli-suppress-show-match;
        }
        list port-iter {
          key "port";
          tailf:cli-drop-node-name;
          tailf:cli-table-legend
            "Rack  Card  Switch  Rack Serial Number
             --------------------------------------
             $(../rack|ljust:4)  $(../card|ljust:4)  $(../switch-id|ljust:6)  $(../serial-num|ljust:18)
            ";
          tailf:cli-enforce-table;
          leaf port {
            type esdma_types:esdma-switch-port-type;
            description
              "Switch port";
            tailf:display-column-name "Port";
          }
          leaf phys-state {
            type esdma_types:esdma-switch-port-state;
            description
              "Physical port state";
            tailf:cli-suppress-show-path;
            tailf:cli-suppress-show-match;
            tailf:display-column-name "Phys State";
            tailf:alt-name "Physical port state:";
          }
          leaf admin-state {
            type esdma_types:esdma-switch-port-state;
            description
              "Administrative port state";
            tailf:cli-suppress-show-path;
            tailf:cli-suppress-show-match;
            tailf:display-column-name "Admin State";
            tailf:alt-name "Administrative port state:";
          }
          leaf protocol-state {
            type esdma_types:mlap-state-enum;
            description
              "Protocol invoked port state";
            tailf:cli-suppress-show-path;
            tailf:cli-suppress-show-match;
            tailf:cli-preformatted;
            tailf:display-column-name "Protocol State";
            tailf:alt-name "Port protocol state:";
          }
          leaf forwarding {
            type esdma_types:switch-forwarding-state;
            description
              "Indicates whether this port is allowed to forward traffic";
            tailf:cli-suppress-show-path;
            tailf:cli-suppress-show-match;
            tailf:display-column-name "Forward State";
            tailf:alt-name "Forwarding state:";
          }
          leaf mlap-protocol {
            type esdma_types:mlap-protocol-enum;
            description
              "Indicates whether the internal or external MLAP protocol is active on this port";
            tailf:cli-suppress-show-path;
            tailf:cli-suppress-show-match;
            tailf:display-column-name "Protocol Type";
            tailf:alt-name "Protocol type:";
          }
          leaf connects-to {
            type string;
            description
              "Indicates what this port connects to";
            tailf:cli-suppress-show-path;
            tailf:cli-suppress-show-match;
            tailf:cli-preformatted;
            tailf:display-column-name "Connects To";
            tailf:alt-name "Connects to:";
          }
        }
      }
    }
  }

  grouping mlap-statistics-data {
    container statistics {
      tailf:callpoint "esdma_mlap_statistics_data";
      tailf:info "MLAP switch statistics data";
      list location {
        key "rack card switch-id";
        tailf:info "Location information for MLAP statistics data";
        tailf:cli-full-command;
        tailf:cli-suppress-table;
        tailf:cli-key-format "$(1)/$(2)/$(3)";
        tailf:cli-show-template "$(port-iter|show)";
        tailf:cli-no-match-completion;
        leaf rack {
          type esdma_types:esdma-rack-num-enum;
        }
        leaf card {
          type esdma_types:esdma-cpu;
          description
            "Card that owns a switch of interest";
        }
        leaf switch-id {
          type esdma_types:esdma-switch-type-enum;
          description
            "Switch type";
        }
        leaf serial-num {
          type string;
          description
            "Rack serial number";
          tailf:cli-suppress-show-path;
          tailf:cli-suppress-show-match;
        }
        list port-iter {
          key "port";
          tailf:cli-drop-node-name;
          tailf:cli-table-legend
            "Rack  Card  Switch  Rack Serial Number
             --------------------------------------
             $(../rack|ljust:4)  $(../card|ljust:4)  $(../switch-id|ljust:6)  $(../serial-num|ljust:18)
            ";
          tailf:cli-enforce-table;
          leaf port {
            type esdma_types:esdma-switch-port-type;
            description
              "Switch port";
            tailf:display-column-name "Port";
          }
          leaf protocol-state {
            type esdma_types:mlap-state-enum;
            description
              "Protocol invoked port state";
            tailf:cli-suppress-show-path;
            tailf:cli-suppress-show-match;
            tailf:cli-preformatted;
            tailf:display-column-name "Protocol State";
            tailf:alt-name "Port protocol state:";
          }
          leaf protocol-state-changes {
            type uint32;
            description
              "Number of state changes";
            tailf:cli-suppress-show-path;
            tailf:cli-suppress-show-match;
            tailf:display-column-name "State Changes";
            tailf:alt-name "Protocol state changes:";
          }
          leaf protocol-pkt-sent {
            type uint64;
            description
              "Number of protocol packets sent";
            tailf:cli-suppress-show-path;
            tailf:cli-suppress-show-match;
            tailf:display-column-name "Pkts Sent";
            tailf:alt-name "Good protocol packets sent:";
          }
          leaf protocol-pkt-recv {
            type uint64;
            description
              "Number of protocol packets received";
            tailf:cli-suppress-show-path;
            tailf:cli-suppress-show-match;
            tailf:display-column-name "Pkts Recv";
            tailf:alt-name "Good protocol packets received:";
          }
          leaf protocol-set-color-pkts-sent {
            type uint64;
            description
              "Number of set-active-VLAN requests";
            tailf:cli-suppress-show-path;
            tailf:cli-suppress-show-match;
            tailf:display-column-name "Set VLAN Requests";
            tailf:alt-name "Set VLAN requests:";
          }
          leaf protocol-set-color-pkts-recv {
            type uint64;
            description
              "Number of set-active-VLAN responses";
            tailf:cli-suppress-show-path;
            tailf:cli-suppress-show-match;
            tailf:display-column-name "Set VLAN Responses";
            tailf:alt-name "Set VLAN responses:";
          }
          leaf protocol-send-error {
            type uint64;
            description
              "Number of protocol packet send errors";
            tailf:cli-suppress-show-path;
            tailf:cli-suppress-show-match;
            tailf:display-column-name "Send Errors";
            tailf:alt-name "Protocol packet send errors:";
          }
          leaf protocol-recv-error {
            type uint64;
            description
              "Number of protocol packet receive errors";
            tailf:cli-suppress-show-path;
            tailf:cli-suppress-show-match;
            tailf:display-column-name "Recv Errors";
            tailf:alt-name "Protocol packet receive errors:";
          }
          leaf connects-to {
            type string;
            description
              "Indicates what this port connects to";
            tailf:cli-suppress-show-path;
            tailf:cli-suppress-show-match;
            tailf:cli-preformatted;
            tailf:display-column-name "Connects To";
            tailf:alt-name "Connects to:";
          }
        }
      }
    }
  }

  grouping mlap-reachable-data {
    container reachable {
      tailf:callpoint "esdma_mlap_reachable";
      tailf:info "Lists all control plane Ethernet switches serviced by MLAP";
      list location {
        key "rack card switch-id";
        tailf:cli-drop-node-name;
        tailf:cli-full-command;
        tailf:cli-enforce-table;
        tailf:cli-no-match-completion;
        tailf:cli-no-key-completion;
        tailf:cli-full-show-path;
        leaf rack {
          type esdma_types:esdma-rack-num-enum;
          tailf:display-column-name "Rack";
        }
        leaf card {
          type esdma_types:esdma-cpu;
          tailf:display-column-name "Card";
        }
        leaf switch-id {
          type esdma_types:esdma-switch-type-enum;
          tailf:display-column-name "Switch";
        }
      }
    }
  }

  grouping mlap-debug-counters {
    container debug {
      tailf:info "MLAP debug information";
      tailf:hidden "advanced-grp";
      container counters {
        tailf:info "MLAP internal debug counters";
        tailf:callpoint "mlap_debug_counters";
        list location {
          key "rack card switch-id";
          tailf:info "Location information for debug counters";
          tailf:cli-suppress-table;
          tailf:cli-key-format "$(1)/$(2)/$(3)";
          tailf:cli-full-command;
          tailf:cli-show-template "$(counters|show)";
          leaf rack {
            type esdma_types:esdma-rack-num-enum;
            tailf:display-column-name "Rack";
          }
          leaf card {
            type esdma_types:esdma-cpu;
            tailf:display-column-name "Card";
          }
          leaf switch-id {
            type esdma_types:esdma-switch-type-enum;
            tailf:display-column-name "Switch";
          }
          container counters {
            tailf:cli-drop-node-name;
            tailf:cli-suppress-show-path;
            tailf:cli-suppress-show-match;
            leaf eval-all-links-called {
              type uint64;
              tailf:alt-name "Eval all links called";
            }
            leaf timer-event-queued {
              type uint64;
              tailf:alt-name "Timer events queued";
            }
            leaf rx-packet-event-queued {
              type uint64;
              tailf:alt-name "Rx packet events queued";
            }
            leaf eval-all-links-queued {
              type uint64;
              tailf:alt-name "Eval all links events queued";
            }
            leaf link-status-queued {
              type uint64;
              tailf:alt-name "Link status' queued";
            }
            leaf admin-status-queued {
              type uint64;
              tailf:alt-name "Admin status' queued";
            }
            leaf fwd-status-queued {
              type uint64;
              tailf:alt-name "Forwarding state status' queued";
            }
            leaf current-fifo-depth {
              type uint64;
              tailf:alt-name "Current event FIFO depth";
            }
            leaf max-fifo-depth {
              type uint64;
              tailf:alt-name "Maximum event FIFO depth";
            }
            leaf vlan-color-changes {
              type uint32;
              tailf:alt-name "Vlan color changes";
            }
            leaf current-mlap-timeout-ms-interval {
              type uint32;
              tailf:alt-name "Current MLAP timeout (ms)";
            }
            leaf aging-debug-enabled {
              type boolean;
              tailf:alt-name "Debug aging disabled";
            }
            leaf trace-verbosity {
              type esdma_types:mlap-trace-verbosity;
              tailf:alt-name "MLAP debug verbosity level";
            }
          }
        }
      }
    }
  }

  grouping mlap-oper-group {
    container mlap {
      description
        "MLAP switch data";
      tailf:info "Control plane Ethernet switch loop avoidance protocol commands";
      uses mlap-reachable-data;
      uses mlap-detail-data;
      uses mlap-statistics-data;
      uses mlap-summary-data;
      uses mlap-debug-counters;
      uses show_trace:traceable;
    }
  }
  tailf:id "http://cisco.com/panini/calvados/esdma/esdma_mlap";
}
