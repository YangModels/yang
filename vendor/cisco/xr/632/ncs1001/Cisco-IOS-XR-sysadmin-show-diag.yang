module Cisco-IOS-XR-sysadmin-show-diag {
  namespace "http://www.cisco.com/ns/yang/Cisco-IOS-XR-sysadmin-show-diag";
  prefix show_diag;

  import tailf-common {
    prefix tailf;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains a collection of YANG
     definitions for Cisco IOS-XR SysAdmin configuration.
     
     This module holds diag data for chassis, card, fan, power.
     
     Copyright(c) 2012-2017 by Cisco Systems, Inc.
     All rights reserved.";

  revision 2017-04-12 {
    description
      "Changed namespace and module name";
  }
  revision 2012-03-27 {
    description
      "Initial revision of show diag commands";
  }

  grouping diag-default-data {

    grouping chassis_eeprom_grp {
      container chassis_eeprom_cnt {
        tailf:cli-drop-node-name;
        list chassis_eeprom_list {
          key "location";
          tailf:info "Select location";
          tailf:alt-name "eeprom";
          tailf:cli-full-command;
          tailf:cli-suppress-table;
          tailf:cli-no-match-completion;
          tailf:cli-show-template-enter
            "
             Diag EEPROM Information For : $(location)
            ";
          tailf:cli-show-template "$(eeprom-data|show)";
          leaf location {
            type string;
            tailf:display-column-name "Location";
          }
          container eeprom-data {
            tailf:cli-drop-node-name;
            leaf-list raw_list {
              type string;
              tailf:cli-drop-node-name;
              tailf:cli-list-syntax;
            }
          }
        }
      }
    }

    grouping chassis_grp {
      container chassis_cnt {
        tailf:cli-drop-node-name;
        list chassis_list {
          key "location";
          tailf:cli-full-command;
          tailf:alt-name "location";
          tailf:cli-suppress-table;
          tailf:cli-no-match-completion;
          tailf:cli-show-template-enter
            "
             Diag Information For : $(location)
            ";
          tailf:cli-show-template "$(default-data|show)";
          leaf location {
            type string;
            tailf:alt-name "Module Location :";
          }
          container default-data {
            tailf:cli-drop-node-name;
            leaf-list default_out_list {
              type string;
              tailf:cli-drop-node-name;
              tailf:cli-list-syntax;
            }
          }
        }
      }
    }
    container default {
      tailf:cli-drop-node-name;
      list default_list {
        key "location";
        tailf:info "Select location";
        tailf:alt-name "location";
        tailf:cli-full-command;
        tailf:cli-suppress-table;
        tailf:cli-no-match-completion;
        tailf:cli-show-template-enter
          "
           Diag Information For : $(location)
          ";
        tailf:cli-show-template "$(default-data|show)";
        leaf location {
          type string;
          tailf:display-column-name "Location";
          tailf:alt-name "Module Location :";
        }
        container default-data {
          tailf:cli-drop-node-name;
          leaf-list default_out_list {
            type string;
            tailf:cli-drop-node-name;
            tailf:cli-list-syntax;
          }
        }
      }
    }
    container fans {
      tailf:info "Fan-tray information";
      list fans_list {
        key "location";
        tailf:cli-full-command;
        tailf:alt-name "location";
        tailf:info "Select location";
        tailf:cli-suppress-table;
        tailf:cli-no-match-completion;
        tailf:cli-show-template-enter
          "
           Diag Information For : $(location)
          ";
        tailf:cli-show-template "$(default-data|show)";
        leaf location {
          type string;
          tailf:alt-name "Module Location :";
        }
        container default-data {
          tailf:cli-drop-node-name;
          leaf-list default_out_list {
            type string;
            tailf:cli-drop-node-name;
            tailf:cli-list-syntax;
          }
        }
      }
    }
    container power-supply {
      tailf:info "Power-tray/Power-module information";
      list pwr_list {
        key "location";
        tailf:cli-full-command;
        tailf:alt-name "location";
        tailf:cli-suppress-table;
        tailf:cli-no-match-completion;
        tailf:cli-show-template-enter
          "
           Diag Information For : $(location)
          ";
        tailf:cli-show-template "$(default-data|show)";
        leaf location {
          type string;
          tailf:alt-name "Module Location :";
        }
        container default-data {
          tailf:cli-drop-node-name;
          leaf-list default_out_list {
            type string;
            tailf:cli-drop-node-name;
            tailf:cli-list-syntax;
          }
        }
      }
    }
    container chassis {
      tailf:info "Chassis information";
      tailf:cli-show-template "$(chassis_cnt|show)";
      uses chassis_grp;
      uses chassis_eeprom_grp;
    }
  }

  grouping diag-summary-data {
    container summary {
      tailf:info "display summary information";
      list summary_list {
        key "location";
        tailf:alt-name "location";
        tailf:info "Select location";
        tailf:cli-full-command;
        tailf:cli-suppress-table;
        tailf:cli-no-match-completion;
        tailf:cli-show-template-enter "";
        tailf:cli-show-template "$(summary-data|show)";
        leaf location {
          type string;
          tailf:display-column-name "Location";
        }
        container summary-data {
          tailf:cli-drop-node-name;
          leaf-list summary_out_list {
            type string;
            tailf:display-column-name "Description";
            tailf:cli-drop-node-name;
            tailf:cli-list-syntax;
          }
        }
      }
    }
  }

  grouping diag-detail-data {
    container detail {
      tailf:info "detail information";
      list detail_list {
        key "location";
        tailf:cli-full-command;
        tailf:alt-name "location";
        tailf:cli-suppress-table;
        tailf:cli-no-match-completion;
        tailf:cli-show-template-enter
          "
           Detail Diag Information For : $(location)
          ";
        tailf:cli-show-template "$(detail-data|show)";
        leaf location {
          type string;
          tailf:alt-name "Module Location :";
        }
        container detail-data {
          tailf:cli-drop-node-name;
          leaf-list detail_out_list {
            type string;
            tailf:cli-drop-node-name;
            tailf:cli-list-syntax;
          }
        }
      }
    }
  }

  grouping diag-eeprom-location-data {
    container eeprom {
      tailf:info "dump contents of the EEPROM";
      list eeprom_list {
        key "location";
        tailf:info "Select location";
        tailf:alt-name "location";
        tailf:cli-full-command;
        tailf:cli-suppress-table;
        tailf:cli-no-match-completion;
        tailf:cli-show-template-enter
          "
           Diag EEPROM Information For : $(location)
          ";
        tailf:cli-show-template "$(eeprom-data|show)";
        leaf location {
          type string;
          tailf:display-column-name "Location";
        }
        container eeprom-data {
          tailf:cli-drop-node-name;
          leaf-list raw_list {
            type string;
            tailf:cli-drop-node-name;
            tailf:cli-list-syntax;
          }
        }
      }
    }
  }
  tailf:id "http://www.cisco.com/calvados/show_diag";

  container diag {
    config false;
    description
      "diag data";
    tailf:info "display diag information";
    tailf:callpoint "diag_cp";
    tailf:cli-show-template "$(default|show)";
    uses diag-default-data;
    uses diag-summary-data;
    uses diag-eeprom-location-data;
    uses diag-detail-data;
  }
}
