module Cisco-IOS-XR-sysadmin-envmon-types {
  namespace "http://www.cisco.com/ns/yang/Cisco-IOS-XR-sysadmin-envmon-types";
  prefix envmon-types;

  import tailf-common {
    prefix tailf;
  }
  import Cisco-IOS-XR-sysadmin-types {
    prefix calvados;
  }

  revision 2017-11-27 {
    description
      "Add graceful shutdown disable CLI.";
  }
  revision 2017-07-31 {
    description
      "Changing the namespace to follow Cisco guidelines on naming convention";
  }
  revision 2017-05-01 {
    description
      "Namespace change to comply with Cisco guidelines on namespace";
  }

  typedef num_pm {
    type uint32 {
      range "0..5";
    }
  }

  grouping fan-speed-group {
    container raise-fan-speed {
      tailf:info "raise the default fan speed in PWM (the speed cannot go lower, but can go higher based on environmental condition)";
      container all {
        tailf:cli-drop-node-name;
        leaf speed_pwm {
          type uint32 {
            range "0..100";
          }
          tailf:cli-drop-node-name;
        }
      }
      container rack_loc {
        tailf:cli-drop-node-name;
        list location {
          key "rackId";
          tailf:info "rack-id";
          tailf:cli-sequence-commands;
          tailf:cli-incomplete-command;
          tailf:cli-compact-syntax;
          tailf:cli-suppress-mode;
          tailf:cli-delete-when-empty;
          leaf rackId {
            type calvados:rack-id;
          }
          leaf speed_pwm {
            type uint32 {
              range "0..100";
            }
            tailf:cli-drop-node-name;
          }
        }
      }
    }
  }

  grouping fan-ctrl-optics-group {
    container fan-ctrl-optics {
      tailf:info "system fans run higher speed than normal case to cool down special optics";
      tailf:cli-sequence-commands;
      container enable {
        tailf:info "enable higher fan speed";
        container rack_loc {
          tailf:cli-drop-node-name;
          leaf all {
            type empty;
            tailf:cli-drop-node-name;
          }
          list location {
            key "rackId";
            tailf:info "rack-id";
            tailf:cli-optional-in-sequence;
            leaf rackId {
              type calvados:rack-id;
            }
          }
        }
      }
    }
  }

  grouping vin-uv-shut-group {
    container graceful-shutdown {
      tailf:info "system graceful shutdown during DC VIN under voltage";
      tailf:cli-sequence-commands;
      container disable {
        tailf:info "disable system graceful shutdown during DC VIN under voltage";
        container rack_loc {
          tailf:cli-drop-node-name;
          leaf all {
            type empty;
            tailf:cli-drop-node-name;
          }
          list location {
            key "rackId";
            tailf:info "rack-id";
            tailf:cli-optional-in-sequence;
            leaf rackId {
              type calvados:rack-id;
            }
          }
        }
      }
    }
  }
  tailf:id "http://www.cisco.com/panini/calvados/envmon/types";
}
