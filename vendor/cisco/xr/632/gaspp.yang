module gaspp {
  namespace "http://cisco.com/panini/calvados/gaspp";
  prefix gaspp;
  import tailf-xsd-types {
    prefix xs;
  }

  organization "Cisco Systems, Inc.";

  contact
    "Cisco Systems, Inc.
     Customer Service

     Postal: 170 West Tasman Drive
     San Jose, CA 95134

     Tel: +1 800 553-NETS

     E-mail: cs-yang@cisco.com";

  description 
    "This module contains definitions
     for the Calvados model objects.

    Copyright (c) 2012-2017 by Cisco Systems, Inc.
     All rights reserved.";

  revision "2015-08-30" {
    description "Initial version.";
  }


  grouping location-grp {
    list location {
      key "location_name";
      leaf location_name {
        mandatory true;
        type string;
      }
      list data {
        leaf address {
          type uint64;
        }
        leaf name {
          type string;
        }
        leaf value {
          type string;
        }
        leaf size {
          type uint32;
        }
      }
    }
  }

  grouping gaspp {
    list asic {
      config false;
      key "asic-name";
      leaf asic-name {
        type string;
      }
      list instance {
        key "instance-id";
        leaf instance-id {
          type uint32;
        }
        leaf instance-name {
          type string;
        }
        list address {
          key "addr size entries";
          leaf addr {
            mandatory true;
            type string;
          }
          leaf width {
            mandatory true;
            type uint32;
          }
          leaf entries {
            mandatory true;
            type uint32;
          }
          leaf size {
            type uint32;
          }
          list location {
            key "location_name";
            leaf location_name {
              mandatory true;
              type string;
            }
            list direct_data {
              leaf address {
                type uint64;
              }
              leaf name {
                type string;
              }
              leaf value {
                type string;
              }
              leaf size {
                type uint32;
              }
            }
          }
        }
        list block-name {
          key "block-nm block-num";
          leaf block-nm {
            type string;
          }
          leaf block-num {
            type uint32;
          }
          list register-name {
            key "name";
            leaf name {
              type string;
            }
            leaf register {
              type uint32;
            }
            list data {
              leaf address {
                type uint64;
              }
              leaf name {
                type string;
              }
              leaf value {
                type string;
              }
              leaf size {
                type uint32;
              }
            }
          }
        }
        list block-number {
          key "block-num";
          leaf block-num {
            type uint32;
          }
          leaf block-nm {
            type string;
          }
          list register-number {
            key "register";
            leaf register {
              type uint32;
            }
            leaf register-name {
              type string;
            }
            list register-offsets {
              key "reg-start num-entries";
              leaf reg-start {
                type uint32;
              }
              leaf num-entries {
                type uint32;
              }
              uses location-grp;
            }
            uses location-grp;
          }
        }
      }
    }
  }
}
