module Cisco-IOS-XR-sysadmin-envmon-ui {
  namespace "http://www.cisco.com/ns/yang/Cisco-IOS-XR-sysadmin-envmon-ui";
  prefix envmon;

  import tailf-common {
    prefix tailf;
  }
  import Cisco-IOS-XR-sysadmin-show-trace {
    prefix show_trace;
  }
  import tailf-xsd-types {
    prefix xs;
  }
  import Cisco-IOS-XR-sysadmin-types {
    prefix calvados;
  }
  import Cisco-IOS-XR-sysadmin-envmon-types {
    prefix envmon-types;
  }

  organization
    "Cisco Systems Inc.";
  description
    "This module holds chassis, cards Enviroment data.";

  revision 2017-11-27 {
    description
      "Add graceful shutdown disable CLI.";
  }
  revision 2017-07-31 {
    description
      "Changing the namespace to follow Cisco guidelines on naming convention";
  }
  revision 2017-04-10 {
    description
      "Adding the source leaf to altitude value, 
       this is to distinguish the source of the altitude value ";
  }
  revision 2017-03-31 {
    description
      "Renamed module and namespace";
  }
  revision 2017-03-30 {
    description
      "commenting the sensor_attributes callpoints for the oper sensors, 
       using only the location based callpoints for sensor_attributes ";
  }
  revision 2016-10-12 {
    description
      "unhide commands and configs. moved to advanced-grp";
  }
  revision 2011-11-24 {
    description
      "Initial revision of show environment commands";
  }

  grouping temp-data {
    container temperatures {
      config false;
      tailf:info "Temperature information";
      list location {
        key "location";
        tailf:info "Select node location";
        tailf:cli-full-command;
        tailf:cli-no-match-completion;
        tailf:callpoint "env_location_cp_temps";
        tailf:cli-suppress-table;
        tailf:cli-show-template-enter "";
        tailf:cli-show-template-legend
          "================================================================================
           Location  TEMPERATURE                 Value   Crit Major Minor Minor Major  Crit
                     Sensor                    (deg C)   (Lo) (Lo)  (Lo)  (Hi)  (Hi)   (Hi)
           --------------------------------------------------------------------------------
          ";
        tailf:cli-show-template
          "$(.legend_shown!=true?================================================================================
           Location  TEMPERATURE                 Value   Crit Major Minor Minor Major  Crit
                     Sensor                    \\\\(deg C\\\\)   \\\\(Lo\\\\) \\\\(Lo\\\\)  \\\\(Lo\\\\)  \\\\(Hi\\\\)  \\\\(Hi\\\\)   \\\\(Hi\\\\)
           --------------------------------------------------------------------------------
           )$(location)        
           $(sensor_attributes|show)";
        leaf location {
          type string;
          tailf:display-column-name "Location";
        }
        list sensor_attributes {
          key "sensor";
          tailf:cli-no-match-completion;
          tailf:cli-drop-node-name;
          tailf:cli-full-command;
          tailf:cli-suppress-show-path;
          tailf:cli-suppress-show-match;
          tailf:cli-suppress-table;
          tailf:cli-show-template-enter "";
          tailf:cli-show-template "        $(alarm) $(sensor_id|ljust:25) $($(temperature_value)|rjust:7)  $(critical_lo|rjust:5) $(major_lo|rjust:5) $(minor_lo|rjust:5) $(minor_hi|rjust:5) $(major_hi|rjust:5) $(critical_hi|rjust:5)\n";
          leaf sensor {
            type string;
          }
          leaf sensor_id {
            type string;
          }
          leaf alarm {
            type string;
          }
          leaf temperature_value {
            type string;
          }
          leaf value {
            type int32;
          }
          leaf critical_lo {
            type int32;
          }
          leaf major_lo {
            type int32;
          }
          leaf minor_lo {
            type int32;
          }
          leaf minor_hi {
            type int32;
          }
          leaf major_hi {
            type int32;
          }
          leaf critical_hi {
            type int32;
          }
        }
      }
    }
  }

  grouping all-temp-data {
    list temperatures {
      key "loc_iden";
      config false;
      tailf:info "All Temperature information";
      tailf:cli-suppress-table;
      tailf:cli-full-show-path;
      tailf:cli-drop-node-name;
      tailf:cli-show-template-enter "";
      leaf loc_iden {
        type string;
      }
      leaf print_header {
        type boolean;
        default "false";
      }
      tailf:cli-show-template
        "$(print_header == true?================================================================================
         Location  TEMPERATURE                 Value   Crit Major Minor Minor Major  Crit
                   Sensor                    \\\\(deg C\\\\)   \\\\(Lo\\\\) \\\\(Lo\\\\)  \\\\(Lo\\\\)  \\\\(Hi\\\\)  \\\\(Hi\\\\)   \\\\(Hi\\\\)
         --------------------------------------------------------------------------------
         $(loc_iden)       
         $(sensor_attributes|show))";
      list sensor_attributes {
        key "sensor";
        tailf:cli-no-match-completion;
        tailf:cli-drop-node-name;
        tailf:cli-full-command;
        tailf:cli-suppress-show-path;
        tailf:cli-suppress-show-match;
        tailf:cli-suppress-table;
        tailf:cli-show-template-enter "";
        tailf:cli-show-template "        $(alarm) $(sensor_id|ljust:25) $($(temperature_value)|rjust:7)  $(critical_lo|rjust:5) $(major_lo|rjust:5) $(minor_lo|rjust:5) $(minor_hi|rjust:5) $(major_hi|rjust:5) $(critical_hi|rjust:5)\n";
        leaf sensor {
          type string;
        }
        leaf sensor_id {
          type string;
        }
        leaf alarm {
          type string;
        }
        leaf temperature_value {
          type string;
        }
        leaf value {
          type int32;
        }
        leaf critical_lo {
          type int32;
        }
        leaf major_lo {
          type int32;
        }
        leaf minor_lo {
          type int32;
        }
        leaf minor_hi {
          type int32;
        }
        leaf major_hi {
          type int32;
        }
        leaf critical_hi {
          type int32;
        }
      }
    }
  }

  grouping volt-data {
    container voltages {
      config false;
      tailf:info "Voltage information";
      list location {
        key "location";
        tailf:info "Select node location";
        tailf:cli-full-command;
        tailf:cli-no-match-completion;
        tailf:cli-suppress-table;
        tailf:cli-show-template-enter "";
        tailf:callpoint "env_location_cp_volts";
        tailf:cli-show-template-legend
          "================================================================================
           Location  VOLTAGE                     Value   Crit Minor Minor  Crit
                     Sensor                      (mV)    (Lo) (Lo)  (Hi)   (Hi)
           --------------------------------------------------------------------------------
          ";
        tailf:cli-show-template
          "$(.legend_shown!=true?================================================================================
           Location  VOLTAGE                     Value   Crit Minor Minor  Crit
                     Sensor                      \\\\(mV\\\\)    \\\\(Lo\\\\) \\\\(Lo\\\\)  \\\\(Hi\\\\)   \\\\(Hi\\\\)
           --------------------------------------------------------------------------------
           )$(location)        
           $(sensor_attributes|show)";
        leaf location {
          type string;
          tailf:display-column-name "Location";
        }
        list sensor_attributes {
          key "sensor";
          tailf:cli-no-match-completion;
          tailf:cli-drop-node-name;
          tailf:cli-suppress-show-path;
          tailf:cli-suppress-show-match;
          tailf:cli-suppress-table;
          tailf:cli-show-template-enter "";
          tailf:cli-show-template "        $(alarm) $(sensor_id|ljust:25) $($(value)|rjust:7)  $(critical_lo|rjust:5) $(minor_lo|rjust:5) $(minor_hi|rjust:5) $(critical_hi|rjust:5)\n";
          leaf sensor {
            type string;
          }
          leaf sensor_id {
            type string;
          }
          leaf alarm {
            type string;
          }
          leaf value {
            type string;
          }
          leaf temperature_value {
            type int32;
          }
          leaf critical_lo {
            type int32;
          }
          leaf major_lo {
            type int32;
          }
          leaf minor_lo {
            type int32;
          }
          leaf minor_hi {
            type int32;
          }
          leaf major_hi {
            type int32;
          }
          leaf critical_hi {
            type int32;
          }
        }
      }
    }
  }

  grouping all-volt-data {
    list voltages {
      key "loc_iden";
      config false;
      tailf:info "All Voltage information";
      tailf:cli-suppress-table;
      tailf:cli-full-show-path;
      tailf:cli-drop-node-name;
      tailf:cli-show-template-enter "";
      leaf loc_iden {
        type string;
      }
      leaf print_header {
        type boolean;
        default "false";
      }
      tailf:cli-show-template
        "$(print_header == true?================================================================================
         Location  VOLTAGE                     Value   Crit Minor Minor  Crit
                   Sensor                      \\\\(mV\\\\)    \\\\(Lo\\\\) \\\\(Lo\\\\)  \\\\(Hi\\\\)   \\\\(Hi\\\\)
         --------------------------------------------------------------------------------
         $(loc_iden)       
         $(sensor_attributes|show))";
      list sensor_attributes {
        key "sensor";
        tailf:cli-no-match-completion;
        tailf:cli-drop-node-name;
        tailf:cli-suppress-show-path;
        tailf:cli-suppress-show-match;
        tailf:cli-suppress-table;
        tailf:cli-show-template-enter "";
        tailf:cli-show-template "        $(alarm) $(sensor_id|ljust:25) $($(value)|rjust:7)  $(critical_lo|rjust:5) $(minor_lo|rjust:5) $(minor_hi|rjust:5) $(critical_hi|rjust:5)\n";
        leaf sensor {
          type string;
        }
        leaf sensor_id {
          type string;
        }
        leaf alarm {
          type string;
        }
        leaf value {
          type string;
        }
        leaf temperature_value {
          type int32;
        }
        leaf critical_lo {
          type int32;
        }
        leaf major_lo {
          type int32;
        }
        leaf minor_lo {
          type int32;
        }
        leaf minor_hi {
          type int32;
        }
        leaf major_hi {
          type int32;
        }
        leaf critical_hi {
          type int32;
        }
      }
    }
  }

  grouping current-data {
    container current {
      config false;
      tailf:info "Current information";
      list location {
        key "location";
        tailf:info "Select node location";
        tailf:cli-full-command;
        tailf:cli-no-match-completion;
        tailf:cli-suppress-table;
        tailf:cli-show-template-enter "";
        tailf:callpoint "env_location_cp_curr";
        tailf:cli-show-template-legend
          "================================================================================
           Location  CURRENT                     Value    
                     Sensor                      (mA)    
           --------------------------------------------------------------------------------
          ";
        tailf:cli-show-template
          "$(.legend_shown!=true?================================================================================
           Location  CURRENT                     Value    
                     Sensor                      \\\\(mA\\\\)     
           --------------------------------------------------------------------------------
           )$(location)        
           $(sensor_attributes|show)";
        leaf location {
          type string;
          tailf:display-column-name "Location";
        }
        list sensor_attributes {
          key "sensor";
          tailf:cli-no-match-completion;
          tailf:cli-drop-node-name;
          tailf:cli-suppress-show-path;
          tailf:cli-suppress-show-match;
          tailf:cli-suppress-table;
          tailf:cli-show-template-enter "";
          tailf:cli-show-template "        $(alarm) $(sensor_id|ljust:25) $($(value)|rjust:7)  \n";
          leaf sensor {
            type string;
          }
          leaf sensor_id {
            type string;
          }
          leaf alarm {
            type string;
          }
          leaf value {
            type string;
          }
          leaf temperature_value {
            type int32;
          }
        }
      }
    }
  }

  grouping all-current-data {
    list current {
      key "loc_iden";
      config false;
      tailf:info "All Current information";
      tailf:cli-suppress-table;
      tailf:cli-full-show-path;
      tailf:cli-drop-node-name;
      tailf:cli-show-template-enter "";
      leaf loc_iden {
        type string;
      }
      leaf print_header {
        type boolean;
        default "false";
      }
      tailf:cli-show-template
        "$(print_header == true?================================================================================
         Location  CURRENT                     Value    
                   Sensor                      \\\\(mA\\\\)     
         --------------------------------------------------------------------------------
         $(loc_iden)    
         $(sensor_attributes|show))";
      list sensor_attributes {
        key "sensor";
        tailf:cli-no-match-completion;
        tailf:cli-drop-node-name;
        tailf:cli-suppress-show-path;
        tailf:cli-suppress-show-match;
        tailf:cli-suppress-table;
        tailf:cli-show-template-enter "";
        tailf:cli-show-template "        $(sensor_id|ljust:25) $($(value)|rjust:7)  \n";
        leaf sensor {
          type string;
        }
        leaf sensor_id {
          type string;
        }
        leaf value {
          type string;
        }
      }
    }
  }

  grouping fan-data {
    container fan {
      config false;
      tailf:info "Chassis Fans information";
      list location {
        key "location";
        tailf:info "Select node location";
        tailf:cli-full-command;
        tailf:callpoint "env_location_cp_fan";
        tailf:cli-no-match-completion;
        tailf:cli-suppress-table;
        tailf:cli-show-template-enter "";
        tailf:cli-show-template-legend "";
        leaf location {
          type string;
          tailf:display-column-name "Location";
        }
        tailf:cli-show-template "$(.licounter == 1?$(fan_attributes|show:key=true):$(.legend_shown != true?$(fan_attributes|show:key=true):$(fan_attributes|show:key=false)))";
        list fan_attributes {
          key "logical_slot";
          tailf:cli-drop-node-name;
          tailf:cli-suppress-show-path;
          tailf:cli-suppress-show-match;
          tailf:cli-suppress-table;
          tailf:cli-show-template-enter "";
          tailf:cli-show-template
            "$(.key == true ?$(print_fan_header))$($(speed_space)==1?$(location|ljust:9)    $(fru_PID|ljust:15)    $(fans_speed))$($(speed_space)==2?$(location|ljust:9)  $(fru_PID|ljust:18) $(fans_speed))
             $($(fan_header)==1?$(
             ))";
          leaf print_fan_header {
            type string;
          }
          leaf location {
            type string;
          }
          leaf logical_slot {
            type string;
          }
          leaf fru_PID {
            type string;
          }
          leaf fans_speed {
            type string;
          }
          leaf fan_header {
            type uint32;
          }
          leaf speed_space {
            type uint32;
          }
        }
      }
    }
  }

  grouping all-fan-data {
    list fan {
      key "loc_iden";
      config false;
      tailf:info "Chassis all-Fans information";
      tailf:cli-suppress-table;
      tailf:cli-full-show-path;
      tailf:cli-drop-node-name;
      tailf:cli-show-template-enter "";
      leaf loc_iden {
        type string;
      }
      list fan_attributes {
        key "logical_slot";
        tailf:cli-drop-node-name;
        tailf:cli-suppress-show-path;
        tailf:cli-suppress-show-match;
        tailf:cli-suppress-table;
        tailf:cli-show-template-enter "";
        tailf:cli-show-template
          "$(print_fan_header)$($(speed_space)==1?$(location|ljust:9)    $(fru_PID|ljust:15)    $(fans_speed))$($(speed_space)==2?$(location|ljust:9)  $(fru_PID|ljust:18) $(fans_speed))
           $($(fan_header)==1?$(
           ))";
        leaf print_fan_header {
          type string;
        }
        leaf location {
          type string;
        }
        leaf logical_slot {
          type string;
        }
        leaf fru_PID {
          type string;
        }
        leaf fans_speed {
          type string;
        }
        leaf fan_header {
          type uint32;
        }
        leaf speed_space {
          type uint32;
        }
      }
    }
  }

  grouping power-data {
    container power {
      config false;
      tailf:info "Power supply voltage and current information";
      list location {
        key "location";
        tailf:info "Select node location";
        tailf:cli-full-command;
        tailf:cli-no-match-completion;
        tailf:cli-suppress-table;
        tailf:callpoint "env_location_cp_power";
        tailf:cli-show-template-enter "";
        leaf location {
          type string;
        }
        list pem_attributes {
          key "pem";
          tailf:cli-no-match-completion;
          tailf:cli-drop-node-name;
          tailf:cli-suppress-show-path;
          tailf:cli-suppress-show-match;
          tailf:cli-suppress-table;
          tailf:cli-show-template-enter
            "$($(power_level)==1?$(================================================================================
             CHASSIS LEVEL POWER INFO: $(pem_id)
             ================================================================================
                Total output power capacity $(confgd_power_redundancy_mode|ljust:19) : $($(usable_power_capacity|rjust:7)W + $(protection_power_capacity|rjust:7)W)
                Total output power required                     : $(power_resrv_and_alloc|rjust:7)W
                Total power input                               : $($(system_power_input)|rjust:7)W
                Total power output                              : $($(system_power_used)|rjust:7)W
             ))$($(output_header)==2?$(
             Power Shelf $(shelf_num): 
             ================================================================================
                Power       Supply     ------Input----   ------Output---      Status
                Module      Type        Volts     Amps    Volts     Amps    
             ================================================================================
             ))$($(output_header)==4?$(
             Power Shelf $(shelf_num): 
             ================================================================================
                Power       Supply      --------Input-------   ----Output----       Status
                Module      Type        Volts A/B   Amps A/B   Volts     Amps    
             ================================================================================
             ))$($(output_header)==7?$(
             Power Shelf $(shelf_num): 
             ================================================================================
                Power       Supply      --------Input-------   ----Output----       Status
                Module      Type        Volts A/B       Amps   Volts     Amps    
             ================================================================================
             ))$($(output_header)==5?$(
             Power Group $(shelf_num): 
             ================================================================================
                Power       Supply     ------Input----   ------Output---      Status
                Module      Type        Volts     Amps    Volts     Amps    
             ================================================================================
             ))$($(output_header)==6?$(
             Power Group $(shelf_num): 
             ================================================================================
                Power       Supply      --------Input-------   ----Output----    Status
                Module      Type        Volts A/B   Amps A/B   Volts     Amps    
             ================================================================================
             ))$($(power_level)==2?$(   $(pem|ljust:11) $(supply_type|ljust:9) $($(input_voltage|rjust:7)) $($(input_current|rjust:8)) $($(output_voltage|floatformat:1)|rjust:8) $($(output_current|floatformat:1)|rjust:8)    $(status) 
             ))$($(power_level)==4?$(   $(pem|ljust:11) $(supply_type|ljust:9) $($(input_voltage|rjust:11)) $($(input_current|rjust:10)) $($(output_voltage|floatformat:1)|rjust:7) $($(output_current|floatformat:1)|rjust:8)    $(status) 
             ))$($(power_level)==7?$(   $(pem|ljust:11) $(supply_type|ljust:9) $($(input_voltage|rjust:11)) $($(input_current|rjust:10)) $($(output_voltage|floatformat:1)|rjust:7) $($(output_current|floatformat:1)|rjust:8)    $(status) 
             ))$($(output_footer)==2?$(
             Total of Power Shelf $(shelf_num):    $($(input_power_to_ps)|rjust:7)W/$($(input_current_to_ps)|rjust:5)A    $($(output_power_from_ps)|rjust:6)W/$($(output_current_from_ps|floatformat:1)|rjust:5)A
             ))$($(output_footer)==3?$(
             Total of Power Shelf $(shelf_num):  $($(input_power_to_ps)|rjust:8)W/$($(input_current_to_ps)|rjust:13)A  $($(output_power_from_ps)|rjust:6)W/$($(output_current_from_ps|floatformat:1)|rjust:5)A
             ))$($(output_footer)==7?$(
             Total of Power Shelf $(shelf_num):  $($(input_power_to_ps)|rjust:12)W/$($(input_current_to_ps)|rjust:8)A  $($(output_power_from_ps)|rjust:6)W/$($(output_current_from_ps|floatformat:1)|rjust:6)A
             ))$($(output_footer)==5?$(
             Total of Power Group $(shelf_num):    $($(input_power_to_ps)|rjust:7)W/$($(input_current_to_ps)|rjust:5)A    $($(output_power_from_ps)|rjust:6)W/$($(output_current_from_ps|floatformat:1)|rjust:5)A
             ))$($(output_footer)==6?$(
             Total of Power Group $(shelf_num):  $($(input_power_to_ps)|rjust:8)W/$($(input_current_to_ps)|rjust:13)A  $($(output_power_from_ps)|rjust:6)W/$($(output_current_from_ps|floatformat:1)|rjust:5)A
             ))$($(output_header)==3?$(
             ================================================================================
                Location     Card Type            Power       Power       Status
                                                  Allocated   Used
                                                  Watts       Watts
             ================================================================================
             ))$($(power_level)==3?$(   $(card_type|ljust:12) $(pem_id|ljust:20) $(power_allocated|rjust:5)       $(power_consumed|rjust:5)       $(power_status) 
             ))";
          tailf:cli-show-template "";
          leaf pem {
            type string;
          }
          leaf pem_id {
            type string;
          }
          leaf card_type {
            type string;
          }
          leaf ps_type {
            type string;
          }
          leaf shelf_num {
            type uint16;
          }
          leaf supply_type {
            type string;
          }
          leaf input_voltage {
            type string;
          }
          leaf input_current {
            type string;
          }
          leaf output_voltage {
            type xs:double;
          }
          leaf output_current {
            type xs:double;
          }
          leaf status {
            type string;
          }
          leaf input_power_to_ps {
            type uint32;
          }
          leaf input_current_to_ps {
            type string;
          }
          leaf output_power_from_ps {
            type uint32;
          }
          leaf output_current_from_ps {
            type xs:double;
          }
          leaf power_allocated {
            type uint32;
          }
          leaf power_consumed {
            type string;
          }
          leaf power_status {
            type string;
          }
          leaf confgd_power_redundancy_mode {
            type string;
          }
          leaf usable_power_capacity {
            type uint32;
          }
          leaf protection_power_capacity {
            type uint32;
          }
          leaf power_resrv_and_alloc {
            type uint32;
          }
          leaf system_power_used {
            type uint32;
          }
          leaf system_power_input {
            type uint32;
          }
          leaf power_level {
            type uint16;
          }
          leaf output_header {
            type uint16;
          }
          leaf output_footer {
            type uint16;
          }
          leaf ps_sum_footer {
            type uint16;
          }
        }
      }
    }
  }

  grouping altitude-data {
    container altitude {
      config false;
      tailf:info "Chassis altitude in Meters";
      tailf:callpoint "env_location_cp_altitude";
      list location {
        key "location";
        tailf:cli-drop-node-name;
        tailf:cli-suppress-show-path;
        tailf:cli-suppress-show-match;
        tailf:cli-suppress-table;
        tailf:cli-show-template-enter "";
        tailf:cli-show-template-legend
          "================================================================================
              Location      Altitude Value (Meters)     Source
           --------------------------------------------------------------------------------
          ";
        leaf location {
          type string;
        }
        tailf:cli-show-template "$(alt_attributes|show)";
        list alt_attributes {
          key "sensor";
          tailf:cli-no-match-completion;
          tailf:cli-drop-node-name;
          tailf:cli-suppress-show-path;
          tailf:cli-suppress-show-match;
          tailf:cli-suppress-table;
          tailf:cli-show-template-enter "";
          tailf:cli-show-template "   $($(rack|hex)|ljust:2)            $(sensor_value|ljust:4)                        $(source|ljust:25)\n";
          leaf sensor {
            type string;
          }
          leaf rack {
            type uint32;
          }
          leaf sensor_value {
            type string;
          }
          leaf source {
            type string;
          }
        }
      }
    }
  }

  grouping rack-location {
    leaf all {
      type empty;
      tailf:cli-drop-node-name;
    }
    list location {
      key "rackId";
      tailf:info "rack-id";
      tailf:cli-optional-in-sequence;
      leaf rackId {
        type calvados:rack-id;
      }
    }
  }

  grouping router-group {
    container router {
      tailf:info "chassis environmental properties";
      tailf:cli-sequence-commands;
      container altitude {
        tailf:info "chassis altitude in Meters";
        container all {
          tailf:cli-drop-node-name;
          leaf num_meters {
            type uint32 {
              range "1..4000";
            }
            tailf:cli-drop-node-name;
          }
        }
        container rack_loc {
          tailf:cli-drop-node-name;
          list location {
            key "rackId";
            tailf:info "rack-id";
            tailf:cli-sequence-commands;
            tailf:cli-incomplete-command;
            tailf:cli-compact-syntax;
            tailf:cli-suppress-mode;
            tailf:cli-delete-when-empty;
            leaf rackId {
              type calvados:rack-id;
            }
            leaf num_meters {
              type uint32 {
                range "1..4000";
              }
              tailf:cli-drop-node-name;
            }
          }
        }
      }
    }
  }

  grouping air-filter-group {
    container air-filter {
      tailf:info "chassis air-filter status";
      tailf:cli-sequence-commands;
      container replaced {
        tailf:info "air-filter replaced date";
        container all {
          tailf:cli-drop-node-name;
          leaf date {
            type xs:date;
          }
        }
        container rack_loc {
          tailf:cli-drop-node-name;
          list location {
            key "rackId";
            tailf:info "rack-id";
            tailf:cli-sequence-commands;
            tailf:cli-incomplete-command;
            tailf:cli-compact-syntax;
            tailf:cli-suppress-mode;
            tailf:cli-delete-when-empty;
            leaf rackId {
              type calvados:rack-id;
            }
            leaf date {
              type xs:date;
            }
          }
        }
      }
    }
  }

  grouping fan-ctrl-group {
    container fan-ctrl {
      tailf:info "Control chassis fan status";
      tailf:hidden "advanced-grp";
      tailf:cli-sequence-commands;
      container disable {
        tailf:info "admin state of chassis fan";
        container rack_loc {
          tailf:cli-drop-node-name;
          uses rack-location;
        }
      }
    }
  }

  grouping temp-monitor-group {
    container temperature {
      tailf:info "Set cards temperature monitoring status";
      tailf:cli-sequence-commands;
      tailf:hidden "advanced-grp";
      container disable {
        tailf:info "admin state of temperature monitoring";
        container rack_loc {
          tailf:cli-drop-node-name;
          uses rack-location;
        }
      }
    }
  }

  grouping env-monitor-group {
    container monitoring {
      tailf:info "Overall Environment monitoring status";
      tailf:cli-sequence-commands;
      tailf:hidden "advanced-grp";
      container disable {
        tailf:info "admin state of temperature monitoring";
        container rack_loc {
          tailf:cli-drop-node-name;
          uses rack-location;
        }
      }
    }
  }

  grouping power-mgmt-group {
    container action {
      tailf:info "action for controlling power budget to not exceed power capacity";
      tailf:cli-sequence-commands;
      container disable {
        tailf:info "disable card power on control action";
        container rack_loc {
          tailf:cli-drop-node-name;
          uses rack-location;
        }
      }
    }
    container single-feed-mode {
      tailf:info "action for suppressing alarms for missing feed(only for dual feed) supplies";
      tailf:cli-sequence-commands;
      container enable {
        tailf:info "enable the suppression of alarms";
        container rack_loc {
          tailf:cli-drop-node-name;
          uses rack-location;
        }
      }
    }
    container extended-temp {
      tailf:info "action for setting power budget for extended temp mode";
      tailf:cli-sequence-commands;
      container enable {
        tailf:info "enable the extended temp";
        container rack_loc {
          tailf:cli-drop-node-name;
          uses rack-location;
        }
      }
    }
    container redundancy-num-pms {
      tailf:info "disable power tray level redundancy and convert to power module redundancy";
      container all {
        tailf:cli-drop-node-name;
        leaf num_pm {
          type envmon-types:num_pm;
          tailf:cli-drop-node-name;
        }
      }
      container rack_loc {
        tailf:cli-drop-node-name;
        list location {
          key "rackId";
          tailf:info "rack-id";
          tailf:cli-sequence-commands;
          tailf:cli-incomplete-command;
          tailf:cli-compact-syntax;
          tailf:cli-suppress-mode;
          tailf:cli-delete-when-empty;
          leaf rackId {
            type calvados:rack-id;
          }
          leaf num_pm {
            type envmon-types:num_pm;
            tailf:cli-drop-node-name;
          }
        }
      }
    }
  }

  grouping cmd_types {
    container oper {
      config false;
      description
        "environment operational (show) data";
      tailf:callpoint "env_oper_cp";
      tailf:cli-drop-node-name;
      uses temp-data;
      uses volt-data;
      uses current-data;
      uses fan-data;
      uses power-data;
      uses altitude-data;
    }
    container all {
      config false;
      tailf:info "All environment monitor parameters";
      tailf:callpoint "env_all_cp";
      list location {
        key "location";
        tailf:info "Select all-level node location";
        tailf:cli-full-command;
        tailf:cli-suppress-table;
        tailf:cli-no-match-completion;
        tailf:cli-show-template-enter "";
        leaf location {
          type string;
          tailf:display-column-name "Location";
        }
        uses all-temp-data;
        uses all-volt-data;
        uses all-current-data;
        uses all-fan-data;
      }
    }
    container config {
      description
        "environment configurational data";
      tailf:cli-drop-node-name;
      uses router-group;
      uses air-filter-group;
      uses fan-ctrl-group;
      uses temp-monitor-group;
      uses env-monitor-group;
      uses envmon-types:fan-speed-group;
      uses envmon-types:fan-ctrl-optics-group;
      uses envmon-types:vin-uv-shut-group;
    }
  }
  tailf:id "http://www.cisco.com/panini/calvados/envmon";

  container environment {
    tailf:info "environment data";
    tailf:cli-show-template "$(oper|show)";
    uses cmd_types;
    uses show_trace:traceable;
  }
  container power-mgmt {
    tailf:info "Manage Chassis Power Trays and PEMs";
    container config {
      description
        "Power Trays and PEMs configurational data";
      tailf:cli-drop-node-name;
      uses power-mgmt-group;
    }
  }
}
