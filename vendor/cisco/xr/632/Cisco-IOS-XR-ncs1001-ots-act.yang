module Cisco-IOS-XR-ncs1001-ots-act {
  namespace "http://cisco.com/ns/yang/Cisco-IOS-XR-ncs1001-ots-act";
  prefix ncs1001-ots-act;

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ncs1001-ots-act package configuration.
     
     This module contains definitions
     for the following management objects:
       hardware-module-action: NCS1k1 HW module config
     
     Copyright (c) 2013-2017 by Cisco Systems, Inc.
     All rights reserved.";

  revision 2017-08-04 {
    description
      "IOS XR 6.3.1 revision.";
  }

  typedef Ots-psm-manual-switch {
    type enumeration {
      enum "working" {
        value 1;
        description
          "Working port";
      }
      enum "protected" {
        value 2;
        description
          "Protected port";
      }
    }
    description
      "Ots psm manual switch";
  }

  rpc psm-manual-switch-to {
    description
      "Psm manual switch to port";
    input {
      leaf slot-id {
        type uint32 {
          range "1..3";
        }
        mandatory true;
        description
          "Set Slot";
      }
      leaf manual-switch-to {
        type Ots-psm-manual-switch;
        mandatory true;
        description
          "Switch active path to selected port";
      }
    }
  }
}
