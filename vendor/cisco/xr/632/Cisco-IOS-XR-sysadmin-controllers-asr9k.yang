module Cisco-IOS-XR-sysadmin-controllers-asr9k {
  namespace "http://www.cisco.com/ns/yang/Cisco-IOS-XR-sysadmin-controllers-ASR9K";
  prefix calvados_controllers;

  import Cisco-IOS-XR-sysadmin-ethsw-esdma-cli-asr9k {
    prefix esdma;
  }
  import tailf-common {
    prefix tailf;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains a collection of YANG
     definitions for Cisco IOS-XR SysAdmin configuration.
     
     This module defines the top level container for
     all hardware devices managed in Sysadmin.
     
     Copyright(c) 2011-2017 by Cisco Systems, Inc.
     All rights reserved.";

  revision 2017-11-10 {
    description
      "Changed the namespace for ASR9K platform";
  }
  revision 2017-01-31 {
    description
      "Changed the namespace and module name";
  }
  revision 2015-02-23 {
    description
      "Initial Revision";
  }
  tailf:id "http://cisco.com/panini/calvados/calvados_controllers";

  container controller {
    tailf:info "Access to hardware controller data";
    tailf:cli-incomplete-show-path;
    container switch {
      tailf:info "Control plane Ethernet switch data";
      uses esdma:switch;
    }
  }
}
