module Cisco-IOS-XR-sysadmin-ethsw-esdma-sdr {
  namespace "http://www.cisco.com/ns/yang/Cisco-IOS-XR-sysadmin-ethsw-esdma-sdr";
  prefix esdma_sdr;

  import tailf-common {
    prefix tailf;
  }
  import Cisco-IOS-XR-sysadmin-ethsw-esdma-types {
    prefix esdma_types;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains the YANG definitions
     for the Cisco IOS-XR SysAdmin
     'show controller switch sdr' commands.
     
     Copyright(c) 2011-2017 by Cisco Systems, Inc.
     All rights reserved.";

  revision 2017-05-01 {
    description
      "Namespace change to comply with Cisco guidelines on namespace";
  }
  revision 2016-07-06 {
    description
      "Initial revision with content extracted from esdma_cli.yang.";
  }

  grouping sdr-detail-group {
    container sdr-detail {
      tailf:cli-drop-node-name;
      tailf:cli-incomplete-show-path;
      tailf:callpoint "esdma_switch_sdr_detail_statistics";
      list sdr-id {
        key "sdr";
        tailf:cli-drop-node-name;
        tailf:cli-incomplete-show-path;
        tailf:info "SDR identifier to retrieve detail for";
        leaf sdr {
          type esdma_types:esdma-sdr-id;
          tailf:cli-drop-node-name;
        }
        container port-statistics {
          tailf:cli-incomplete-show-path;
          tailf:info "Display SDR statistics for specific SDR";
          list location {
            key "rack card switch-id";
            tailf:info "Location information for switch SDR statistics";
            tailf:cli-full-command;
            tailf:cli-suppress-table;
            tailf:cli-key-format "$(1)/$(2)/$(3)";
            leaf rack {
              type esdma_types:esdma-rack-num-enum;
            }
            leaf card {
              type esdma_types:esdma-cpu;
              description
                "Card that owns a switch of interest";
            }
            leaf switch-id {
              type esdma_types:esdma-switch-type-enum;
              description
                "Switch type";
            }
            list port-iter {
              key "port";
              tailf:cli-drop-node-name;
              tailf:cli-full-command;
              leaf port {
                type esdma_types:esdma-switch-port-type;
                description
                  "Switch port";
                tailf:display-column-name "Switch Port";
              }
              list traffic-type-id {
                key "traffic-type";
                tailf:cli-drop-node-name;
                tailf:cli-suppress-show-path;
                tailf:cli-suppress-show-match;
                leaf traffic-type {
                  type esdma_types:esdma-sdr-traffic-type;
                  tailf:display-column-name "Traffic Type";
                }
                list direction-id {
                  key "direction";
                  tailf:cli-drop-node-name;
                  leaf direction {
                    type esdma_types:switch-data-direction-enum;
                    description
                      "Packet direction this rule applies to";
                    tailf:display-column-name "Packet Direction";
                  }
                  list traffic-class-id {
                    key "tc";
                    tailf:cli-drop-node-name;
                    leaf tc {
                      type esdma_types:switch-traffic-class-enum;
                      description
                        "Traffic class (0->7) for these statistics.";
                      tailf:display-column-name "Traffic Class";
                      tailf:cli-value-display-template "$(.!=-1?$(.):-)";
                    }
                    leaf green-packets {
                      type uint64;
                      description
                        "Counts packets within the committed information rate for a traffic class on this VLAN.";
                      tailf:display-column-name "Conforming";
                    }
                    leaf yellow-packets {
                      type uint64;
                      description
                        "Counts packets above the committed information rate, but within the excess information rate for a traffic class on this VLAN.";
                      tailf:display-column-name "Exceeding";
                    }
                    leaf red-packets {
                      type uint64;
                      description
                        "Counts packets above the excess information rate for a traffic class on this VLAN. Generally, these packets are dropped.";
                      tailf:display-column-name "Dropped";
                    }
                  }
                }
              }
            }
          }
        }
      }
    }
  }

  grouping sdr-summary-port-stats {
    container port-statistics {
      tailf:cli-incomplete-show-path;
      tailf:callpoint "esdma_switch_sdr_summary_statistics_data";
      tailf:info "Display SDR port statistics summary";
      list location {
        key "rack card switch-id";
        tailf:info "Location information for switch SDR statistics";
        tailf:cli-full-command;
        tailf:cli-suppress-table;
        tailf:cli-key-format "$(1)/$(2)/$(3)";
        leaf rack {
          type esdma_types:esdma-rack-num-enum;
        }
        leaf card {
          type esdma_types:esdma-cpu;
          description
            "Card that owns a switch of interest to display the SDR configuration for";
        }
        leaf switch-id {
          type esdma_types:esdma-switch-type-enum;
          description
            "Switch type";
        }
        list port-iter {
          key "port";
          tailf:cli-drop-node-name;
          tailf:cli-full-command;
          leaf port {
            type esdma_types:esdma-switch-port-type;
            description
              "Switch port";
            tailf:display-column-name "Switch Port";
          }
          list sdr-id {
            key "sdr";
            tailf:cli-drop-node-name;
            tailf:info "SDR identifier to retrieve statistics for";
            tailf:cli-suppress-show-path;
            tailf:cli-suppress-show-match;
            leaf sdr {
              type esdma_types:esdma-sdr-id;
              tailf:display-column-name "SDR ID";
            }
            leaf esd-sdr-name {
              type string;
              tailf:display-column-name "SDR Name";
            }
            list traffic-type-id {
              key "traffic-type";
              tailf:cli-drop-node-name;
              leaf traffic-type {
                type esdma_types:esdma-sdr-traffic-type;
                tailf:display-column-name "Traffic Type";
              }
              list direction-id {
                key "direction";
                tailf:cli-drop-node-name;
                leaf direction {
                  type esdma_types:switch-data-direction-enum;
                  description
                    "Packet direction this rule applies to";
                  tailf:display-column-name "Packet Direction";
                }
                leaf green-packets {
                  type uint64;
                  description
                    "Counts packets within the committed information rate for all traffic classes on this SDR.";
                  tailf:display-column-name "Conforming";
                }
                leaf yellow-packets {
                  type uint64;
                  description
                    "Counts packets above the committed information rate, but within the excess information rate for all traffic classes on this SDR.";
                  tailf:display-column-name "Exceeding";
                }
                leaf red-packets {
                  type uint64;
                  description
                    "Counts packets above the excess information rate for all traffic classes on this SDR. Generally, these packets are dropped.";
                  tailf:display-column-name "Dropped";
                }
              }
            }
          }
        }
      }
    }
  }

  grouping sdr-summary-global-stats {
    container global-statistics {
      tailf:cli-incomplete-show-path;
      tailf:callpoint "esdma_switch_sdr_global_statistics_data";
      tailf:info "Display SDR global statistics summary";
      list location {
        key "rack card switch-id";
        tailf:info "Location information for switch SDR statistics";
        tailf:cli-full-command;
        tailf:cli-suppress-table;
        tailf:cli-key-format "$(1)/$(2)/$(3)";
        leaf rack {
          type esdma_types:esdma-rack-num-enum;
        }
        leaf card {
          type esdma_types:esdma-cpu;
          description
            "Card that owns a switch of interest to display the SDR configuration for";
        }
        leaf switch-id {
          type esdma_types:esdma-switch-type-enum;
          description
            "Switch type";
        }
        list sdr-id {
          key "sdr";
          tailf:cli-drop-node-name;
          tailf:cli-enforce-table;
          tailf:cli-suppress-show-path;
          tailf:cli-suppress-show-match;
          tailf:info "SDR identifier to retrieve statistics for";
          leaf sdr {
            type esdma_types:esdma-sdr-id;
            tailf:display-column-name "SDR ID";
            tailf:cli-column-width "6";
          }
          leaf esd-sdr-name {
            type string;
            tailf:display-column-name "SDR Name";
          }
          list traffic-type-id {
            key "traffic-type";
            tailf:cli-drop-node-name;
            leaf traffic-type {
              type esdma_types:esdma-sdr-traffic-type;
              tailf:display-column-name "Traffic Type";
            }
            list traffic-class-id {
              key "tc";
              tailf:cli-drop-node-name;
              leaf tc {
                type esdma_types:switch-traffic-class-enum;
                description
                  "Traffic class (0->7) for these statistics.";
                tailf:display-column-name "Traffic Class";
              }
              leaf green-packets {
                type uint64;
                description
                  "Counts packets within the committed information rate for a traffic class on this VLAN.";
                tailf:display-column-name "Conforming";
              }
              leaf yellow-packets {
                type uint64;
                description
                  "Counts packets above the committed information rate, but within the excess information rate for a traffic class on this VLAN.";
                tailf:display-column-name "Exceeding";
              }
              leaf red-packets {
                type uint64;
                description
                  "Counts packets above the excess information rate for a traffic class on this VLAN. Generally, these packets are dropped.";
                tailf:display-column-name "Dropped";
              }
            }
          }
        }
      }
    }
  }

  grouping sdr-summary-policers {
    container policers {
      tailf:cli-incomplete-show-path;
      tailf:callpoint "esdma_switch_sdr_summary_policer_data";
      tailf:info "Display SDR policer summary";
      list location {
        key "rack card switch-id";
        tailf:info "Location information for SDR policer data";
        tailf:cli-full-command;
        tailf:cli-suppress-table;
        tailf:cli-key-format "$(1)/$(2)/$(3)";
        leaf rack {
          type esdma_types:esdma-rack-num-enum;
        }
        leaf card {
          type esdma_types:esdma-cpu;
        }
        leaf switch-id {
          type esdma_types:esdma-switch-type-enum;
        }
        container esd-policer-status {
          tailf:cli-drop-node-name;
          tailf:cli-suppress-show-path;
          tailf:cli-suppress-show-match;
          tailf:cli-show-template
            "Summary Policer Information for Switch $(../rack)/$(../card)/$(../switch-id)
             $(indent-group|show:indent=4)";
          container indent-group {
            tailf:cli-drop-node-name;
            leaf esd-port-policing-enabled {
              type esdma_types:esdma-switch-yes-no-enum;
              tailf:alt-name "Port Policing Enabled: ";
            }
            leaf esd-port-committed-burst-size {
              type uint32;
              tailf:alt-name "Port Committed Burst Size (bytes): ";
            }
            leaf esd-port-peak-burst-size {
              type uint32;
              tailf:alt-name "Port Peak Burst Size (bytes): ";
            }
            leaf esd-port-policer-mru {
              type uint32;
              tailf:alt-name "Port Policer MRU (bytes): ";
            }
            leaf esd-global-policing-enabled {
              type esdma_types:esdma-switch-yes-no-enum;
              tailf:alt-name "Global Policing Enabled: ";
            }
            leaf esd-global-committed-burst-size {
              type uint32;
              tailf:alt-name "Global Committed Burst Size (bytes): ";
            }
            leaf esd-global-peak-burst-size {
              type uint32;
              tailf:alt-name "Global Peak Burst Size (bytes): ";
            }
            leaf esd-global-policer-mru {
              type uint32;
              tailf:alt-name "Global Policer MRU (bytes): ";
            }
          }
        }
        list sdr-id {
          key "sdr";
          tailf:cli-drop-node-name;
          tailf:cli-full-command;
          tailf:cli-suppress-show-path;
          tailf:cli-suppress-show-match;
          tailf:cli-enforce-table;
          tailf:info "SDR identifier to retrieve policer data for";
          tailf:cli-table-legend " ";
          leaf sdr {
            type esdma_types:esdma-sdr-id;
            tailf:display-column-name "SDR ID";
            tailf:cli-column-width "6";
          }
          leaf esd-sdr-name {
            type string;
            tailf:display-column-name "SDR Name";
          }
          leaf esd-sdr-cir {
            type esdma_types:esd-percentage;
            tailf:display-column-name "SDR CIR(%)";
          }
          leaf esd-sdr-pir {
            type esdma_types:esd-percentage;
            tailf:display-column-name "SDR PIR(%)";
          }
          list esd-sdr-cos-type-iter {
            key "esd-sdr-cos-type";
            leaf esd-sdr-cos-type {
              type esdma_types:esd-cir-eir-type;
              tailf:display-column-name "CoS B/W";
            }
            leaf esd-sdr-cos-0 {
              type esdma_types:esd-percentage;
              tailf:display-column-name "CoS 0(%)";
            }
            leaf esd-sdr-cos-1 {
              type esdma_types:esd-percentage;
              tailf:display-column-name "CoS 1(%)";
            }
            leaf esd-sdr-cos-2 {
              type esdma_types:esd-percentage;
              tailf:display-column-name "CoS 2(%)";
            }
            leaf esd-sdr-cos-3 {
              type esdma_types:esd-percentage;
              tailf:display-column-name "CoS 3(%)";
            }
            leaf esd-sdr-cos-4 {
              type esdma_types:esd-percentage;
              tailf:display-column-name "CoS 4(%)";
            }
            leaf esd-sdr-cos-5 {
              type esdma_types:esd-percentage;
              tailf:display-column-name "CoS 5(%)";
            }
            leaf esd-sdr-cos-6 {
              type esdma_types:esd-percentage;
              tailf:display-column-name "CoS 6(%)";
            }
            leaf esd-sdr-cos-7 {
              type esdma_types:esd-percentage;
              tailf:display-column-name "CoS 7(%)";
            }
          }
        }
      }
    }
  }

  grouping sdr-summary-group {
    uses sdr-summary-port-stats;
    uses sdr-summary-global-stats;
    uses sdr-summary-policers;
  }

  grouping switch-sdr-group {
    container sdr {
      tailf:info "Control Plane Ethernet SDR Information";
      tailf:cli-incomplete-show-path;
      uses sdr-summary-group;
      uses sdr-detail-group;
    }
  }
  tailf:id "http://cisco.com/panini/calvados/esdma/esdma_sdr";
}
