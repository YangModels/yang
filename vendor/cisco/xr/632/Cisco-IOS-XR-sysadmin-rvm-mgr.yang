module Cisco-IOS-XR-sysadmin-rvm-mgr {
  namespace "http://www.cisco.com/ns/yang/Cisco-IOS-XR-sysadmin-rvm-mgr";
  prefix rvmmh;

  import tailf-common {
    prefix tailf;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains a collection of YANG
     definitions for Cisco IOS-XR SysAdmin configuration.
     
     Copyright(c) 2013-2017 by Cisco Systems, Inc.
     All rights reserved.";

  revision 2017-04-12 {
    description
      "Changed the namespace and module name";
  }
  revision 2016-05-12 {
    description
      "Initial Version";
  }

  typedef nodetype_td {
    type enumeration {
      enum "sysadmin" {
        value 1;
      }
      enum "service" {
        value 2;
      }
    }
  }

  typedef flagtype_td {
    type enumeration {
      enum "clear" {
        value 0;
      }
      enum "set" {
        value 1;
      }
    }
  }
  tailf:id "http://cisco.com/calvados/rvmm";

  container RVM {
    config false;
    description
      "RVM Manager Info";
    tailf:callpoint "rvmm_show_location";
    list all-locations {
      key "location";
      tailf:cli-drop-node-name;
      tailf:cli-suppress-table;
      tailf:cli-show-template-enter "------ RVMs Info for location $(location) ------\n";
      leaf location {
        type string;
        tailf:cli-expose-key-name;
      }
      container objects {
        config false;
        description
          "RVM Manager Info";
        tailf:callpoint "rvmm_show_location";
        list all-objs {
          key "index";
          tailf:cli-show-template-enter
            "
             ---- Object DB Info -----
              ";
          tailf:cli-suppress-table;
          tailf:cli-suppress-show-path;
          tailf:cli-suppress-show-match;
          tailf:cli-show-template
            " ------------------
               Index     : $(index)
               Allocated : $(num_allocated)
               Freed     : $(num_freed)
               Objects   : $(num_objects)
              ------------------
            ";
          leaf index {
            type uint32;
            description
              "Index into obj_db array";
          }
          leaf num_allocated {
            type uint32;
            description
              "Number of allocated nodes";
          }
          leaf num_freed {
            type uint32;
            description
              "Number of freed nodes";
          }
          leaf num_objects {
            type uint32;
            description
              "Number of current object nodes";
          }
        }
      }
      container node {
        config false;
        description
          "RVM Manager Node Info";
        tailf:callpoint "rvmm_show_location";
        list all-nodes {
          key "ipv4_addr";
          tailf:cli-show-template-enter
            "
             ---- Node Info -----
              ";
          tailf:cli-suppress-table;
          tailf:cli-suppress-show-path;
          tailf:cli-suppress-show-match;
          tailf:cli-show-template
            " ------------------
               IP Address: $(ipv4_addr_str)
               Info      : $(node_info)
               Heartbeat : $(node_hb_info)
               Card Info : $(node_card_info)
              ------------------
            ";
          leaf ipv4_addr {
            type uint32;
            description
              "IP address of the node";
          }
          leaf ipv4_addr_str {
            type string;
            description
              "IP address of the node in string format";
          }
          leaf node_info {
            type string;
            description
              "Node type state and flag";
          }
          leaf node_hb_info {
            type string;
            description
              "Node heartbeat related info";
          }
          leaf node_card_info {
            type string;
            description
              "Card info the node belongs to";
          }
        }
      }
      container card {
        config false;
        description
          "RVM Manager Card Info";
        tailf:callpoint "rvmm_show_location";
        list all-cards {
          key "serial_num";
          tailf:cli-show-template-enter
            "
             ---- Card Info -----
              ";
          tailf:cli-suppress-table;
          tailf:cli-suppress-show-path;
          tailf:cli-suppress-show-match;
          tailf:cli-show-template
            " ------------------
               Serial Num     : $(serial_num)
               Flags          : $(card_flag)
               Card Info      : $(card_info)
               Sysadmin Nodes : $(sysadmin_nodes)
               XR Nodes       : $(xr_nodes)
              ------------------
            ";
          leaf serial_num {
            type string;
            description
              "Serial number of the card";
          }
          leaf card_flag {
            type string;
            description
              "Card flags";
          }
          leaf card_info {
            type string;
            description
              "Card rack and slot num";
          }
          leaf sysadmin_nodes {
            type string;
            description
              "Sysadmin nodes on this card";
          }
          leaf xr_nodes {
            type string;
            description
              "XR nodes on this card";
          }
        }
      }
    }
  }
}
