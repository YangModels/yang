submodule Cisco-IOS-XR-asr9k-np-oper-sub1 {
  belongs-to Cisco-IOS-XR-asr9k-np-oper {
    prefix Cisco-IOS-XR-asr9k-np-oper;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR asr9k-np package operational data.
     
     Copyright (c) 2013-2017 by Cisco Systems, Inc.
     All rights reserved.";

  revision 2015-11-09 {
    description
      "IOS XR 6.0 revision.";
  }

  grouping PRM-NP-FAST-DROP-A {
    description
      "NP fast drop";
    leaf interface-name {
      type string;
      description
        "Interface name";
    }
    leaf counter-value {
      type uint64;
      description
        "The Value of the counter";
    }
  }

  grouping PRM-NP-FAST-DROP {
    description
      "Array of NP Fast Drop Counters";
    list np-fast-drop {
      description
        "Array of NP Fast Drop Counters";
      uses PRM-NP-FAST-DROP-A;
    }
  }

  grouping PRM-NP-COUNTERS-A {
    description
      "NP Counters";
    leaf counter-index {
      type uint32;
      description
        "Counter Index";
    }
    leaf counter-value {
      type uint64;
      description
        "The accurate value of the counter";
    }
    leaf rate {
      type uint32;
      units "packet/s";
      description
        "Rate in Packets Per Second";
    }
    leaf counter-type {
      type string;
      description
        "Counter TypeDROP: Drop counterPUNT: Punt
         counterFWD:  Forward or generic counterUNKNOWN:
         Counter type unknown";
    }
    leaf counter-name {
      type string;
      description
        "Counter name";
    }
  }

  grouping PRM-NP-COUNTERS {
    description
      "Array of NP Counters";
    list np-counter {
      description
        "Array of NP Counters";
      uses PRM-NP-COUNTERS-A;
    }
  }

  grouping TCAM-VMR-ENTRY {
    description
      "application vmr entry";
    leaf num-vmr-ids {
      type uint32;
      description
        "Vmr IDs";
    }
    leaf num-active-entries {
      type uint32;
      description
        "The number of active vmr entries";
    }
    leaf num-allocated-entries {
      type uint32;
      description
        "The number of active vmr entries";
    }
  }

  grouping ACL-COMM-REGION {
    description
      "acl common region";
    leaf free-entries {
      type uint32;
      description
        "Free entries in the table";
    }
    leaf allocated-entries {
      type uint32;
      description
        "The number of active vmr entries";
    }
  }

  grouping TCAM-ODS-TABLE {
    description
      "tcam ods table";
    container acl-common {
      description
        "ACL common region";
      uses ACL-COMM-REGION;
    }
    container app-id-ifib {
      description
        "app IFIB entry";
      uses TCAM-VMR-ENTRY;
    }
    container app-id-qos {
      description
        "app qos entry";
      uses TCAM-VMR-ENTRY;
    }
    container app-id-acl {
      description
        "app acl entry";
      uses TCAM-VMR-ENTRY;
    }
    container app-id-afmon {
      description
        "app afmon entry";
      uses TCAM-VMR-ENTRY;
    }
    container app-id-li {
      description
        "app LI entry";
      uses TCAM-VMR-ENTRY;
    }
    container app-id-pbr {
      description
        "app PBR entry";
      uses TCAM-VMR-ENTRY;
    }
    container app-id-edpl {
      description
        "app EDPL entry";
      uses TCAM-VMR-ENTRY;
    }
    leaf free-entries {
      type uint32;
      description
        "Free entries in the table";
    }
    leaf reserved-entries {
      type uint32;
      description
        "The number of active vmr entries";
    }
  }

  grouping TCAM-L2-TABLE-A {
    description
      "tcam l2 table";
    leaf partition-id {
      type uint32;
      description
        "PartitionID";
    }
    leaf priority {
      type uint32;
      description
        "Priority";
    }
    leaf valid-entries {
      type uint32;
      description
        "Valid Entries";
    }
    leaf free-entries {
      type uint32;
      description
        "Free Entries";
    }
  }

  grouping TCAM-SHOW-SUM {
    description
      "tcam summary";
    container tcam-lt-ods2 {
      description
        "TCAM ODS2 partition summary";
      uses TCAM-ODS-TABLE;
    }
    container tcam-lt-ods8 {
      description
        "TCAM ODS8 partition summary";
      uses TCAM-ODS-TABLE;
    }
    list tcam-lt-l2 {
      description
        "Array of TCAM L2 partition summaries";
      uses TCAM-L2-TABLE-A;
    }
  }

  grouping TCAM-VMR-ENTRY-INT {
    description
      "application vmr entry internal";
    leaf num-vmr-ids {
      type uint32;
      description
        "Vmr IDs";
    }
    leaf total-used-entries {
      type uint32;
      description
        "number of used vmr entries";
    }
    leaf total-allocated-entries {
      type uint32;
      description
        "The number of active vmr entries";
    }
  }

  grouping TCAM-ODS-TABLE-INT {
    description
      "tcam ods table internal";
    container app-id-ifib {
      description
        "app IFIB entry";
      uses TCAM-VMR-ENTRY-INT;
    }
    container app-id-qos {
      description
        "app qos entry";
      uses TCAM-VMR-ENTRY-INT;
    }
    container app-id-acl {
      description
        "app acl entry";
      uses TCAM-VMR-ENTRY-INT;
    }
    container app-id-afmon {
      description
        "app afmon entry";
      uses TCAM-VMR-ENTRY-INT;
    }
    container app-id-li {
      description
        "app LI entry";
      uses TCAM-VMR-ENTRY-INT;
    }
    container app-id-pbr {
      description
        "app PBR entry";
      uses TCAM-VMR-ENTRY-INT;
    }
    container application-edpl-entry {
      description
        "app EDPL entry";
      uses TCAM-VMR-ENTRY-INT;
    }
    leaf max-entries {
      type uint32;
      description
        "Max entries";
    }
    leaf free-entries {
      type uint32;
      description
        "free entries";
    }
  }

  grouping TCAM-L2-TABLE-INT-A {
    description
      "tcam l2 table internal";
    leaf partition-id {
      type uint32;
      description
        "PartitionID";
    }
    leaf valid-entries {
      type uint32;
      description
        "Valid Entries";
    }
    leaf free-entries {
      type uint32;
      description
        "Free Entries";
    }
  }

  grouping TCAM-SHOW-SUM-INT {
    description
      "tcam summary internal";
    container tcam-lt-ods2 {
      description
        "TCAM LT ODS 2 summary";
      uses TCAM-ODS-TABLE-INT;
    }
    container tcam-lt-ods8 {
      description
        "TCAM LT_ODS 8 summary";
      uses TCAM-ODS-TABLE-INT;
    }
    list tcam-lt-l2 {
      description
        "Array of TCAM LT L2 partition summaries";
      uses TCAM-L2-TABLE-INT-A;
    }
  }

  grouping TCAM-INFO-SHOW-SUM {
    description
      "tcam summary info";
    container internal-tcam-info {
      description
        "Internal tcam summary info";
      uses TCAM-SHOW-SUM-INT;
    }
    container tcam-info {
      description
        "External tcam summary info";
      uses TCAM-SHOW-SUM;
    }
  }

  grouping PRM-NP-CHN-LOAD-A {
    description
      "NP Channel load counters";
    leaf flow-ctr-counter {
      type uint32;
      description
        "Flow control counters";
    }
    leaf avg-rfd-usage {
      type uint32;
      description
        "Average RFD Usage";
    }
    leaf peak-rfd-usage {
      type uint32;
      description
        "Peak RFD Usage";
    }
    leaf avg-guar-rfd-usage {
      type uint32;
      description
        "Average of garanteed RFD usage";
    }
    leaf peak-guar-rfd-usage {
      type uint32;
      description
        "Peak of garanteed RFD usage";
    }
    leaf interface-name {
      type string;
      description
        "Inerface Name";
    }
  }

  grouping PRM-NP-CHN-LOAD {
    description
      "Array of NP Channel load counters";
    list np-chn-load {
      description
        "Array of NP Channel load counters";
      uses PRM-NP-CHN-LOAD-A;
    }
  }
}
