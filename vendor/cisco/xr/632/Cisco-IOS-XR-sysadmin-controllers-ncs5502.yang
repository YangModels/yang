module Cisco-IOS-XR-sysadmin-controllers-ncs5502 {
  namespace "http://www.cisco.com/ns/yang/Cisco-IOS-XR-sysadmin-controllers";
  prefix calvados_controllers;

  import Cisco-IOS-XR-sysadmin-fabric-ncs5502 {
    prefix fabric;
  }
  import tailf-common {
    prefix tailf;
  }
  import fit {
    prefix fit;
  }
  import Cisco-IOS-XR-sysadmin-ethsw-esdma-cli-ncs5500 {
    prefix esdma;
  }
  import Cisco-IOS-XR-sysadmin-card-mgr {
    prefix card_mgr;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains a collection of YANG
     definitions for Cisco IOS-XR SysAdmin configuration.
     
     This module defines the top level container for
     all hardware devices managed in Sysadmin.
     
     Copyright(c) 2015-2016 by Cisco Systems, Inc.
     All rights reserved.";

  revision 2017-01-31 {
    description
      "Changed the namespace and module name";
  }
  revision 2015-03-20 {
    description
      "Created initial 'controller' implementation for Fretta";
  }
  tailf:id "http://cisco.com/panini/calvados/calvados_controllers";

  container set {
    tailf:cli-suppress-show-path;
    container controller {
      uses fit:fit-grp;
    }
  }
  container controller {
    tailf:info "Access to hardware controller data";
    tailf:cli-incomplete-show-path;
    uses fabric:fabric;
    container switch {
      tailf:info "Control plane Ethernet switch data";
      uses esdma:switch;
    }
    uses fabric:fabric_action_cmds;
    uses card_mgr:card_mgr-group;
  }
}
