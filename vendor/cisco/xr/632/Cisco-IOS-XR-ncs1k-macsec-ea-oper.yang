module Cisco-IOS-XR-ncs1k-macsec-ea-oper {
  namespace "http://cisco.com/ns/yang/Cisco-IOS-XR-ncs1k-macsec-ea-oper";
  prefix ncs1k-macsec-ea-oper;

  import Cisco-IOS-XR-types {
    prefix xr;
  }
  include Cisco-IOS-XR-ncs1k-macsec-ea-oper-sub1 {
    revision-date 2015-11-09;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ncs1k-macsec-ea package operational data.
     
     This module contains definitions
     for the following management objects:
       ncs1k-macsec-oper: Macsec data
     
     Copyright (c) 2013-2017 by Cisco Systems, Inc.
     All rights reserved.";

  revision 2015-11-09 {
    description
      "IOS XR 6.0 revision.";
  }

  container ncs1k-macsec-oper {
    config false;
    description
      "Macsec data";
    container ncs1k-macsec-ctrlr-names {
      description
        "All Macsec operational data";
      list ncs1k-macsec-ctrlr-name {
        key "name";
        description
          "Interface name";
        container ncs1k-status-info {
          description
            "controller data";
          uses NCS1K-MACSEC-IF-STATUS;
        }
        leaf name {
          type xr:Interface-name;
          description
            "Port name";
        }
      }
    }
  }
}
