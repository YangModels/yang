module Cisco-IOS-XR-ofa-qosea-stuck-voq-oper {
  namespace "http://cisco.com/ns/yang/Cisco-IOS-XR-ofa-qosea-stuck-voq-oper";
  prefix ofa-qosea-stuck-voq-oper;

  import Cisco-IOS-XR-types {
    prefix xr;
  }
  import cisco-semver {
    prefix semver;
  }
  include Cisco-IOS-XR-ofa-qosea-stuck-voq-oper-sub1 {
    revision-date 2025-01-02;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ofa-qosea-stuck-voq package operational data.
     
     This module contains definitions
     for the following management objects:
       stuck-voq: Stuck VOQ operational data
     
     Copyright (c) 2013-2025 by Cisco Systems, Inc.
     All rights reserved.";

  revision 2025-01-02 {
    description
      "Initial version for Stuck VOQ operational data";
    semver:module-version "1.0.0";
  }
  revision 2019-04-05 {
    description
      "Establish semantic version baseline.";
  }
  revision 2015-11-09 {
    description
      "IOS XR 6.0 revision.";
  }

  typedef Max-stuck-voqs {
    type uint32 {
      range "0..1024";
    }
    description
      "Max stuck voqs";
  }

  container stuck-voq {
    config false;
    description
      "Stuck VOQ operational data";
    container nodes {
      description
        "Table of nodes";
      list node {
        key "node-name";
        description
          "Information about a particular node";
        container isolation-detail-infos {
          description
            "Container for detailed stuck VOQ isolation
             information";
          list isolation-detail-info {
            key "index";
            description
              "Detailed stuck VOQ isolation information";
            leaf index {
              type Max-stuck-voqs;
              description
                "Stuck VOQ index";
            }
            uses STUCK-VOQ-INFO-BG;
          }
        }
        container status-infos {
          description
            "Container for stuck VOQ status information";
          list status-info {
            key "index";
            description
              "Stuck VOQ detection status information";
            leaf index {
              type Max-stuck-voqs;
              description
                "Stuck VOQ index";
            }
            uses STUCK-VOQ-INFO-BG;
          }
        }
        container isolation-infos {
          description
            "Container for stuck VOQ isolation information";
          list isolation-info {
            key "index";
            description
              "Stuck VOQ isolation information";
            leaf index {
              type Max-stuck-voqs;
              description
                "Stuck VOQ index";
            }
            uses STUCK-VOQ-INFO-BG;
          }
        }
        leaf node-name {
          type xr:Node-id;
          description
            "Node name";
        }
      }
    }
  }
}
