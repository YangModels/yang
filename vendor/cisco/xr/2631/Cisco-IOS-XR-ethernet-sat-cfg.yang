module Cisco-IOS-XR-ethernet-sat-cfg {
  namespace "http://cisco.com/ns/yang/Cisco-IOS-XR-ethernet-sat-cfg";
  prefix ethernet-sat-cfg;

  import Cisco-IOS-XR-types {
    prefix xr;
  }
  import cisco-semver {
    prefix semver;
  }
  import Cisco-IOS-XR-ethernet-sat-datatypes {
    prefix dt1;
  }
  import Cisco-IOS-XR-ifmgr-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ethernet-sat package configuration.
     
     This module contains definitions
     for the following management objects:
       service-activation-test: Service Activation Testing global
         configuration
     
     This YANG module augments the
       Cisco-IOS-XR-ifmgr-cfg
     module with configuration data.
     
     Copyright (c) 2013-2024 by Cisco Systems, Inc.
     All rights reserved.";

  revision 2024-03-08 {
    description
      "Fix microsecond bin widths union";
    semver:module-version "4.0.0";
  }
  revision 2021-09-10 {
    description
      "Fix frame delay range decimal handling and increase to four decimal places
       2021-03-29
           Add support for reporting frame delay statistics";
    semver:module-version "3.0.0";
  }
  revision 2020-04-15 {
    description
      "Fixed must conditions bug.";
    semver:module-version "2.0.0";
  }
  revision 2019-04-05 {
    description
      "Establish semantic version baseline.";
    semver:module-version "1.0.0";
  }
  revision 2015-11-09 {
    description
      "IOS XR 6.0 revision.";
  }

  augment "/a1:interface-configurations/a1:interface-configuration" {
    description
      "This augment extends the configuration data of
       'Cisco-IOS-XR-ifmgr-cfg'";
    container service-activation-test {
      description
        "Service Activation Testing interface
         configuration";
      leaf permit {
        type dt1:Sat-permit;
        description
          "Set SAT permission on the interface";
      }
    }
  }
  container service-activation-test {
    description
      "Service Activation Testing global configuration";
    container profiles {
      description
        "Table for profile configuration";
      list profile {
        key "profile-name";
        description
          "Profile configuration";
        container frame-delay {
          description
            "Set the frame delay reporting config";
          leaf bins {
            type uint32 {
              range "2..100";
            }
            must "../width or (../width and ../range-percentile) or (../width and ../range-percentile-millionths) or (../width and ../minimum-delay) or (../width and ../minimum-delay and ../range-percentile) or (../width and ../minimum-delay and ../range-percentile-millionths) or (../width and ../microseconds) or (../width and ../microseconds and ../range-percentile) or (../width and ../microseconds and ../range-percentile-millionths) or (../width and ../minimum-delay and ../microseconds) or (../width and ../minimum-delay and ../range-percentile and ../microseconds) or (../width and ../minimum-delay and ../range-percentile-millionths and ../microseconds)";
            description
              "Number of delay aggregation bins";
          }
          leaf width {
            type uint32 {
              range "1..10000000";
            }
            units "millisecond";
            must "../bins or (../bins and ../range-percentile) or (../bins and ../range-percentile-millionths) or (../bins and ../minimum-delay) or (../bins and ../minimum-delay and ../range-percentile) or (../bins and ../minimum-delay and ../range-percentile-millionths) or (../bins and ../microseconds) or (../bins and ../microseconds and ../range-percentile) or (../bins and ../microseconds and ../range-percentile-millionths) or (../bins and ../minimum-delay and ../microseconds) or (../bins and ../minimum-delay and ../range-percentile and ../microseconds) or (../bins and ../minimum-delay and ../range-percentile-millionths and ../microseconds)";
            description
              "Width of each delay aggregation bin in
               milliseconds (or microseconds if Microseconds
               is True";
          }
          leaf range-percentile {
            type uint32 {
              range "0..99";
            }
            units "percentage";
            must "../bins and ../width and not(../range-percentile-millionths)";
            description
              "Frame delay range percentile as an integer";
          }
          leaf range-percentile-millionths {
            type uint32 {
              range "0..999999";
            }
            units "percentage";
            must "../bins and ../width and not(../range-percentile)";
            description
              "PFrame delay range percentile in parts per
               million";
          }
          leaf microseconds {
            type boolean;
            must "../bins and ../width";
            description
              "Interpret the bin width in microseconds if
               true";
          }
          leaf minimum-delay {
            type uint32 {
              range "1..10000000";
            }
            units "millisecond";
            must "../bins and ../width";
            description
              "The width of the first aggregation bin in
               milliseconds (or microseconds if Microseconds
               is True";
          }
        }
        container ether-type {
          description
            "Set the ethertype configuration";
          leaf protocol {
            type dt1:Sat-l2cp-ether;
            description
              "Enum indicating which Layer 2 Control
               Protocol ethertype should be used";
          }
          leaf ethertype-hex-value {
            type uint32 {
              range "1536..65535";
            }
            description
              "The user-specified hex value for the
               ethertype";
          }
          leaf subtype-hex-value {
            type uint32 {
              range "0..65535";
            }
            description
              "The user-specified hex value for the subtype";
          }
        }
        container color-aware {
          description
            "Set the SAT color aware config";
          leaf cir-value {
            type uint32 {
              range "1..4294967295";
            }
            must "(../cir-units and ../set-dei) or (../cir-units and ../eir-cos) or (../cir-units and ../set-dei and ../eir-cos)";
            description
              "CIR value";
          }
          leaf cir-units {
            type dt1:Sat-inf-rate-units;
            must "(../cir-value and ../set-dei) or (../cir-value and ../eir-cos) or (../cir-value and ../set-dei and ../eir-cos)";
            description
              "CIR units";
          }
          leaf set-dei {
            type boolean;
            must "../cir-value and ../cir-units";
            description
              "Set DEI in EIR packets";
          }
          leaf eir-cos {
            type uint32 {
              range "0..7";
            }
            must "../cir-value and ../cir-units";
            description
              "CoS value in EIR packets";
          }
        }
        container cos {
          presence "Indicates a cos node is configured.";
          description
            "Set the SAT CoS config";
          leaf outer-cos {
            type uint32 {
              range "0..7";
            }
            mandatory true;
            description
              "Outer CoS value";
          }
          leaf inner-cos {
            type uint32 {
              range "0..7";
            }
            description
              "Inner CoS value";
          }
        }
        container duration {
          presence "Indicates a duration node is configured.";
          description
            "Set the SAT duration config";
          leaf value {
            type uint32 {
              range "1..1440";
            }
            mandatory true;
            description
              "Duration value";
          }
          leaf units {
            type dt1:Sat-duration-units;
            mandatory true;
            description
              "Duration units";
          }
          leaf per-step {
            type empty;
            description
              "Per-step flag";
          }
        }
        container information-rate {
          description
            "Set the SAT information rate config";
          leaf fixed-value {
            type uint32 {
              range "1..4294967295";
            }
            must "../units and not(../minimum or ../step or ../maximum or ../bs or ../bs-units or ../ir)";
            description
              "Fixed information rate value";
          }
          leaf minimum {
            type uint32 {
              range "1..4294967295";
            }
            must "../step and ../maximum and ../units and not(../fixed-value or ../bs or ../bs-units or ../ir)";
            description
              "Minimum information rate";
          }
          leaf step {
            type uint32 {
              range "1..4294967295";
            }
            must "../minimum and ../maximum and ../units and not(../fixed-value or ../bs or ../bs-units or ../ir)";
            description
              "Information rate step";
          }
          leaf maximum {
            type uint32 {
              range "1..4294967295";
            }
            must "../minimum and ../step and ../units and not(../fixed-value or ../bs or ../bs-units or ../ir)";
            description
              "Maximum information rate";
          }
          leaf units {
            type dt1:Sat-inf-rate-units;
            must "../fixed-value or (../minimum and ../step and ../maximum) or (../bs and ../bs-units and ../ir)";
            description
              "Information rate units";
          }
          leaf bs {
            type uint32 {
              range "1..1024";
            }
            must "../bs-units and ../ir and ../units and not(../fixed-value or ../minimum or ../step or ../maximum)";
            description
              "Burst Size";
          }
          leaf bs-units {
            type dt1:Sat-cbs-unites;
            must "../bs and ../ir and ../units and not(../fixed-value or ../minimum or ../step or ../maximum)";
            description
              "Units for the BS";
          }
          leaf ir {
            type uint32 {
              range "1..4294967295";
            }
            must "../bs and ../bs-units and ../units and not(../fixed-value or ../minimum or ../step or ../maximum)";
            description
              "Fixed information rate value";
          }
        }
        container packet-size {
          description
            "Set the SAT packet size config";
          leaf emix {
            type empty;
            must "not(../size)";
            description
              "Use EMIX profile flag";
          }
          leaf sequence {
            type string;
            must "../emix and not(../size)";
            description
              "EMIX Sequence";
          }
          leaf user-defined-frame-size {
            type uint32 {
              range "64..10236";
            }
            must "../emix and ../sequence and not(../size)";
            description
              "User Defined Frame Size";
          }
          leaf size {
            type uint32 {
              range "1..10236";
            }
            units "byte";
            must "not(../emix or ../sequence or ../user-defined-frame-size)";
            description
              "Packet size in bytes";
          }
          leaf pseudo-random {
            type empty;
            must "../emix or ../size and not(../hex-pattern)";
            description
              "Use pseudo-random data for packet contents";
          }
          leaf hex-pattern {
            type uint32 {
              range "0..255";
            }
            must "../emix or ../size and not(../pseudo-random)";
            description
              "Hex pattern used as packet contents";
          }
        }
        leaf measurement {
          type dt1:Measurement-option;
          description
            "Set the measurement options configuration";
        }
        leaf enable {
          type empty;
          description
            "Enable the profile";
        }
        leaf oam-level {
          type uint32 {
            range "0..7";
          }
          description
            "Set the SAT OAM level config";
        }
        leaf description {
          type string {
            length "1..511";
          }
          description
            "Set the SAT description config";
        }
        leaf packet-format {
          type dt1:Packet-format;
          description
            "Send LBMs instead of SAT packets";
        }
        leaf mode {
          type dt1:Sat-mode;
          description
            "Set the SAT mode config";
        }
        leaf profile-name {
          type xr:Cisco-ios-xr-string {
            length "1..511";
          }
          description
            "Profile";
        }
      }
    }
  }
}
