module Cisco-IOS-XR-alarmgr-server-oper-deviations {
  namespace "http://cisco.com/ns/yang/Cisco-IOS-XR-alarmgr-server-oper-deviations";
  prefix alarmgr-server-oper-dev;

  import Cisco-IOS-XR-alarmgr-server-oper {
    prefix am-server-oper;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a set of deviations of container rack
     for spirit platform on Ciso-IOS-XR device.
     
     Copyright (c) 2017, 2019-2020 by Cisco Systems, Inc.
     All rights reserved.";

  revision 2020-05-29 {
    description
      "Initial revision applicable to IOS-XR 6.0 and older releases";
    reference "RFC RFC 8407: 4.8";
  }

  deviation "/am-server-oper:alarms/am-server-oper:detail/am-server-oper:detail-rack" {
    deviate not-supported;
  }
  deviation "/am-server-oper:alarms/am-server-oper:brief/am-server-oper:brief-rack" {
    deviate not-supported;
  }
}
