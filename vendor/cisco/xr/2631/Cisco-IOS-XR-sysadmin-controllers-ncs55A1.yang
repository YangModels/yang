module Cisco-IOS-XR-sysadmin-controllers-ncs55A1 {
  namespace "http://www.cisco.com/ns/yang/Cisco-IOS-XR-sysadmin-controllers-NCS55A1";
  prefix calvados_controllers;

  import Cisco-IOS-XR-sysadmin-fabric-ncs5502 {
    prefix fabric;
  }
  import fit {
    prefix fit;
  }
  import Cisco-IOS-XR-sysadmin-card-mgr {
    prefix card_mgr;
  }
  import cisco-semver {
    prefix semver;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains a collection of YANG
     definitions for Cisco IOS-XR SysAdmin configuration.
     
     This module defines the top level container for
     all hardware devices managed in Sysadmin.
     
     Copyright (c) 2015-2020 by Cisco Systems, Inc.
     All rights reserved.";

  revision 2019-04-15 {
    description
      "Establish semantic version baseline.";
    semver:module-version "1.0.0";
  }
  revision 2017-10-11 {
    description
      "Changed the namespace to unique namespace per unique model";
  }
  revision 2015-03-20 {
    description
      "Created initial 'controller' implementation for Fretta";
  }

  container set {
    container controller {
      uses fit:fit-grp;
    }
  }
  container controller {
    uses fabric:fabric;
    uses fabric:fabric_action_cmds;
    uses card_mgr:card_mgr-group;
  }
}
