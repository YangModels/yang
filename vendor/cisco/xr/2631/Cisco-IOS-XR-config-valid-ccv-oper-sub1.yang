submodule Cisco-IOS-XR-config-valid-ccv-oper-sub1 {
  belongs-to Cisco-IOS-XR-config-valid-ccv-oper {
    prefix Cisco-IOS-XR-config-valid-ccv-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR config-valid-ccv package operational data.
     
     Copyright (c) 2013-2026 by Cisco Systems, Inc.
     All rights reserved.";

  revision 2026-07-02 {
    description
      "Remove deprecated nodes specific to commit check.";
    semver:module-version "3.0.0";
  }
  revision 2021-06-16 {
    description
      "Deprecate nodes specific to commit check.";
    semver:module-version "2.1.0";
  }
  revision 2020-09-14 {
    description
      "Added Config Scripts operational data support.";
    semver:module-version "2.0.0";
  }
  revision 2019-04-05 {
    description
      "Establish semantic version baseline.";
    semver:module-version "1.0.1";
  }
  revision 2015-11-09 {
    description
      "IOS XR 6.0 revision.";
  }

  grouping CCV-SCRIPT-EXCEPTION {
    description
      "Script exception";
    leaf error-message {
      type string;
      description
        "The error message for the exception";
    }
    leaf file-name {
      type string;
      description
        "The name of the file that the exception was
         raised from";
    }
    leaf line {
      type uint32;
      description
        "The line number on which the exception occurred";
    }
    leaf backtrace {
      type string;
      description
        "The full backtrace for the exception";
    }
  }

  grouping CCV-SCRIPT-EXECUTION-INFO-ITEM-BAG {
    description
      "Script Execution Information";
    container exception-details {
      description
        "Details of the first exception that was raised,
         if any";
      uses CCV-SCRIPT-EXCEPTION;
    }
    leaf currently-configured {
      type boolean;
      description
        "TRUE if currently in running configuration, else
         FALSE";
    }
    leaf call-count {
      type uint32;
      description
        "The number of times called during execution";
    }
    leaf duration-milliseconds {
      type uint32;
      units "millisecond";
      description
        "The total execution time, in milliseconds";
    }
    leaf validation-errors {
      type uint32;
      description
        "The number of error-level validation failures
         raised";
    }
    leaf validation-warnings {
      type uint32;
      description
        "The number of warning-level validation failures
         raised";
    }
    leaf modifications {
      type uint32;
      description
        "The number of configuration modifications made";
    }
    leaf pending-modifications {
      type uint32;
      description
        "The number of configuration modifications
         pending";
    }
  }
}
