module Cisco-IOS-XR-portmode-cfg {
  namespace "http://cisco.com/ns/yang/Cisco-IOS-XR-portmode-cfg";
  prefix portmode-cfg;

  import cisco-semver {
    prefix semver;
  }
  import Cisco-IOS-XR-ifmgr-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR portmode package configuration.
     
     This YANG module augments the
       Cisco-IOS-XR-ifmgr-cfg
     module with configuration data.
     
     Copyright (c) 2013-2021 by Cisco Systems, Inc.
     All rights reserved.";

  revision 2021-02-04 {
    description
      "New rate OTU2, OTU2E, OTU4, FC1, FC2, FC4, FC8, FC16 and FC32 are added to Port-mode-rate type.";
    semver:module-version "2.0.0";
  }
  revision 2020-04-03 {
    description
      "Portmode Config and Datatype Yang model added.
       2020-04-03
          CPRI role/datarate-list parameters added.";
    semver:module-version "1.1.0";
  }
  revision 2019-07-05 {
    description
      "Portmode Config and Datatype Yang model added.";
    semver:module-version "1.0.0";
  }
  revision 2019-04-05 {
    description
      "Establish semantic version baseline.";
  }
  revision 2015-11-09 {
    description
      "IOS XR 6.0 revision.";
  }

  typedef Port-mode-mapping {
    type enumeration {
      enum "none" {
        value 0;
        description
          "No mapping";
      }
      enum "gfp-f" {
        value 1;
        description
          "GFP_F mapping";
      }
      enum "amp" {
        value 2;
        description
          "AMP mapping";
      }
      enum "bmp" {
        value 3;
        description
          "BMP mapping";
      }
      enum "gmp" {
        value 4;
        description
          "GMP mapping";
      }
      enum "wis" {
        value 5;
        description
          "WIS mapping";
      }
      enum "gfp-f-ext" {
        value 6;
        description
          "GFP_F_EXT mapping";
      }
    }
    description
      "Port mode mapping";
  }

  typedef Cpri-role {
    type enumeration {
      enum "slave" {
        value 0;
        description
          "Slave";
      }
      enum "master" {
        value 1;
        description
          "Master";
      }
    }
    description
      "Cpri role";
  }

  typedef Port-mode-rate {
    type enumeration {
      enum "none" {
        value 0;
        description
          "No Rate";
      }
      enum "oc3" {
        value 1;
        description
          "OC3 Rate";
      }
      enum "oc12" {
        value 2;
        description
          "OC12 Rate";
      }
      enum "oc48" {
        value 3;
        description
          "OC48 Rate";
      }
      enum "oc192" {
        value 4;
        description
          "OC192 Rate";
      }
      enum "oc768" {
        value 5;
        description
          "OC768 Rate";
      }
      enum "stm1" {
        value 6;
        description
          "STM1 Rate";
      }
      enum "stm4" {
        value 7;
        description
          "STM4 Rate";
      }
      enum "stm16" {
        value 8;
        description
          "STM16 Rate";
      }
      enum "stm64" {
        value 9;
        description
          "STM64 Rate";
      }
      enum "stm256" {
        value 10;
        description
          "STM256 Rate";
      }
      enum "100ge" {
        value 11;
        description
          "100GE Rate";
      }
      enum "10ge" {
        value 12;
        description
          "10GE Rate";
      }
      enum "40ge" {
        value 13;
        description
          "40GE Rate";
      }
      enum "1ge" {
        value 14;
        description
          "1GE Rate";
      }
      enum "25ge" {
        value 15;
        description
          "25GE Rate";
      }
      enum "otu2" {
        value 16;
        description
          "OTU2 rate";
      }
      enum "otu2e" {
        value 17;
        description
          "OTU2E rate";
      }
      enum "otu4" {
        value 18;
        description
          "OTU4 rate";
      }
      enum "fc1" {
        value 19;
        description
          "FC1 rate";
      }
      enum "fc2" {
        value 20;
        description
          "FC2 rate";
      }
      enum "fc4" {
        value 21;
        description
          "FC4 rate";
      }
      enum "fc8" {
        value 22;
        description
          "FC8 rate";
      }
      enum "fc16" {
        value 23;
        description
          "FC16 rate";
      }
      enum "fc32" {
        value 24;
        description
          "FC32 rate";
      }
    }
    description
      "Port mode rate";
  }

  typedef Port-mode-types {
    type enumeration {
      enum "invalid" {
        value 0;
        description
          "Invalid portmode";
      }
      enum "ethernet" {
        value 1;
        description
          "Ethernet portmode type";
      }
      enum "sonet" {
        value 2;
        description
          "Sonet portmode type";
      }
      enum "fc" {
        value 3;
        description
          "FC portmode type";
      }
      enum "otn" {
        value 4;
        description
          "OTN portmode type";
      }
      enum "sdh" {
        value 5;
        description
          "SDH portmode type";
      }
      enum "cpri" {
        value 7;
        description
          "CPRI portmode type";
      }
    }
    description
      "Port mode types";
  }

  typedef Cpri-data-rate {
    type enumeration {
      enum "2457" {
        value 3;
        description
          "CPRI option 3 - 2457 Mbps";
      }
      enum "3072" {
        value 4;
        description
          "CPRI option 4 - 3072 Mbps";
      }
      enum "4915" {
        value 5;
        description
          "CPRI option 5 - 4915 Mbps";
      }
      enum "6144" {
        value 6;
        description
          "CPRI option 6 - 6144 Mbps";
      }
      enum "9830" {
        value 7;
        description
          "CPRI option 7 - 9830 Mbps";
      }
      enum "10137" {
        value 9;
        description
          "CPRI option 8 - 10137 Mbps";
      }
    }
    description
      "Cpri data rate";
  }

  typedef Port-mode-framing {
    type enumeration {
      enum "none" {
        value 0;
        description
          "No framing";
      }
      enum "opu0" {
        value 1;
        description
          "OPU0 framing";
      }
      enum "opu1" {
        value 2;
        description
          "OPU1 framing";
      }
      enum "opu1e" {
        value 3;
        description
          "OPU1e framing";
      }
      enum "opu1f" {
        value 4;
        description
          "OPU1f framing";
      }
      enum "opu2" {
        value 5;
        description
          "OPU2 framing";
      }
      enum "opu2e" {
        value 6;
        description
          "OPU2e framing";
      }
      enum "opu2f" {
        value 7;
        description
          "OPU2f framing";
      }
      enum "opu3" {
        value 8;
        description
          "OPU3 framing";
      }
      enum "opu3e1" {
        value 9;
        description
          "OPU3e1 framing";
      }
      enum "opu3e2" {
        value 10;
        description
          "OPU3e2 framing";
      }
      enum "opu4" {
        value 11;
        description
          "OPU4 framing";
      }
      enum "opu-flex" {
        value 12;
        description
          "OPUFlex framing";
      }
      enum "opuc2" {
        value 13;
        description
          "OPUC2 framing";
      }
      enum "opuc4" {
        value 14;
        description
          "OPUC4 framing";
      }
      enum "packet" {
        value 15;
        description
          "Packet framing";
      }
      enum "cem-packetize" {
        value 17;
        description
          "CEM packetization";
      }
    }
    description
      "Port mode framing";
  }

  augment "/a1:interface-configurations/a1:interface-configuration" {
    description
      "This augment extends the configuration data of
       'Cisco-IOS-XR-ifmgr-cfg'";
    container port-mode {
      description
        "Portmode configuration";
      container lane-numbers {
        description
          "Breakout Configuration";
        list lane-number {
          key "lane-no";
          description
            "Lane number for breakout configuration";
          leaf lane-no {
            type uint32 {
              range "1..10";
            }
            description
              "LANE NO";
          }
          leaf rate {
            type Port-mode-rate;
            description
              "PortMode rate";
          }
          leaf mapping {
            type Port-mode-mapping;
            description
              "PortMode mapping types";
          }
          leaf framing {
            type Port-mode-framing;
            description
              "PortMode framing types";
          }
          leaf type {
            type Port-mode-types;
            description
              "PortMode types";
          }
        }
      }
      container info {
        description
          "PortMode configuration";
        leaf rate {
          type Port-mode-rate;
          description
            "PortMode rate";
        }
        leaf mapping {
          type Port-mode-mapping;
          description
            "PortMode mapping types";
        }
        leaf framing {
          type Port-mode-framing;
          description
            "PortMode framing types";
        }
        leaf type {
          type Port-mode-types;
          description
            "PortMode types";
        }
      }
      container cpri-info {
        presence "Indicates a cpri-info node is configured.";
        description
          "CPRI PortMode configuration";
        leaf type {
          type Port-mode-types;
          description
            "PortMode types";
        }
        leaf cpri-role {
          type Cpri-role;
          mandatory true;
          description
            "CPRI Role";
        }
        leaf-list cpri-rate {
          type Cpri-data-rate;
          max-elements "4";
          description
            "Array of CPRI line rates";
        }
      }
    }
  }
}
