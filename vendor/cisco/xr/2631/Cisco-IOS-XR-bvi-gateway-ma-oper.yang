module Cisco-IOS-XR-bvi-gateway-ma-oper {
  namespace "http://cisco.com/ns/yang/Cisco-IOS-XR-bvi-gateway-ma-oper";
  prefix bvi-gateway-ma-oper;

  import Cisco-IOS-XR-types {
    prefix xr;
  }
  import cisco-semver {
    prefix semver;
  }
  include Cisco-IOS-XR-bvi-gateway-ma-oper-sub1 {
    revision-date 2026-05-08;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR bvi-gateway-ma package operational data.
     
     This module contains definitions
     for the following management objects:
       bvi-gateway-ma: BVIGateway MA operational data
     
     Copyright (c) 2013-2026 by Cisco Systems, Inc.
     All rights reserved.";

  revision 2026-05-08 {
    description
      "Added: leaf mtu, leaf state";
    semver:module-version "1.0.0";
  }
  revision 2026-05-07 {
    description
      "Added: leaf mapped-l3ac-count, list mapped-l3ac";
  }
  revision 2026-04-13 {
    description
      "Initial revision.";
  }
  revision 2019-04-05 {
    description
      "Establish semantic version baseline.";
  }
  revision 2015-11-09 {
    description
      "IOS XR 6.0 revision.";
  }

  container bvi-gateway-ma {
    config false;
    description
      "BVIGateway MA operational data";
    container idbs {
      description
        "BVIGateway MA interface database table";
      list idb {
        key "if-handle";
        description
          "BVIGateway MA interface database entry";
        leaf if-handle {
          type xr:Interface-name;
          description
            "BVI-Gateway interface handle";
        }
        uses BVI-GATEWAY-INFO;
      }
    }
  }
}
