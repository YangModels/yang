submodule Cisco-IOS-XR-procthreadname-oper-sub1 {
  belongs-to Cisco-IOS-XR-procthreadname-oper {
    prefix Cisco-IOS-XR-procthreadname-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR procthreadname package operational data.
     
     Copyright (c) 2013-2022 by Cisco Systems, Inc.
     All rights reserved.";

  revision 2022-07-07 {
    description
      "Removed container thread-name.";
    semver:module-version "2.0.0";
  }
  revision 2019-05-28 {
    description
      "Initial version.";
    semver:module-version "1.0.0";
  }
  revision 2019-04-05 {
    description
      "Establish semantic version baseline.";
  }
  revision 2015-11-09 {
    description
      "IOS XR 6.0 revision.";
  }

  grouping PROCESSESTHREAD-ENTRY {
    description
      " Per Thread Information";
    leaf name {
      type string;
      description
        "Thread name";
    }
    leaf state {
      type string;
      description
        "Thread State";
    }
    leaf stack {
      type string;
      description
        "Stack";
    }
    leaf pri {
      type uint32;
      description
        "Priority";
    }
    leaf rtpri {
      type uint32;
      description
        "Rt pri";
    }
    leaf jid {
      type uint32;
      description
        "Job ID";
    }
    leaf tid {
      type uint32;
      description
        "Thread ID";
    }
  }

  grouping THREADLIST {
    description
      " Per node thread list";
    list thread {
      description
        "Thread list";
      uses PROCESSESTHREAD-ENTRY;
    }
  }
}
