submodule Cisco-IOS-XR-healthcheck-oper-sub1 {
  belongs-to Cisco-IOS-XR-healthcheck-oper {
    prefix Cisco-IOS-XR-healthcheck-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR healthcheck package operational data.
     
     Copyright (c) 2013-2026 by Cisco Systems, Inc.
     All rights reserved.";

  revision 2026-07-10 {
    description
      "Added deprecation message for Healthcheck packet-drop and asic-reset use-cases
       2026-04-15
         created a new oper yang for NCS1004 and retained support for performing a get operation on individual HC metrics
       2026-03-24
         Made the drop-tolerance field specific to ASIC reset and tolerance-levels low, medium and high specific to the packet-drop use case
       2026-03-11
         Removed the support for report metric and status metric
       2026-01-21
         Deprecated Healthcheck legacy metrics";
    semver:module-version "2.0.0";
  }
  revision 2025-09-30 {
    description
      "Updated version in which legacy metrics are getting deprecated
       2025-04-28
          Added deprecation message for Healthcheck legacy metrics in oper yang
       2024-04-04
          Added history under packet-drop usecase with node-name and npu id
       2024-03-27
          Timestamp removed from ASIC reset and Packet drop usecase summary
       2023-10-10
          Updated usecase status to have tolerance low, medium and high
       2022-04-07
          Updated Install Metric
       2021-10-19
          Updated Custom Metric
       2021-07-22
          ASIC reset and packet drops use case updated
       2021-05-25
          ASIC reset and packet drops usecases added";
    semver:module-version "1.1.0";
  }
  revision 2020-09-18 {
    description
      "Fabric health metric updated.";
    semver:module-version "1.0.0";
  }
  revision 2019-04-05 {
    description
      "Establish semantic version baseline.";
  }
  revision 2015-11-09 {
    description
      "IOS XR 6.0 revision.";
  }

  typedef Stage-status {
    type enumeration {
      enum "running" {
        value 0;
        description
          "NOSI stage is in running state";
      }
      enum "stopped" {
        value 1;
        description
          "NOSI stage is in stopped state";
      }
      enum "exited" {
        value 2;
        description
          "NOSI stage is in exited state";
      }
      enum "fatal" {
        value 3;
        description
          "NOSI stage is in fatal state";
      }
      enum "error" {
        value 4;
        description
          "NOSI stage is in error state";
      }
      enum "unknown" {
        value 5;
        description
          "NOSI stage is in unknown state";
      }
      enum "not-running" {
        value 6;
        description
          "NOSI stage is in not running state";
      }
    }
    description
      "Stage status";
  }

  typedef Config-state {
    type enumeration {
      enum "enabled" {
        value 0;
        description
          "Use case configuration state enabled";
      }
      enum "disabled" {
        value 1;
        description
          "Use case configuration state disabled";
      }
      enum "unknown" {
        value 2;
        description
          "Use case configuration state unknown";
      }
    }
    description
      "Config state";
  }

  typedef Nosi-state {
    type enumeration {
      enum "normal" {
        value 1;
        description
          "Use case health state normal";
      }
      enum "warning" {
        value 2;
        description
          "Use case health state warning";
      }
      enum "error" {
        value 3;
        description
          "Health check service state error";
      }
    }
    description
      "Nosi state";
  }

  grouping HCMGR-STATUS-USECASE-DATA-LEGACY {
    description
      "Health check status information of a use case";
    leaf use-case-name {
      type string;
      description
        "Use case name associated with its state and
         tolerence";
    }
    leaf state {
      type Config-state;
      description
        "Configuration state of use case";
    }
    leaf drop-tolerance {
      when "../use-case-name = 'asic-reset'" {
        description
          "Use case is asic-reset";
      }
      type uint8;
      description
        "Drop tolerance as a percentage of incoming
         packets/bytes";
    }
    leaf tolerance-level-low {
      when "../use-case-name = 'packet-drop'" {
        description
          "Use case is packet-drop";
      }
      type uint32;
      description
        "Tolerance for low classified Traps";
    }
    leaf tolerance-level-medium {
      when "../use-case-name = 'packet-drop'" {
        description
          "Use case is packet-drop";
      }
      type uint32;
      description
        "Tolerance for medium classified Traps";
    }
    leaf tolerance-level-high {
      when "../use-case-name = 'packet-drop'" {
        description
          "Use case is packet-drop";
      }
      type uint32;
      description
        "Tolerance for high classified Traps";
    }
  }

  grouping HCMGR-USE-CASE {
    description
      "Healthcheck use-case description";
    leaf pipeline-state {
      type Stage-status;
      description
        "Running state of NOSI container";
    }
    list use-case {
      description
        "Collection of different use cases";
      uses HCMGR-STATUS-USECASE-DATA-LEGACY;
    }
  }

  grouping HCMGR-INSTALL-CUSTOM-METRIC {
    description
      "Healthcheck install custom metrics";
    leaf metric-name {
      type string;
      description
        "Metric Name";
    }
  }

  grouping HCMGR-STATUS-DATA {
    description
      "Health check status data";
    container use-case-status {
      description
        "Use-case details";
      uses HCMGR-USE-CASE;
    }
    leaf collector-cadence {
      type string;
      description
        "Healthcheck collector cadence";
    }
    leaf service-status {
      type string;
      description
        "Healthcheck service status";
    }
    leaf time-started {
      type string;
      description
        "Healthcheck enabled time";
    }
    leaf time-stopped {
      type string;
      description
        "Healthcheck disabled time";
    }
    leaf reason {
      type string;
      description
        "Healthcheck reason for error";
    }
    list install-custom-metric {
      description
        "Install Custom metrics";
      uses HCMGR-INSTALL-CUSTOM-METRIC;
    }
  }

  grouping HCMGR-STATUS-USECASE-DATA {
    description
      "Health check status information of use case";
    leaf state {
      type Config-state;
      description
        "Configuration state of use case";
    }
    leaf drop-tolerance {
      when "../use-case = 'asic-reset'" {
        description
          "Use case is asic-reset";
      }
      type uint8;
      description
        "Drop tolerance as a percentage of incoming
         packets/bytes";
    }
    leaf tolerance-level-low {
      when "../use-case = 'packet-drop'" {
        description
          "Use case is packet-drop";
      }
      type uint32;
      description
        "Tolerance for low classified Traps";
    }
    leaf tolerance-level-medium {
      when "../use-case = 'packet-drop'" {
        description
          "Use case is packet-drop";
      }
      type uint32;
      description
        "Tolerance for medium classified Traps";
    }
    leaf tolerance-level-high {
      when "../use-case = 'packet-drop'" {
        description
          "Use case is packet-drop";
      }
      type uint32;
      description
        "Tolerance for high classified Traps";
    }
  }

  grouping HCMGR-USE-CASE-REPORT-DATA {
    description
      "Health check use case report data";
    leaf alert {
      type string;
      description
        "Alert message. For display only";
    }
    leaf state {
      type Nosi-state;
      description
        "NOSI state";
    }
  }

  grouping HCMGR-USE-CASE-SUMMARY {
    description
      "Health check use case summary data";
    container use-case-info {
      description
        "Use case report data";
      uses HCMGR-USE-CASE-REPORT-DATA;
    }
    leaf use-case {
      type string;
      description
        "Enabled use case";
    }
  }

  grouping HCMGR-REPORT-METRIC-DATA {
    description
      "Health check report metric data";
    leaf name {
      type string;
      description
        "Metric name";
    }
    leaf service-msg {
      type string;
      description
        "Metric service msg";
    }
    leaf state {
      type string;
      description
        "Metric state";
    }
    leaf reason {
      type string;
      description
        "Metric not healthy reason";
    }
  }

  grouping HCMGR-REPORT-DATA {
    description
      "Healthcheck Report data";
    leaf time-stamp {
      type string;
      description
        "Last updated timestamp for metrics";
    }
    list metric {
      description
        "Metric info";
      uses HCMGR-REPORT-METRIC-DATA;
    }
    list summary {
      description
        "Usecase summary report information";
      uses HCMGR-USE-CASE-SUMMARY;
    }
  }
}
