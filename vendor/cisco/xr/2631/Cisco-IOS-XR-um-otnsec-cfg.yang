module Cisco-IOS-XR-um-otnsec-cfg {
  namespace "http://cisco.com/ns/yang/Cisco-IOS-XR-um-otnsec-cfg";
  prefix um-otnsec-cfg;

  import Cisco-IOS-XR-types {
    prefix xr;
  }
  import ietf-inet-types {
    prefix inet;
  }
  import Cisco-IOS-XR-um-interface-cfg {
    prefix a1;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR otnsec package configuration.
     
     This YANG module augments the
     modules with configuration data.
     
     Copyright (c) 2020-2025 by Cisco Systems, Inc., and/or its affiliates.
     All rights reserved.";

  revision 2022-07-11 {
    description
      "Added missing description statement to nodes";
    semver:module-version "1.1.0";
  }
  revision 2020-12-14 {
    description
      "Initial release";
    semver:module-version "1.0.0";
  }

  grouping CONT-BODY {
    description
      "Grouping for controller";
    container otnsec {
      description
        "Configure otnsec submode";
      leaf policy {
        type xr:Cisco-ios-xr-string {
          length "1..32" {
            description
              "Policy";
          }
        }
        description
          "otnsec policy";
      }
      leaf session-id {
        type uint32 {
          range "1..65535" {
            description
              "session ID";
          }
        }
        description
          "IKEv2 Session ID";
      }
      container source {
        description
          "ikev2 SA source IP";
        leaf ipv4 {
          type inet:ipv4-address-no-zone;
          description
            "";
        }
      }
      container destination {
        description
          "IKEv2 SA destination IP";
        leaf ipv4 {
          type inet:ipv4-address-no-zone;
          description
            "";
        }
      }
      leaf ikev2 {
        type xr:Cisco-ios-xr-string {
          length "1..800" {
            description
              "profile";
          }
        }
        description
          "IKEv2 profile";
      }
    }
  }

  augment "/a1:controllers/a1:controller" {
    description
      "This augment extends active nodes configuration";
    uses CONT-BODY;
  }
  augment "/a1:controllers/a1:controller-preconfigure" {
    description
      "This augment extends preconfigured nodes
       configuration";
    uses CONT-BODY;
  }
  container otnsec {
    description
      "Configure otnsec submode";
    container policies {
      description
        "otnsec policy";
      list policy {
        key "policy-name";
        description
          "otnsec-policy";
        leaf policy-name {
          type xr:Cisco-ios-xr-string {
            length "1..32" {
              description
                "otnsec-policy";
            }
          }
          description
            "otnsec-policy";
        }
        leaf cipher-suite {
          type enumeration {
            enum "AES-GCM-256" {
              value 0;
              description
                "";
            }
          }
          description
            "Encryption/Decryption datapath algorithm";
        }
        leaf security-policy {
          type enumeration {
            enum "must-secure" {
              value 1;
              description
                "Mandatory security";
            }
          }
          description
            "Securing policy";
        }
        leaf sak-rekey-interval {
          type uint32 {
            range "30..1209600" {
              description
                "rekey timer in seconds";
            }
          }
          description
            "Rekey timeout (in seconds)";
        }
      }
    }
  }
}
