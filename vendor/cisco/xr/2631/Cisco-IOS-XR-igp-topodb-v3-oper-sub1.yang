submodule Cisco-IOS-XR-igp-topodb-v3-oper-sub1 {
  belongs-to Cisco-IOS-XR-igp-topodb-v3-oper {
    prefix Cisco-IOS-XR-igp-topodb-v3-oper;
  }

  import ietf-inet-types {
    prefix inet;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR igp-topodb-v3 package operational data.
     
     Copyright (c) 2013-2025 by Cisco Systems, Inc.
     All rights reserved.";

  revision 2025-08-21 {
    description
      "Adding ospfv3 support";
    semver:module-version "1.0.0";
  }
  revision 2019-04-05 {
    description
      "Establish semantic version baseline.";
  }
  revision 2015-11-09 {
    description
      "IOS XR 6.0 revision.";
  }

  grouping OTLIB-V3-SHOW-AREA-SUMMARY {
    description
      "OTLIB Area Summary";
    leaf area-id-string {
      type string {
        length "0..16";
      }
      description
        "Area ID";
    }
    leaf num-nodes {
      type uint16;
      description
        "No. of Nodes";
    }
    leaf is-distribute-linkstate-enabled {
      type boolean;
      description
        "Is Distribute Linkstate Enabled for this area";
    }
  }

  grouping OTLIB-V3-SHOW-INST-SUMMARY {
    description
      "OTLIB V3 Instance Summary";
    leaf vrf-name {
      type string;
      description
        "VRF Name";
    }
    leaf router-id {
      type inet:ipv4-address;
      description
        "Router ID";
    }
    leaf num-areas {
      type uint16;
      description
        "No. of Areas";
    }
    leaf is-distribute-linkstate-enabled {
      type boolean;
      description
        "Is Distribute Linkstate Enabled for this
         instance";
    }
    list area {
      description
        "List of Areas";
      uses OTLIB-V3-SHOW-AREA-SUMMARY;
    }
  }

  grouping OTLIB-V3-SHOW-PREFIX-CONTRIB {
    description
      "OTLIB V3 Prefix contributor";
    leaf algo {
      type uint8;
      description
        "Algo number";
    }
    leaf igp-metric {
      type uint32;
      description
        "Base IGP metric of the prefix by the node";
    }
    leaf fapm-metric {
      type uint32;
      description
        "FAPM metric of the prefix by the node";
    }
    leaf total-metric {
      type uint64;
      description
        "Total metric to reach the prefix";
    }
    leaf contrib-flags {
      type uint32;
      description
        "Prefix contributor flags";
    }
    leaf route-type {
      type uint8;
      description
        "Route Type of this contributor";
    }
    leaf adv-router-id {
      type inet:ipv4-address;
      description
        "Advertising Router ID";
    }
    leaf area-id {
      type uint32;
      description
        "Area ID of the contributor";
    }
  }

  grouping OTLIB-V3-SHOW-PREFIX {
    description
      "OTLIB V3 Prefix";
    leaf prefix-v6-address {
      type inet:ipv6-address;
      description
        "Prefix V6 Address";
    }
    leaf prefix-length {
      type uint8;
      description
        "Prefix Length";
    }
    leaf route-type {
      type uint32;
      description
        "Route Type";
    }
    leaf ext-e-bit {
      type boolean;
      description
        "External E Bit. Valid when route type is
         external";
    }
    leaf forwarding-address {
      type inet:ipv6-address;
      description
        "Forwarding Address applicable only for external
         prefixes";
    }
    leaf external-tag {
      type uint32;
      description
        "Tag applicable only for external prefixes";
    }
    leaf prefix-flags {
      type uint32;
      description
        "Prefix Flags";
    }
    list prefix-contributor {
      description
        "Prefix Contributors";
      uses OTLIB-V3-SHOW-PREFIX-CONTRIB;
    }
  }

  grouping OTLIB-V3-SHOW-LINK-OPTICAL-INFO {
    description
      "OTLIB Link Optical Info";
    leaf optical-tlv-type {
      type uint16;
      description
        "Optical TLV Type";
    }
    leaf optical-tlv-length {
      type uint16;
      description
        "Optical TLV Length";
    }
    leaf ent-num {
      type uint16;
      description
        "enterprise number";
    }
    leaf-list optical-tlv-data {
      type uint8;
      description
        "Optical TLV Data";
    }
  }

  grouping OTLIB-V3-SHOW-LINK-ATTR {
    description
      "OTLIB V3 Link Attrs";
    container optical-info {
      description
        "Optical Info";
      uses OTLIB-V3-SHOW-LINK-OPTICAL-INFO;
    }
    leaf lsid {
      type inet:ipv4-address;
      description
        "LSA ID";
    }
  }

  grouping OTLIB-V3-SHOW-LINK-ID {
    description
      "OTLIB V3 Link ID";
    leaf link-id {
      type inet:ipv4-address;
      description
        "Link ID";
    }
    leaf link-data {
      type inet:ipv4-address;
      description
        "Link Data";
    }
    leaf link-remote-data {
      type inet:ipv4-address;
      description
        "Link Remote Data";
    }
    leaf link-type {
      type uint8;
      description
        "Link Type";
    }
  }

  grouping OTLIB-V3-SHOW-LINK {
    description
      "OTLIB V3 Link";
    container link-id {
      description
        "Link ID";
      uses OTLIB-V3-SHOW-LINK-ID;
    }
    container remote-link-id {
      description
        "Remote Link ID";
      uses OTLIB-V3-SHOW-LINK-ID;
    }
    container link-attrs {
      description
        "Link Attributes";
      uses OTLIB-V3-SHOW-LINK-ATTR;
    }
    leaf link-metric {
      type uint16;
      description
        "Link Metric";
    }
    leaf link-oper-flags {
      type uint16;
      description
        "Link Operational flags";
    }
    leaf is-local-link {
      type boolean;
      description
        "Is the link attached to self router";
    }
    leaf local-interface-id {
      type uint32;
      description
        "Local Interface ID";
    }
    leaf remote-interface-id {
      type uint32;
      description
        "Remote Interface ID";
    }
    leaf is-router-lsa-contrib {
      type boolean;
      description
        "Is Router LSA Contributing";
    }
    leaf is-network-lsa-contrib {
      type boolean;
      description
        "Is Network LSA Contributing";
    }
    leaf is-ext-link-lsa-contrib {
      type boolean;
      description
        "Is Ext Link LSA Contributing";
    }
    leaf is-link-lsa-contrib {
      type boolean;
      description
        "Is Link LSA Contributing";
    }
    leaf is-ext-router-lsa-contrib {
      type boolean;
      description
        "Is Extended Router LSA Contributing";
    }
  }

  grouping OTLIB-V3-SHOW-NODE-ID {
    description
      "OTLIB V3 Node ID";
    leaf adv-router-id {
      type inet:ipv4-address;
      description
        "Advertising Router ID";
    }
    leaf dr-interface-id {
      type uint32;
      description
        "Node DR Interface Identifier";
    }
  }

  grouping OTLIB-V3-SHOW-NODE {
    description
      "OTLIB V3 Node";
    container node-id {
      description
        "Node ID";
      uses OTLIB-V3-SHOW-NODE-ID;
    }
    leaf num-links {
      type uint16;
      description
        "Number of Links";
    }
    leaf num-prefixes {
      type uint32;
      description
        "Number of prefixes";
    }
    leaf is-root-node {
      type boolean;
      description
        "Is root node";
    }
    leaf is-area-border-router {
      type boolean;
      description
        "Node is ABR";
    }
    leaf is-as-border-router {
      type boolean;
      description
        "Node is ASBR";
    }
    leaf node-oper-flags {
      type uint16;
      description
        "Node Operational flags";
    }
    leaf is-router-lsa-contrib {
      type boolean;
      description
        "Is Router LSA Contributing";
    }
    leaf is-network-lsa-contrib {
      type boolean;
      description
        "Is Network LSA Contributing";
    }
    leaf is-router-info-lsa-contrib {
      type boolean;
      description
        "Is Router Info LSA Contributing";
    }
    leaf is-ext-router-lsa-contrib {
      type boolean;
      description
        "Is Extended Router LSA Contributing";
    }
    list link {
      description
        "List of Links";
      uses OTLIB-V3-SHOW-LINK;
    }
    list prefix {
      description
        "List of prefixes";
      uses OTLIB-V3-SHOW-PREFIX;
    }
  }

  grouping OTLIB-V3-SHOW-AREA {
    description
      "OTLIB V3 Area";
    leaf area-id-string {
      type string {
        length "0..16";
      }
      description
        "Area ID string. Valid only if not AS scoped";
    }
    leaf is-as-scoped {
      type boolean;
      description
        "Is the prefixes AS scoped";
    }
    leaf num-nodes {
      type uint16;
      description
        "No. of nodes under area";
    }
    list node {
      description
        "List of Nodes";
      uses OTLIB-V3-SHOW-NODE;
    }
  }

  grouping OTLIB-V3-SHOW-INSTANCE {
    description
      "OTLIB V3 Instance";
    leaf vrf-name {
      type string;
      description
        "VRF Name";
    }
    leaf router-id {
      type inet:ipv4-address;
      description
        "Router ID";
    }
    list area {
      description
        "List of Areas";
      uses OTLIB-V3-SHOW-AREA;
    }
  }
}
