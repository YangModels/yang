submodule Cisco-IOS-XR-crypto-cepki-oper-sub1 {
  belongs-to Cisco-IOS-XR-crypto-cepki-oper {
    prefix Cisco-IOS-XR-crypto-cepki-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR crypto-cepki package operational data.
     
     Copyright (c) 2013-2026 by Cisco Systems, Inc.
     All rights reserved.";

  revision 2026-02-28 {
    description
      "Added telemetry support for x509 and openssh certificate info by implementing bags for the same.";
    semver:module-version "2.0.0";
  }
  revision 2022-07-22 {
    description
      "added multiple rsa authentication keys support.
       2022-04-06
          Added serial number and fingerprint for ca.
       2022-03-20
          OpenSSH certificate support.";
    semver:module-version "1.1.0";
  }
  revision 2019-04-05 {
    description
      "Establish semantic version baseline.";
    semver:module-version "1.0.0";
  }
  revision 2015-11-09 {
    description
      "IOS XR 6.0 revision.";
  }

  grouping OPENSSH-ROUTER-CERTIFICATE {
    description
      "OpenSSH Router Certificate Information";
    leaf principal {
      type string;
      description
        "Openssh certificate principal name";
    }
    leaf pub-key-type {
      type string;
      description
        "Openssh certificate public key type";
    }
    leaf expires-on {
      type uint64;
      description
        "Openssh certificate expiration time";
    }
    leaf comment {
      type string;
      description
        "Comment associated with the Openssh certificate";
    }
    leaf serial {
      type uint64;
      description
        "Openssh Certificate serial number";
    }
    leaf key-id {
      type string;
      description
        "Key label for the Openssh certificate";
    }
    leaf valid-from {
      type uint64;
      description
        "Openssh certificate validity start time";
    }
    leaf openssh-router-certificate-data {
      type string;
      description
        "Openssh Router certificate";
    }
  }

  grouping OPENSSH-TRUSTPOINT {
    description
      "OpenSSH Trustpoint Information";
    container openssh-router-certificate {
      description
        "Router certificate info";
      uses OPENSSH-ROUTER-CERTIFICATE;
    }
    leaf openssh-certificate-authority-certificate {
      type string;
      description
        "Openssh CA certificate";
    }
  }

  grouping CDP-ENTRY {
    description
      "CRL Distribution Point Entry";
    leaf index {
      type uint32;
      description
        "CDP Entry Index";
    }
    leaf cdp-content {
      type string;
      description
        "CRLDistributionPoint Content";
    }
  }

  grouping CRL-DISTRIBUTION-POINT-TABLE {
    description
      "Router Certificates CRLDistributionPoint Table";
    list crl-distribution-point {
      key "index";
      description
        "Certificate CRLDistributionPoint Instance";
      uses CDP-ENTRY;
    }
  }

  grouping CRYPTO-CERTIFICATE {
    description
      "OpenSSH Trustpoint Information";
    container crl-distribution-points {
      description
        "Router Certificates CRLDistributionPoint Table";
      uses CRL-DISTRIBUTION-POINT-TABLE;
    }
    leaf subject {
      type string;
      description
        "Certificate Subject";
    }
    leaf certificate-valid-from {
      type uint64;
      description
        "Certificate Validity Start Time";
    }
    leaf certificate-expires-on {
      type uint64;
      description
        "Certificate Expiration Time";
    }
    leaf serial-num {
      type string;
      description
        "Certificate Serial Number";
    }
    leaf finger-print {
      type string;
      description
        "Certificate SHA1 Fingerprint";
    }
    leaf issuer {
      type string;
      description
        "Certificate Issuer";
    }
    leaf certificate-data {
      type string;
      description
        "PEM-encoded Certificate";
    }
  }

  grouping CRYPTO-TRUSTPOINT {
    description
      "OpenSSH Trustpoint Information";
    container router-certificate {
      description
        "Router Certificate Attributes";
      uses CRYPTO-CERTIFICATE;
    }
    container router-encryption-certificate {
      description
        "Router Encryption Certificate Attributes";
      uses CRYPTO-CERTIFICATE;
    }
    container router-signature-certificate {
      description
        "Router Signature Certificate Attributes";
      uses CRYPTO-CERTIFICATE;
    }
    container certificate-authority-certificate {
      description
        "Certificate Authority Certificate Attributes";
      uses CRYPTO-CERTIFICATE;
    }
  }
}
