module Cisco-IOS-XR-infra-statsd-act {
  namespace "http://cisco.com/ns/yang/Cisco-IOS-XR-infra-statsd-act";
  prefix statsd-act;

  import cisco-semver {
    prefix semver;
  }
  import Cisco-IOS-XR-types {
    prefix csc;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR action package configuration.
     
     Copyright (c) 2018-2019, 2022 by Cisco Systems, Inc.
     All rights reserved.";

  revision 2019-10-01 {
    description
      "Made changes to be RFC6087 compliant";
    semver:module-version "1.0.1";
  }
  revision 2019-04-05 {
    description
      "Establish semantic version baseline.";
    semver:module-version "1.0.0";
  }
  revision 2018-01-10 {
    description
      "IOS XR 6.4.1 revision.";
  }

  rpc clear-counters-controller {
    description
      "Controller name.\n";
    input {
      leaf controller-name {
        type csc:Interface-name;
        mandatory true;
        description
          "Controller name";
      }
    }
    csc:xr-task "interface";
    csc:cli-command "clear counters <controller-name>";
  }
  rpc clear-counters-all {
    description
      "Clear counters on all interfaces.\n";
    csc:xr-task "interface";
    csc:cli-command "clear counters all";
  }
  rpc clear-counters-interface {
    description
      "Clear counters for interface.\n";
    input {
      leaf interface-name {
        type csc:Interface-name;
        mandatory true;
        description
          "Interface name";
      }
    }
    csc:xr-task "interface";
    csc:cli-command "clear counters interface <interface-name>";
  }
}
