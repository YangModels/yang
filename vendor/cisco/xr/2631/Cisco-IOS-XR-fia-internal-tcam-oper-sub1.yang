submodule Cisco-IOS-XR-fia-internal-tcam-oper-sub1 {
  belongs-to Cisco-IOS-XR-fia-internal-tcam-oper {
    prefix Cisco-IOS-XR-fia-internal-tcam-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR fia-internal-tcam package operational data.
     
     Copyright (c) 2013-2022 by Cisco Systems, Inc.
     All rights reserved.";

  revision 2022-07-09 {
    description
      "Updated type fia-max-asic-instances to fia-max-npu-instances";
    semver:module-version "2.0.0";
  }
  revision 2019-04-05 {
    description
      "Establish semantic version baseline.";
    semver:module-version "1.0.1";
  }
  revision 2015-11-09 {
    description
      "IOS XR 6.0 revision.";
  }

  grouping FIA-TCAM-DB {
    description
      "FIA TCAM DB";
    leaf db-id {
      type uint32;
      description
        "Unique Identifier for database";
    }
    leaf db-inuse-entries {
      type uint32;
      description
        "Number of elements having valid values";
    }
    leaf db-prefix {
      type string;
      description
        "Prefix for database categories";
    }
  }

  grouping FIA-TCAM-BANK {
    description
      "FIA TCAM BANK";
    leaf bank-id {
      type string;
      description
        "Unique Identifier for Bank";
    }
    leaf bank-key-size {
      type string;
      description
        "Size of Bank Key";
    }
    leaf bank-free-entries {
      type uint32;
      description
        "No of Entries not having bank data";
    }
    leaf bank-inuse-entries {
      type uint32;
      description
        "No of Entries having bank data";
    }
    leaf owner {
      type string;
      description
        "Name of Owner for this tcam bank";
    }
    leaf nof-dbs {
      type uint32;
      description
        "Count of database entries of fia tcam bank";
    }
    list bank-db {
      key "db-id";
      description
        "Database info of fia tcam bank";
      uses FIA-TCAM-DB;
    }
  }

  grouping FIA-TCAM-USAGE {
    description
      "FIA TCAM USAGE";
    leaf comp-name {
      type string;
      description
        "component using the NPU TCAM";
    }
    leaf tcam-entries-free {
      type uint32;
      description
        "Number of Free entries in npu tcam";
    }
    leaf tcam-entries-used {
      type uint32;
      description
        "Number of entries used by the component";
    }
  }

  grouping FIA-NPU-TCAM {
    description
      "FIA NPU TCAM";
    leaf npu-id {
      type uint32;
      description
        "Unique Identifier for npu tcam";
    }
    list tcam-usage {
      key "comp-name";
      description
        "Details of fia tcam resource";
      uses FIA-TCAM-USAGE;
    }
    list tcam-bank {
      key "bank-id";
      description
        "Details of fia tcam bank";
      uses FIA-TCAM-BANK;
    }
  }
}
