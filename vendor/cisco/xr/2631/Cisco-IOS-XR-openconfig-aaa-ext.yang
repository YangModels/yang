module Cisco-IOS-XR-openconfig-aaa-ext {
  yang-version 1;
  namespace "http://cisco.com/ns/yang/Cisco-IOS-XR-openconfig-aaa-ext";
  prefix oc-aaa-cisco-xr-ext;

  import openconfig-extensions {
    prefix oc-ext;
  }
  import openconfig-system {
    prefix oc-sys;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module adds Cisco IOS XR extensions to the OpenConfig AAA
     model.";

  revision 2026-07-07 {
    description
      "Add non-sensitive configured-state leaves for local user
       credentials and TACACS shared secrets.";
    reference "0.1.0";
  }

  grouping aaa-authentication-user-security-state {
    description
      "Cisco IOS XR operational state for local user credential
       configuration presence.";
    leaf password-configured {
      type boolean;
      description
        "Indicates whether a legacy local user password is configured.
         The password value is intentionally not exposed.";
    }
    leaf password-hash-configured {
      type boolean;
      description
        "Indicates whether a local user hashed password or secret is
         configured. The hash value is intentionally not exposed.";
    }
  }

  grouping aaa-tacacs-server-security-state {
    description
      "Cisco IOS XR operational state for TACACS shared-secret
       configuration presence.";
    leaf secret-configured {
      type boolean;
      description
        "Indicates whether a TACACS shared secret is configured. The
         secret value is intentionally not exposed.";
    }
  }

  augment "/oc-sys:system/oc-sys:aaa/oc-sys:authentication/oc-sys:users/oc-sys:user/oc-sys:state" {
    description
      "Add Cisco IOS XR local user credential presence state.";
    uses aaa-authentication-user-security-state;
  }
  augment "/oc-sys:system/oc-sys:aaa/oc-sys:server-groups/oc-sys:server-group/oc-sys:servers/oc-sys:server/oc-sys:tacacs/oc-sys:state" {
    description
      "Add Cisco IOS XR TACACS shared-secret presence state.";
    uses aaa-tacacs-server-security-state;
  }
  oc-ext:openconfig-version "0.1.0";
}
