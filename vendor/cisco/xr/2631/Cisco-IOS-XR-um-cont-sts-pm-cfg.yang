module Cisco-IOS-XR-um-cont-sts-pm-cfg {
  namespace "http://cisco.com/ns/yang/Cisco-IOS-XR-um-cont-sts-pm-cfg";
  prefix um-cont-sts-pm-cfg;

  import Cisco-IOS-XR-um-interface-cfg {
    prefix a1;
  }
  import tailf-common {
    prefix tailf;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR cont-sts-pm package configuration.
     
     This YANG module augments the
     modules with configuration data.
     
     Copyright (c) 2020-2025 by Cisco Systems, Inc., and/or its affiliates.
     All rights reserved.";

  revision 2022-07-11 {
    description
      "Added missing description statement to nodes";
    semver:module-version "1.1.0";
  }
  revision 2020-06-11 {
    description
      "Initial release";
    semver:module-version "1.0.0";
  }

  grouping CONT-BODY {
    description
      "Grouping for controller";
    container pm {
      when "../a1:controller-name[starts-with(text(),'STS')]" {
        tailf:dependency "../a1:controller-name";
      }
      description
        "Configure pm parameters";
      container interval-15-min {
        description
          "Configure pm parameters of 15 minute interval";
        container sts {
          description
            "configure STS performance monitoring";
          container threshold {
            description
              "Configure threshold on sts parameters";
            leaf cv-p {
              type uint32 {
                range "0..7967700" {
                  description
                    "CV-P threshold range";
                }
              }
              description
                "set cv-p threshold";
            }
            leaf es-p {
              type uint32 {
                range "0..900" {
                  description
                    "es-p threshold range";
                }
              }
              description
                "set es-p threshold";
            }
            leaf ses-p {
              type uint32 {
                range "0..900" {
                  description
                    "ses-p threshold range";
                }
              }
              description
                "set ses-p threshold";
            }
            leaf uas-p {
              type uint32 {
                range "0..900" {
                  description
                    "uas-p threshold range";
                }
              }
              description
                "set uas-p threshold";
            }
          }
          container report {
            description
              "set sts TCA reporting status";
            container cv-p {
              description
                "set cv TCA reporting status";
              container enable {
                presence "Indicates a enable node is configured.";
                description
                  "Enable TCA reporting";
              }
            }
            container es-p {
              description
                "set es TCA reporting status";
              container enable {
                presence "Indicates a enable node is configured.";
                description
                  "Enable TCA reporting";
              }
            }
            container ses-p {
              description
                "set ses TCA reporting status";
              container enable {
                presence "Indicates a enable node is configured.";
                description
                  "Enable TCA reporting";
              }
            }
            container uas-p {
              description
                "set uas TCA reporting status";
              container enable {
                presence "Indicates a enable node is configured.";
                description
                  "Enable TCA reporting";
              }
            }
          }
        }
      }
      container interval-24-hour {
        description
          "Configure pm parameters of 24 hour interval";
        container sts {
          description
            "configure STS performance monitoring";
          container threshold {
            description
              "Configure threshold on sts parameters";
            leaf cv-p {
              type uint32 {
                range "0..764899200" {
                  description
                    "CV-P threshold range";
                }
              }
              description
                "set cv-p threshold";
            }
            leaf es-p {
              type uint32 {
                range "0..86400" {
                  description
                    "es-p threshold range";
                }
              }
              description
                "set es-p threshold";
            }
            leaf ses-p {
              type uint32 {
                range "0..86400" {
                  description
                    "ses-p threshold range";
                }
              }
              description
                "set ses-p threshold";
            }
            leaf uas-p {
              type uint32 {
                range "0..86400" {
                  description
                    "uas-p threshold range";
                }
              }
              description
                "set uas-p threshold";
            }
          }
          container report {
            description
              "set sts TCA reporting status";
            container cv-p {
              description
                "set cv TCA reporting status";
              container enable {
                presence "Indicates a enable node is configured.";
                description
                  "Enable TCA reporting";
              }
            }
            container es-p {
              description
                "set es TCA reporting status";
              container enable {
                presence "Indicates a enable node is configured.";
                description
                  "Enable TCA reporting";
              }
            }
            container ses-p {
              description
                "set ses TCA reporting status";
              container enable {
                presence "Indicates a enable node is configured.";
                description
                  "Enable TCA reporting";
              }
            }
            container uas-p {
              description
                "set uas TCA reporting status";
              container enable {
                presence "Indicates a enable node is configured.";
                description
                  "Enable TCA reporting";
              }
            }
          }
        }
      }
    }
  }

  augment "/a1:controllers/a1:controller" {
    description
      "This augment extends active nodes configuration";
    uses CONT-BODY;
  }
  augment "/a1:controllers/a1:controller-preconfigure" {
    description
      "This augment extends preconfigured nodes
       configuration";
    uses CONT-BODY;
  }
}
