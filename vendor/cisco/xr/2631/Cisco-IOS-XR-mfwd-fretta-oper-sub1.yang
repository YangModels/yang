submodule Cisco-IOS-XR-mfwd-fretta-oper-sub1 {
  belongs-to Cisco-IOS-XR-mfwd-fretta-oper {
    prefix Cisco-IOS-XR-mfwd-fretta-oper;
  }

  import ietf-inet-types {
    prefix inet;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR mfwd-fretta package operational data.
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  typedef Mfwd-bag-addr-st {
    type inet:ipv4-address;
    description
      "Mfwd bag addr st";
  }

  grouping IPV4-MFWD-FRETTA-CONNECTION-BAG {
    description
      "List of connections";
    leaf-list connection {
      type boolean;
      description
        "Array containing status of each connection";
    }
    leaf-list connect-count {
      type uint32;
      description
        "Array for connection counter";
    }
    leaf-list dis-connect-count {
      type uint32;
      description
        "Array for Disconnection counter";
    }
  }

  grouping IPV4-MFWD-FRETTA-MGMT-BAG {
    description
      "Fretta MFIB management stats";
    leaf-list mem-alloc-stat {
      type uint32;
      description
        "Internal Memory Usage Stats";
    }
    leaf-list mem-free-stat {
      type uint32;
      description
        "Internal Memory Usage Stats";
    }
  }

  grouping IPV4-MFWD-FRETTA-ROUTE-EGR-NPU-RES-EXT-REPL-BAG {
    description
      "MFIB Egress NPU per-replication information";
    leaf gport {
      type int32;
      description
        "Gport information";
    }
    leaf cud1 {
      type int32;
      description
        "CUD1";
    }
    leaf cud2 {
      type int32;
      description
        "CUD2";
    }
  }

  grouping IPV4-MFWD-FRETTA-ROUTE-EGR-NPU-RES-EXT-BAG {
    description
      "MFIB Egress NPU resource information";
    leaf npu-id {
      type uint32;
      description
        "npu";
    }
    leaf status {
      type uint32;
      description
        "Error Code from BRCM";
    }
    list repl-bag {
      description
        "Replications on this NPU";
      uses IPV4-MFWD-FRETTA-ROUTE-EGR-NPU-RES-EXT-REPL-BAG;
    }
  }

  grouping IPV4-MFWD-FRETTA-ROUTE-ING-NPU-RES-EXT-BAG {
    description
      "MFIB Ingress NPU resource information";
    leaf status1 {
      type uint32;
      description
        "Error Code 1 from BRCM";
    }
    leaf status2 {
      type uint32;
      description
        "Error Code 2 from BRCM";
    }
    leaf npu-id {
      type uint32;
      description
        "npu";
    }
    leaf vrf-id {
      type uint32;
      description
        "VRF ID";
    }
    leaf source {
      type Mfwd-bag-addr-st;
      description
        "Source address";
    }
    leaf group {
      type Mfwd-bag-addr-st;
      description
        "Group address";
    }
    leaf result {
      type uint32;
      description
        "BRCM FEC id";
    }
    leaf fec-id {
      type uint32;
      description
        "Fec ID";
    }
    leaf rpf-id {
      type uint32;
      description
        "RPF ID";
    }
    leaf mcid {
      type uint32;
      description
        "MCID";
    }
    leaf comp-result {
      type uint32;
      description
        "compression FEC";
    }
    leaf comp-id {
      type uint16;
      description
        "compression  ID";
    }
  }

  grouping IPV4-MFWD-FRETTA-DNX-DPA-ROUTE-BAG {
    description
      "MFIB DNX DPA route bag";
    leaf dpa-route-hdl {
      type uint64;
      description
        "DPA Route Handle";
    }
    leaf dpa-route-trans-id {
      type uint32;
      description
        "DPA Route transaction ID";
    }
    leaf npu-id {
      type uint32;
      description
        "NPU ID";
    }
    leaf ipmc-vrf {
      type int32;
      description
        "VRF ID";
    }
    leaf use-merged {
      type boolean;
      description
        "Used Merged";
    }
    leaf a-intf {
      type int32;
      description
        "Accepting interface";
    }
    leaf a-intf-id {
      type int32;
      description
        "Accepting interface ID";
    }
    leaf a-tun-rif {
      type uint32;
      description
        "Tunnel RIF";
    }
    leaf a-tun-lif {
      type uint32;
      description
        "Tunnel LIF";
    }
    leaf fgid {
      type uint32;
      description
        "Route MCID";
    }
    leaf ipmc-fec-id {
      type uint32;
      description
        "BRCM specific FEC id";
    }
    leaf ipmc-punt-action {
      type uint16;
      description
        "Punt action";
    }
    leaf tcam-entry-id {
      type uint32;
      description
        "TCAM entry ID";
    }
    leaf ipmc-action {
      type uint32;
      description
        "IPMC Action";
    }
    leaf l3intf-refhdl {
      type uint64;
      description
        "L3 interface refhandle";
    }
    leaf l3intf-refkey {
      type uint64;
      description
        "L3 interface refkey";
    }
    leaf ipmc-fec-accessed {
      type uint32;
      description
        "IPMC Fec accessed";
    }
    leaf stats-enabled {
      type boolean;
      description
        "Statistics enabled";
    }
    leaf stats-activated {
      type boolean;
      description
        "Statistics activated";
    }
  }

  grouping IPV4-MFWD-FRETTA-ROUTE-DIR-BAG {
    description
      "MFIB Route pgm status";
    leaf rc {
      type uint32;
      description
        "Return value of route programed";
    }
    leaf ts {
      type int32;
      units "second";
      description
        "Time in current state (seconds)";
    }
  }

  grouping IPV4-MFWD-FRETTA-ROUTE-EG-DNX-EXT-BAG {
    description
      "MFIB Egress DNX extension";
    leaf bvi-count {
      type int16;
      description
        "BVI count";
    }
  }

  grouping IPV4-MFWD-FRETTA-ROUTE-ING-DNX-EXT-BAG {
    description
      "MFIB Ingress DNX extension";
    leaf local-route {
      type boolean;
      description
        "Local route";
    }
    leaf in-hw {
      type boolean;
      description
        "Programmed in H/W";
    }
    leaf is-accept-intf-bvi {
      type boolean;
      description
        "Is BVI accepting interface";
    }
    leaf is-tun-rif-set {
      type boolean;
      description
        "Is tunnel RIF set";
    }
    leaf ipmc-fec-id {
      type uint32;
      description
        "BRCM specific FEC id";
    }
    leaf encap-id {
      type uint32;
      description
        "Encap id";
    }
    leaf tun-rif-vrf-id {
      type uint32;
      description
        "tun rif vrf id";
    }
    leaf tun-rif-rpf-id {
      type uint32;
      description
        "tun rif rpf id";
    }
    leaf tun-rif {
      type uint32;
      description
        "tun rif";
    }
    leaf tun-lif {
      type uint32;
      description
        "tun lif";
    }
  }

  grouping IPV4-MFWD-FRETTA-DPA-OLIST-DETAIL-BAG {
    description
      "MFIB DNX DPA OLE bag";
    leaf bundle-ifhandle {
      type uint32;
      description
        "Bundle interface handle";
    }
    leaf mem-ifhandle {
      type uint32;
      description
        "Ifhandle of Bundle Member";
    }
    leaf parent-ifhandle {
      type uint32;
      description
        "Ifhandle of Bundle Parent Interface";
    }
    leaf bvi-ifhandle {
      type uint32;
      description
        "Ifhandle of BVI Interface";
    }
    leaf member-sysport {
      type uint16;
      description
        "BRCM sysport number";
    }
    leaf is-local {
      type uint8;
      description
        "BRCM view of interface scope";
    }
    leaf ole-type {
      type uint8;
      description
        "OLE Type";
    }
    leaf npu-id {
      type uint32;
      description
        "NPU ID";
    }
    leaf o-intf {
      type int64;
      description
        "OLE count";
    }
    leaf is-bd-recycle-lif-ole {
      type boolean;
      description
        "Is Recycle Lif Ole";
    }
    leaf bd-recycle-lif {
      type uint32;
      description
        "BD Recycle Lif";
    }
    leaf o-port {
      type uint32;
      description
        "Outgoing port";
    }
    leaf cud {
      type int64;
      description
        "Copy unique data";
    }
    leaf is-bundle {
      type boolean;
      description
        "Is a bundle OLE";
    }
    leaf efp-visibiity {
      type boolean;
      description
        "EFP visibiity";
    }
    leaf df-state {
      type boolean;
      description
        "MH DF/NDF state";
    }
    leaf sys-port {
      type uint16;
      description
        "Sys port";
    }
    leaf mpls-encap-id {
      type uint64;
      description
        "MPLS encap ID";
    }
    leaf is-pw-access {
      type boolean;
      description
        "Is a Access PW";
    }
    leaf pw-encap-id {
      type uint32;
      description
        "PW encap ID";
    }
    leaf lag-id {
      type uint64;
      description
        "LAG ID";
    }
    leaf esi-ifh {
      type uint32;
      description
        "MH ESI interface";
    }
    leaf bucket-id {
      type uint32;
      description
        "EVPN bucket_id";
    }
    leaf l3intf-refhdl {
      type uint64;
      description
        "L3 interface refhandle";
    }
    leaf l3intf-refkey {
      type uint64;
      description
        "L3 interface refkey";
    }
    leaf l2port-refhandl {
      type uint64;
      description
        "L2 port refhandle";
    }
    leaf l2port-refkey {
      type uint64;
      description
        "L2 port refkey";
    }
    leaf mplsnh-refhandl {
      type uint64;
      description
        "MPLS NH refhandle";
    }
    leaf mplsnh-refkey {
      type uint64;
      description
        "MPLS NH refkey";
    }
    leaf lagport-refhndl {
      type uint64;
      description
        "LAG Port refhandle";
    }
    leaf lagport-refkey {
      type uint64;
      description
        "LAG Port refkey";
    }
    leaf packets {
      type uint64;
      description
        "total packets out of this intf";
    }
    leaf bytes {
      type uint64;
      units "byte";
      description
        "total bytes out of this intf";
    }
  }

  grouping DNX-MCAST-BVI-MSG-INFO {
    description
      "DNX MCAST BVI MSG INFO";
    leaf shm-entry-id {
      type uint32;
      description
        "shm entry id";
    }
    leaf trans-id {
      type uint32;
      description
        "trans id";
    }
    leaf ole-cnt {
      type uint16;
      description
        "ole cnt";
    }
  }

  grouping IPV4-MFWD-FRETTA-OLIST-DETAIL-BAG {
    description
      "MFIB Fretta-olist detail";
    leaf npu-id {
      type uint32;
      description
        "Device or unit number";
    }
    leaf o-intf {
      type uint32;
      description
        "Outgoing interface handle";
    }
    leaf o-port {
      type uint16;
      description
        "System port of physical interface";
    }
    leaf ole-type {
      type uint8;
      description
        "OLE Type";
    }
    leaf ul-ifh {
      type uint32;
      description
        "Underlying interface handle";
    }
    leaf is-bundle {
      type uint8;
      description
        "Is this a bundle interface";
    }
    leaf is-local {
      type uint8;
      description
        "BRCM view of interface scope";
    }
    leaf bundle-ifhandle {
      type uint32;
      description
        "Bundle interface handle";
    }
    leaf mem-ifhandle {
      type uint32;
      description
        "Ifhandle of Bundle Member";
    }
    leaf member-sysport {
      type uint16;
      description
        "BRCM sysport number";
    }
    leaf is-bvi {
      type boolean;
      description
        "Is BVI";
    }
    leaf bd-id {
      type uint32;
      description
        "BVI associated BD_ID";
    }
    leaf rif {
      type uint32;
      description
        "BVI associated RIF";
    }
    leaf bvi-shm-entry-id {
      type uint32;
      description
        "Currently used shm_id for BVI OLE";
    }
    leaf trans-id {
      type uint32;
      description
        "intf transaction id";
    }
    list irb-nfn-msg {
      max-elements "4";
      description
        "IRB Message Info";
      uses DNX-MCAST-BVI-MSG-INFO;
    }
  }

  grouping IPV4-MFWD-FRETTA-EG-ROUTE-EXT-BAG {
    description
      "MFIB Egress Route extension";
    leaf rpf-id {
      type uint32;
      description
        "RPF ID";
    }
  }

  grouping IPV4-MFWD-FRETTA-ING-ROUTE-EXT-BAG {
    description
      "MFIB Ingress Route extension";
    leaf route-fgid {
      type uint32;
      description
        "Route's FGID";
    }
    leaf rpf-if-signal {
      type boolean;
      description
        "RPF Interface signal";
    }
    leaf encap-rpf-id {
      type uint32;
      description
        "New RPF ID";
    }
    leaf local-rcvr {
      type boolean;
      description
        "Head end with local receivers";
    }
    leaf encap-id-flag {
      type boolean;
      description
        "P2MP/TE-mLDP headend ";
    }
    leaf encap-id {
      type int32;
      description
        "Encap ID of the core";
    }
    leaf punt {
      type boolean;
      description
        "Punt";
    }
    leaf punt-if-fwd {
      type boolean;
      description
        "Punt";
    }
    leaf punt-action {
      type uint32;
      description
        "Punt action";
    }
    leaf tun-rif {
      type uint32;
      description
        "Tunnel RIF";
    }
    leaf tun-lif {
      type uint32;
      description
        "Tunnel LIF";
    }
    leaf stats-enabled {
      type boolean;
      description
        "Statistics enabled";
    }
  }

  grouping IPV4-MFWD-FRETTA-ROUTE-EXT-BAG {
    description
      "MFIB Route extension";
    leaf vrf-id {
      type uint32;
      description
        "VRF ID";
    }
    leaf routeid {
      type uint32;
      description
        "route id";
    }
    leaf pri-mcid {
      type int32;
      description
        "Core Primary MC ID";
    }
    leaf bkup-mcid {
      type int32;
      description
        "Core Backup MC ID";
    }
    leaf trans-id {
      type uint32;
      description
        "transaction id";
    }
  }

  grouping IPV4-MFWD-FRETTA-ROUTE-BAG {
    description
      "MFIB Fretta-multicast-routing entry";
    container route-ext {
      description
        "Route platform extension";
      uses IPV4-MFWD-FRETTA-ROUTE-EXT-BAG;
    }
    container ing-route-ext {
      description
        "Ingress route extension";
      uses IPV4-MFWD-FRETTA-ING-ROUTE-EXT-BAG;
    }
    container eg-route-ext {
      description
        "Engress route extension";
      uses IPV4-MFWD-FRETTA-EG-ROUTE-EXT-BAG;
    }
    container dnx-ing-ext {
      description
        "Ingress DNX extension";
      uses IPV4-MFWD-FRETTA-ROUTE-ING-DNX-EXT-BAG;
    }
    container dnx-eg-ext {
      description
        "Egress DNX extension";
      uses IPV4-MFWD-FRETTA-ROUTE-EG-DNX-EXT-BAG;
    }
    container eg {
      description
        "Egress route status info";
      uses IPV4-MFWD-FRETTA-ROUTE-DIR-BAG;
    }
    container ing {
      description
        "Ingress route status info";
      uses IPV4-MFWD-FRETTA-ROUTE-DIR-BAG;
    }
    container dpa-route {
      description
        "DPA contents of route";
      uses IPV4-MFWD-FRETTA-DNX-DPA-ROUTE-BAG;
    }
    leaf internal {
      type boolean;
      description
        "Internal cmd";
    }
    leaf internal-detail {
      type boolean;
      description
        "internal detail cmd";
    }
    leaf vrf {
      type uint32;
      description
        "vrf id";
    }
    leaf npu-id {
      type uint32;
      description
        "A intf Npu ID";
    }
    leaf npu-mask {
      type uint32;
      description
        "A intf programed in list of NPUs";
    }
    leaf dpa-olist-hdl {
      type uint64;
      description
        "DPA Olist Handle";
    }
    leaf dpa-olist-trans-id {
      type uint32;
      description
        "DPA Ole transaction ID";
    }
    leaf source {
      type Mfwd-bag-addr-st;
      description
        "Source address";
    }
    leaf src-pfx-len {
      type Mfwd-bag-addr-st;
      description
        "Group address prefix";
    }
    leaf group {
      type Mfwd-bag-addr-st;
      description
        "Group address prefix length";
    }
    leaf grp-pfx-len {
      type Mfwd-bag-addr-st;
      description
        "The prefix length of the entire address";
    }
    leaf flags {
      type uint32;
      description
        "Route status-flags";
    }
    leaf a-intf {
      type uint32;
      description
        "Accepting Interface-handle";
    }
    leaf a-intf-id {
      type uint32;
      description
        "Accepting Interface BRCM specific id";
    }
    leaf fgid {
      type uint32;
      description
        "FGID that maps route with oles";
    }
    leaf ipmc-fec-id {
      type uint32;
      description
        "BRCM specific FEC id";
    }
    leaf olist-count {
      type uint32;
      description
        "Olist count";
    }
    leaf olist-fgid {
      type uint32;
      description
        "Olist FGID that maps route with oles";
    }
    leaf error {
      type uint32;
      description
        "Error code from BRCM";
    }
    leaf rc-val {
      type uint32;
      description
        "RC val from EDM backend, will be used to print
         the error message on CLI";
    }
    list ing-bdl {
      description
        "A interface is a bundle";
      uses IPV4-MFWD-FRETTA-OLIST-DETAIL-BAG;
    }
    list dpa-ing-bdl {
      description
        "A interface is a bundle";
      uses IPV4-MFWD-FRETTA-DPA-OLIST-DETAIL-BAG;
    }
    list ole {
      description
        "Olist BRCM related detailed info";
      uses IPV4-MFWD-FRETTA-OLIST-DETAIL-BAG;
    }
    list dpa-ole {
      description
        "Olist BRCM related detailed info";
      uses IPV4-MFWD-FRETTA-DPA-OLIST-DETAIL-BAG;
    }
    list ing-route-res-ext-bag {
      description
        "Ingress NPU resource extension";
      uses IPV4-MFWD-FRETTA-ROUTE-ING-NPU-RES-EXT-BAG;
    }
    list egr-route-res-ext-bag {
      description
        "Egress NPU resource extension";
      uses IPV4-MFWD-FRETTA-ROUTE-EGR-NPU-RES-EXT-BAG;
    }
  }

  grouping IPV4-MFWD-FRETTA-ROUTE-SUMM-BAG {
    description
      "HFR MFIB Route Summary";
    leaf groutes-count {
      type uint32;
      description
        "No. of (*,G) routes";
    }
    leaf sg-routes-count {
      type uint32;
      description
        "No. of (S,G) routes";
    }
    leaf sg-route-oleg-intf {
      type uint32;
      description
        "No. of Egress Interface";
    }
    leaf sg-route-oleg-u-intf {
      type uint32;
      description
        "No. of Unique Egress Interface";
    }
    leaf bundle-mem-count {
      type uint32;
      description
        " No. of Bundle Member count";
    }
    leaf bundle-intf-count {
      type uint32;
      description
        " No. of Bundle Interface count";
    }
  }
}
