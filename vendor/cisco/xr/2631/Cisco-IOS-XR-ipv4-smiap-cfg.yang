module Cisco-IOS-XR-ipv4-smiap-cfg {
  namespace "http://cisco.com/ns/yang/Cisco-IOS-XR-ipv4-smiap-cfg";
  prefix ipv4-smiap-cfg;

  import ietf-inet-types {
    prefix inet;
  }
  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ipv4-smiap package configuration.
     
     This module contains definitions
     for the following management objects:
       ipv4-virtual: IPv4 virtual address for management interfaces
     
     Copyright (c) 2013-2019 by Cisco Systems, Inc.
     All rights reserved.";

  revision 2019-04-05 {
    description
      "Establish semantic version baseline.";
    semver:module-version "1.0.1";
  }
  revision 2016-07-04 {
    description
      "this schema file has all the latest changes.";
  }
  revision 2015-11-09 {
    description
      "IOS XR 6.0 revision.";
  }

  container ipv4-virtual {
    description
      "IPv4 virtual address for management interfaces";
    container vrfs {
      description
        "VRFs for the virtual IPv4 addresses";
      list vrf {
        key "vrf-name";
        description
          "A VRF for a virtual IPv4 address.  Specify
           'default' for VRF default";
        container address {
          presence "Indicates a address node is configured.";
          description
            "IPv4 sddress and mask";
          leaf address {
            type inet:ipv4-address-no-zone;
            mandatory true;
            description
              "IPv4 address";
          }
          leaf netmask {
            type xr:Ipv4-prefix-length;
            mandatory true;
            description
              "IPv4 address mask";
          }
        }
        leaf vrf-name {
          type xr:Cisco-ios-xr-string;
          description
            "Name of VRF";
        }
      }
    }
    leaf use-as-source-address {
      type empty;
      description
        "Enable use as default source address on sourced
         packets";
    }
  }
}
