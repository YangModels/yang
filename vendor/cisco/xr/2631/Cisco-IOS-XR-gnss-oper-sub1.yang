submodule Cisco-IOS-XR-gnss-oper-sub1 {
  belongs-to Cisco-IOS-XR-gnss-oper {
    prefix Cisco-IOS-XR-gnss-oper;
  }

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR gnss package operational data.
     
     Copyright (c) 2013-2024 by Cisco Systems, Inc.
     All rights reserved.";

  revision 2024-12-16 {
    description
      "Add satellite band information.";
    semver:module-version "2.2.0";
  }
  revision 2020-10-20 {
    description
      "Add optional serial number field";
    semver:module-version "2.1.0";
  }
  revision 2019-09-30 {
    description
      "Removed enum usage from alarms, added elevation, azimuth and time locked by gnss receiver";
    semver:module-version "2.0.0";
  }
  revision 2019-04-05 {
    description
      "Establish semantic version baseline.";
    semver:module-version "1.0.0";
  }
  revision 2017-09-07 {
    description
      "Fixed type translation error.";
  }
  revision 2015-11-09 {
    description
      "IOS XR 6.0 revision.";
  }

  typedef Gnssmgr-bag-spoofing-status {
    type enumeration {
      enum "unknown" {
        value 0;
        description
          "Unknown";
      }
      enum "detected" {
        value 1;
        description
          "Detected";
      }
      enum "not-detected" {
        value 2;
        description
          "Not Detected";
      }
    }
    description
      "Spoofing status";
  }

  typedef Gnssmgr-bag-spoofing-detection {
    type enumeration {
      enum "not-supported" {
        value 0;
        description
          "Not Supported";
      }
      enum "active" {
        value 1;
        description
          "Active";
      }
      enum "inactive" {
        value 2;
        description
          "Inactive";
      }
    }
    description
      "Spoofing Detection";
  }

  typedef Gnssmgr-bag-sat-sig {
    type enumeration {
      enum "gps-l1ca" {
        value 0;
        description
          "GPS L1CA";
      }
      enum "gps-l1c" {
        value 1;
        description
          "GPS L1C";
      }
      enum "gps-l2c-l" {
        value 2;
        description
          "GPS L2C";
      }
      enum "gps-l5" {
        value 3;
        description
          "GPS L5";
      }
      enum "sbas-l1" {
        value 4;
        description
          "SBAS L1";
      }
      enum "sbas-l5" {
        value 5;
        description
          "SBAS L5";
      }
      enum "gal-e1" {
        value 6;
        description
          "Galileo E1";
      }
      enum "gal-e5a" {
        value 7;
        description
          "Galileo E5a";
      }
      enum "gal-e5b" {
        value 8;
        description
          "Galileo E5b";
      }
      enum "gal-e6" {
        value 9;
        description
          "Galileo E6";
      }
      enum "bei-b1" {
        value 10;
        description
          "BeiDou B1";
      }
      enum "bei-b2" {
        value 11;
        description
          "BeiDou B2";
      }
      enum "bei-b3" {
        value 12;
        description
          "BeiDou B3";
      }
      enum "bei-b1c" {
        value 13;
        description
          "BeiDou B1C";
      }
      enum "bei-b2a" {
        value 14;
        description
          "BeiDou B2a";
      }
      enum "bei-b2b" {
        value 15;
        description
          "BeiDou B2b";
      }
      enum "qzs-l1ca" {
        value 16;
        description
          "QZSS L1CA";
      }
      enum "qzs-l1cb" {
        value 17;
        description
          "QZSS L1CB";
      }
      enum "qzs-l1c" {
        value 18;
        description
          "QZSS L1C";
      }
      enum "qzs-l1s" {
        value 19;
        description
          "QZSS L1S";
      }
      enum "qzs-l2c" {
        value 20;
        description
          "QZSS L2C";
      }
      enum "qzs-l5" {
        value 21;
        description
          "QZSS L5";
      }
      enum "qzs-l6" {
        value 22;
        description
          "QZSS L6";
      }
      enum "glo-l1of" {
        value 23;
        description
          "GLONASS L1OF";
      }
      enum "glo-l2of" {
        value 24;
        description
          "GLONASS L2OF";
      }
      enum "glo-l1oc" {
        value 25;
        description
          "GLONASS L1OC";
      }
      enum "glo-l2oc" {
        value 26;
        description
          "GLONASS L2OC";
      }
      enum "glo-l3oc" {
        value 27;
        description
          "GLONASS L3OC";
      }
      enum "nav-l1" {
        value 28;
        description
          "IRNSS L5";
      }
      enum "nav-l5" {
        value 29;
        description
          "IRNSS L5";
      }
      enum "nav-s" {
        value 30;
        description
          "IRNSS S";
      }
    }
    description
      "Space vehicle (SV) signal type";
  }

  typedef Gnssmgr-bag-sat-sv {
    type enumeration {
      enum "gps" {
        value 0;
        description
          "GPS";
      }
      enum "glonass" {
        value 1;
        description
          "GLONASS";
      }
      enum "sbas" {
        value 2;
        description
          "SBAS (WAAS)";
      }
      enum "qzss" {
        value 3;
        description
          "QZSS";
      }
      enum "bei-dou" {
        value 4;
        description
          "BeiDou";
      }
      enum "galileo" {
        value 5;
        description
          "Galileo";
      }
      enum "irnss" {
        value 6;
        description
          "IRNSS";
      }
      enum "gnss" {
        value 7;
        description
          "GNSS";
      }
      enum "unknown" {
        value 8;
        description
          "Unknown";
      }
      enum "reserved" {
        value 9;
        description
          "Reserved";
      }
    }
    description
      "Space vehicle (SV) type";
  }

  typedef Gnssmgr-bag-optional-string {
    type string;
    description
      "Gnssmgr bag optional string";
  }

  typedef Gnssmgr-bag-rx-mode {
    type enumeration {
      enum "no-fix" {
        value 0;
        description
          "No fix";
      }
      enum "dead-reckoning-only" {
        value 1;
        description
          "Dead Reckoning only";
      }
      enum "fix-2d" {
        value 2;
        description
          "2D fix";
      }
      enum "fix-3d" {
        value 3;
        description
          "3D fix";
      }
      enum "gnss-and-dead-reckoning" {
        value 4;
        description
          "GNSS and Dead Reckoning";
      }
      enum "time-fix-only" {
        value 5;
        description
          "Time fix only";
      }
      enum "a-gnss" {
        value 6;
        description
          "A GNSS";
      }
      enum "gnss-and-sbas" {
        value 7;
        description
          "GNSS and SBAS";
      }
      enum "gnss-and-gbas" {
        value 8;
        description
          "GNSS and GBAS";
      }
      enum "reserved" {
        value 9;
        description
          "Reserved";
      }
    }
    description
      "Receiver mode";
  }

  typedef Gnssmgr-bag-lock-status {
    type enumeration {
      enum "phase-locked" {
        value 0;
        description
          "Phase locked";
      }
      enum "frequency-locked" {
        value 1;
        description
          "Frequency locked";
      }
      enum "initializing" {
        value 2;
        description
          "Initializing";
      }
      enum "auto-holdover" {
        value 3;
        description
          "Auto holdover";
      }
      enum "manual-holdover" {
        value 4;
        description
          "Manual holdover";
      }
      enum "recovery" {
        value 5;
        description
          "Recovery";
      }
      enum "inactive" {
        value 6;
        description
          "Inactive";
      }
    }
    description
      "Lock status";
  }

  typedef Gnssmgr-bag-1pps-polarity {
    type enumeration {
      enum "positive" {
        value 0;
        description
          "Positive";
      }
      enum "negative" {
        value 1;
        description
          "Negative";
      }
    }
    description
      "1PPS polarity";
  }

  typedef Gnssmgr-bag-constellation {
    type enumeration {
      enum "auto" {
        value 0;
        description
          "Auto choose constellation";
      }
      enum "gps" {
        value 1;
        description
          "GPS";
      }
      enum "galileo" {
        value 2;
        description
          "Galileo";
      }
      enum "bei-dou" {
        value 3;
        description
          "BeiDou";
      }
      enum "qzss" {
        value 4;
        description
          "QZSS";
      }
      enum "glonass" {
        value 5;
        description
          "GLONASS";
      }
      enum "sbas" {
        value 6;
        description
          "SBAS (WAAS)";
      }
      enum "irnss" {
        value 7;
        description
          "IRNSS";
      }
    }
    description
      "Consetellation";
  }

  grouping GNSSMGR-BAG-SATELLITE {
    description
      "Satellite information";
    leaf prn-number {
      type uint8;
      description
        "PRN number";
    }
    leaf channel-number {
      type uint8;
      description
        "Channel number";
    }
    leaf acquisition-flag {
      type boolean;
      description
        "Acquisition flag";
    }
    leaf ephemeris-flag {
      type boolean;
      description
        "Ephemeris flag";
    }
    leaf sv-type {
      type Gnssmgr-bag-sat-sv;
      description
        "Space vehicle (SV) type";
    }
    leaf signal-strength {
      type uint32;
      description
        "Signal strength (0.001 dB-Hz)";
    }
    leaf elevation {
      type uint32;
      description
        "Elevation (0.001 degrees)";
    }
    leaf azimuth {
      type uint32;
      description
        "Azimuth (0.001 degrees)";
    }
    leaf-list signal {
      type Gnssmgr-bag-sat-sig;
      description
        "Space vehicle (SV) signal type";
    }
  }

  grouping GNSSMGR-RX-INFO {
    description
      "GNSS receiver information";
    leaf receiver-number {
      type uint32;
      description
        "Receiver number";
    }
    leaf node {
      type xr:Node-id;
      description
        "Node the receiver is on";
    }
    leaf enabled {
      type boolean;
      description
        "Whether the receiver is enabled";
    }
    leaf shutdown {
      type boolean;
      description
        "Whether the receiver is shutdown";
    }
    leaf anti-jam-disable {
      type boolean;
      description
        "Whether anti-jam mode is disabled";
    }
    leaf constellation {
      type Gnssmgr-bag-constellation;
      description
        "Constellation used by the receiver";
    }
    leaf snr-threshold {
      type uint32;
      description
        "Satellite SNR threshold";
    }
    leaf elevation-threshold {
      type uint32;
      description
        "Satellite elevation threshold";
    }
    leaf pdop-threshold {
      type uint32;
      description
        "Satellite position (3D) dilution of precision
         (PDOP) threshold";
    }
    leaf traim-threshold {
      type uint32;
      description
        "Satellite TRAIM threshold";
    }
    leaf cable-delay-compensation {
      type int32;
      description
        "Cable delay compensation";
    }
    leaf polarity1pps {
      type Gnssmgr-bag-1pps-polarity;
      description
        "1PPS polarity";
    }
    leaf available {
      type boolean;
      description
        "Whether the receiver is available";
    }
    leaf lock-status {
      type Gnssmgr-bag-lock-status;
      description
        "The lock status of the receiver";
    }
    leaf receiver-mode {
      type Gnssmgr-bag-rx-mode;
      description
        "The receiver mode of the receiver";
    }
    leaf survey-progress {
      type uint32;
      description
        "The survey progress of the receiver";
    }
    leaf holdover-duration {
      type uint32;
      description
        "The holdover duration of the receier";
    }
    leaf major-alarm {
      type uint32;
      description
        "The status of the receiver's major alarm";
    }
    leaf minor-alarm {
      type uint32;
      description
        "The status of the receiver's minor alarm";
    }
    leaf pdop {
      type uint32;
      description
        "Position (3D) dilution of precision (in
         thousandths)";
    }
    leaf hdop {
      type uint32;
      description
        "Horizontal dilution of precision (in
         thousandths)";
    }
    leaf vdop {
      type uint32;
      description
        "Vertical dilution of precision (in thousandths)";
    }
    leaf tdop {
      type uint32;
      description
        "Time dilution of precision (in thousandths)";
    }
    leaf latitude {
      type int32;
      units "centisecond";
      description
        "Latitude of the receiver (arcseconds)";
    }
    leaf longitude {
      type int32;
      units "centisecond";
      description
        "Longitude of the receiver (arcseconds)";
    }
    leaf altitude {
      type int64;
      description
        "Altitude of the receiver (m)";
    }
    leaf time {
      type uint32;
      units "second";
      description
        "Current time recovered by the receiver (secs
         since epoch)";
    }
    leaf utc-offset {
      type int16;
      description
        "UTC offset of the receiver";
    }
    leaf firmware-version {
      type Gnssmgr-bag-optional-string;
      description
        "Firmware version of the receiver";
    }
    leaf locked-time {
      type uint32;
      units "second";
      description
        "Locked time recovered by the receiver (secs
         since epoch)";
    }
    leaf serial-number {
      type Gnssmgr-bag-optional-string;
      description
        "Serial number of the receiver";
    }
    leaf satellite-data-known {
      type boolean;
      description
        "Is the satellite data known?";
    }
    leaf spoofing-detection {
      type Gnssmgr-bag-spoofing-detection;
      description
        "Whether spoofing detection is active";
    }
    leaf spoofing-status {
      type Gnssmgr-bag-spoofing-status;
      description
        "Spoofing status";
    }
    leaf spoofing-time {
      type uint32;
      units "second";
      description
        "Time of spoofing attempt detection (secs since
         epoch)";
    }
    list satellite {
      description
        "Satellites visible to the receiver";
      uses GNSSMGR-BAG-SATELLITE;
    }
  }
}
