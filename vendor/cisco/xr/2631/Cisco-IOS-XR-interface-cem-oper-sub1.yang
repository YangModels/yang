submodule Cisco-IOS-XR-interface-cem-oper-sub1 {
  belongs-to Cisco-IOS-XR-interface-cem-oper {
    prefix Cisco-IOS-XR-interface-cem-oper;
  }

  import ietf-yang-types {
    prefix yang;
  }
  import cisco-semver {
    prefix semver;
  }
  include Cisco-IOS-XR-interface-cem-oper-sub2 {
    revision-date 2024-04-19;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR interface-cem package operational data.
     
     Copyright (c) 2013-2024 by Cisco Systems, Inc.
     All rights reserved.";

  revision 2024-04-19 {
    description
      "Added leaf for CEM interface to support the Packet loss threshold timer value.";
    semver:module-version "2.1.0";
  }
  revision 2021-08-18 {
    description
      "Configured, operational, in-use fields for dejitter and configured, operational fields for payload are added.
       2021-07-20
           CEM interface payload-dejitter-mapping and capabilities command added.
       2021-06-06
           CEM interface oper command added.";
    semver:module-version "2.0.0";
  }
  revision 2019-04-05 {
    description
      "Establish semantic version baseline.";
    semver:module-version "1.0.0";
  }
  revision 2015-11-09 {
    description
      "IOS XR 6.0 revision.";
  }

  typedef Cem-ac-client-types {
    type enumeration {
      enum "none" {
        value 0;
        description
          "None";
      }
      enum "oc3" {
        value 1;
        description
          "OC3";
      }
      enum "oc12" {
        value 2;
        description
          "OC12";
      }
      enum "oc48" {
        value 3;
        description
          "OC48";
      }
      enum "oc192" {
        value 4;
        description
          "OC192";
      }
      enum "oc768" {
        value 5;
        description
          "OC768";
      }
      enum "stm1" {
        value 6;
        description
          "STM1";
      }
      enum "stm4" {
        value 7;
        description
          "STM4";
      }
      enum "stm16" {
        value 8;
        description
          "STM16";
      }
      enum "stm64" {
        value 9;
        description
          "STM64";
      }
      enum "stm256" {
        value 10;
        description
          "STM256";
      }
      enum "hundred-gig-ethernet" {
        value 11;
        description
          "HundredGigEthernet";
      }
      enum "ten-gig-ethernet" {
        value 12;
        description
          "TenGigEthernet";
      }
      enum "fourty-gig-ethernet" {
        value 13;
        description
          "FourtyGigEthernet";
      }
      enum "one-gig-ethernet" {
        value 14;
        description
          "OneGigEthernet";
      }
      enum "twenty-five-gig-ethernet" {
        value 15;
        description
          "TwentyFiveGigEthernet";
      }
      enum "otu2" {
        value 16;
        description
          "OTU2";
      }
      enum "otu2e" {
        value 17;
        description
          "OTU2E";
      }
      enum "otu4" {
        value 18;
        description
          "OTU4";
      }
      enum "one-gig-fiber-channel" {
        value 19;
        description
          "OneGigFiberChannel";
      }
      enum "two-gig-fiber-channel" {
        value 20;
        description
          "TwoGigFiberChannel";
      }
      enum "four-gig-fiber-channel" {
        value 21;
        description
          "FourGigFiberChannel";
      }
      enum "eight-gig-fiber-channel" {
        value 22;
        description
          "EightGigFiberChannel";
      }
      enum "ten-gig-fiber-channel" {
        value 23;
        description
          "TenGigFiberChannel";
      }
      enum "sixteen-gig-fiber-channel" {
        value 24;
        description
          "SixteenGigFiberChannel";
      }
      enum "thirty-two-gig-fiber-channel" {
        value 25;
        description
          "ThirtyTwoGigFiberChannel";
      }
    }
    description
      "Cem ac client types";
  }

  typedef Cem-packet-replace-policy {
    type enumeration {
      enum "ais" {
        value 1;
        description
          "AIS";
      }
      enum "user-specific" {
        value 2;
        description
          "User Specific";
      }
    }
    description
      "CEM PACKET REPLACE POLICY";
  }

  typedef Cem-end-point-str {
    type enumeration {
      enum "endpoint-raw" {
        value 0;
        description
          "EndpointRawString";
      }
      enum "endpoint-ascii" {
        value 1;
        description
          "EndpointAsciiString";
      }
      enum "endpoint-hex" {
        value 2;
        description
          "EndpointHexString";
      }
    }
    description
      "CEM ENDPOINT STR TYPE";
  }

  typedef Cem-rtp {
    type enumeration {
      enum "disabled" {
        value 0;
        description
          "Disabled";
      }
      enum "enabled" {
        value 1;
        description
          "Enabled";
      }
    }
    description
      "CEM RTP";
  }

  typedef Cem-signalling {
    type enumeration {
      enum "no-cas" {
        value 0;
        description
          "NoCAS";
      }
      enum "cas" {
        value 1;
        description
          "CAS";
      }
    }
    description
      "CEM signalling";
  }

  typedef Cem-dummy-mode {
    type enumeration {
      enum "last-frame" {
        value 0;
        description
          "LastFrame";
      }
      enum "user-defined" {
        value 1;
        description
          "UserDefined";
      }
    }
    description
      "CEM interface dummy mode";
  }

  typedef Cem-interface-state {
    type enumeration {
      enum "down" {
        value 0;
        description
          "Down";
      }
      enum "up" {
        value 1;
        description
          "Up";
      }
    }
    description
      "CEM interface states";
  }

  grouping CEM-PAYLOAD-DEJITTER-INFO {
    description
      "CEM PAYLOAD DEJITTER INFO";
    leaf payload {
      type uint32;
      description
        "Payload";
    }
    list dejitter-array {
      description
        "Dejitter array";
      leaf entry {
        type uint32;
        description
          "Dejitter array";
      }
    }
  }

  grouping CEM-PAYLOAD-DEJITTER-MAPPING-INFO {
    description
      "CEM payload dejitter mapping information";
    leaf client-type {
      type Cem-ac-client-types;
      description
        "Client type";
    }
    leaf client-rate {
      type uint32;
      units "kbit/s";
      description
        "Client Rate in kbps";
    }
    leaf default-payload-size {
      type uint32;
      description
        "Default payload Size";
    }
    leaf default-dejitt-buffer-length {
      type uint32;
      description
        "Default Dejitter buffer length";
    }
    list payload-dejitter-info {
      description
        "Payload Dejitter Info";
      uses CEM-PAYLOAD-DEJITTER-INFO;
    }
  }

  grouping CEM-AC-CLIENT-BAG-INFO {
    description
      "CEM AC CLIENT BAG INFO";
    leaf attachment-circuit-client-type {
      type Cem-ac-client-types;
      description
        " Attachment Circuit Client type";
    }
    leaf attachment-circuit-client-rate {
      type uint32;
      description
        " Attachment Circuit Client rate";
    }
  }

  grouping CEM-PLOAD-DJB-SIZE-BAG-INFO {
    description
      "CEM PLOAD DJB SIZE BAG INFO";
    leaf maximum-payload-for-dejitter-buffer-size-in-block-range {
      type uint32;
      description
        "Max Payload for dejitter buffer size in block
         range";
    }
    leaf minimum-dejitter-buffer-size-in-blocks {
      type uint32;
      description
        "Mininum Dejitter buffer size in blocks";
    }
    leaf maximum-dejitter-buffer-size-in-blocks {
      type uint32;
      description
        "Maximum Dejitter buffer size in blocks";
    }
    leaf multiple-factor {
      type uint32;
      description
        "Multiple factor";
    }
  }

  grouping CEM-CLIENT-CAPABILITIES-INFO {
    description
      "CEM client capabilities info";
    container attachment-circuit-client-info {
      description
        "Attachment Circuit Client info";
      uses CEM-AC-CLIENT-BAG-INFO;
    }
    leaf internal-parent-interface-name {
      type string;
      description
        "Internal parent Interface name";
    }
    leaf internal-parent-interface-handle {
      type uint32;
      description
        "Internal parent interface handle";
    }
    leaf rtp-default-enabled {
      type boolean;
      description
        "RTP default enabled";
    }
    leaf clock-type {
      type Cem-recovered-clock;
      description
        "Clock type";
    }
    leaf default-payload-size {
      type uint32;
      description
        "Default payload Size";
    }
    leaf minimum-payload-size {
      type uint32;
      description
        "Minimum payload size";
    }
    leaf maximum-payload-size {
      type uint32;
      description
        "Maximum payload size";
    }
    leaf payload-incremental-value {
      type uint32;
      description
        "Payload incremental value";
    }
    leaf default-dejitter-buffer-length {
      type uint32;
      description
        "Default Dejitter buffer length";
    }
    leaf minimum-dejitter-buffer-length {
      type uint32;
      description
        "Minimum Dejitter buffer length";
    }
    leaf maximum-dejitter-buffer-length {
      type uint32;
      description
        "Maximum Dejitter buffer length";
    }
    leaf default-idle-pattern {
      type uint32;
      description
        "Default idle pattern";
    }
    leaf default-dummy-pattern {
      type uint32;
      description
        "Default dummy pattern";
    }
    leaf default-dummy-mode {
      type uint32;
      description
        "Default dummy mode";
    }
    leaf is-payload-dejitter-buffer-size-info-valid {
      type boolean;
      description
        "Is Payload Dejitter Buffer size info valid";
    }
    list payload-dejitter-buffer-size-info {
      description
        "Payload Dejitter Buffer size info";
      uses CEM-PLOAD-DJB-SIZE-BAG-INFO;
    }
  }

  grouping CEM-ALARM-INFO {
    description
      "CEM Alarm info";
    leaf is-detected {
      type boolean;
      description
        "Is defect detected?";
    }
    leaf count {
      type uint64;
      description
        "Alarm count";
    }
  }

  grouping CEM-ENDPT-INFO {
    description
      "CEM endpoint info";
    leaf endpoint-string-type {
      type Cem-end-point-str;
      description
        "Endpoint String type";
    }
    leaf endpoint-string {
      type string {
        length "0..129";
      }
      description
        "Endpoint String";
    }
  }

  grouping CEM-INFO {
    description
      "CEM controller information";
    container endpoint-send-info {
      description
        "Endpoint Send Info";
      uses CEM-ENDPT-INFO;
    }
    container endpoint-expected-info {
      description
        "Endpoint Expected Info";
      uses CEM-ENDPT-INFO;
    }
    container endpoint-received-info {
      description
        "Endpoint Received Info";
      uses CEM-ENDPT-INFO;
    }
    container local-attachment-circuit-fault {
      description
        "Local Attachment Circuit Fault";
      uses CEM-ALARM-INFO;
    }
    container remote-attachment-circuit-fault {
      description
        "Remote Attachment Circuit Fault, L-bit Received
         in the control word";
      uses CEM-ALARM-INFO;
    }
    container local-lops {
      description
        "Local Loss of Packets State(LOPS)";
      uses CEM-ALARM-INFO;
    }
    container remote-lops {
      description
        "Remote Loss Of Packets State(LOPS), R-bit
         received in the control word";
      uses CEM-ALARM-INFO;
    }
    leaf admin-state {
      type Cem-interface-state;
      description
        "Administrative state";
    }
    leaf oper-state {
      type Cem-interface-state;
      description
        "Operational state";
    }
    leaf bandwidth {
      type uint32;
      units "kbit/s";
      description
        "Bandwidth in kbps";
    }
    leaf configured-dejitter-buffer-length {
      type uint32;
      units "microsecond";
      description
        "Configured dejitter buffer length in
         microseconds";
    }
    leaf operational-dejitter-buffer-length {
      type uint32;
      units "microsecond";
      description
        "Operational dejitter buffer length in
         microseconds";
    }
    leaf dejitter-buffer-length-in-use {
      type uint32;
      description
        "Dejitter buffer length In Use";
    }
    leaf configured-payload-size {
      type uint16;
      units "byte";
      description
        "Configured payload size in bytes";
    }
    leaf operational-payload-size {
      type uint16;
      units "byte";
      description
        "Operational payload size in bytes";
    }
    leaf minimum-packet-delay-variation {
      type uint32;
      description
        "Minimum packet delay variation";
    }
    leaf maximum-packet-delay-variation {
      type uint32;
      description
        "Maximum packet delay variation";
    }
    leaf average-packet-delay-variation {
      type uint32;
      description
        "Average packet delay variation";
    }
    leaf packet-loss-timer {
      type uint32;
      units "millisecond";
      description
        "Packet loss timer value in milliseconds";
    }
    leaf dummy-mode {
      type Cem-dummy-mode;
      description
        "Dummy mode";
    }
    leaf dummy-pattern {
      type yang:hex-string;
      description
        "Dummy pattern";
    }
    leaf idle-pattern {
      type yang:hex-string;
      description
        "Idle pattern";
    }
    leaf signalling {
      type Cem-signalling;
      description
        "Signalling";
    }
    leaf rtp-enabled {
      type Cem-rtp;
      description
        "RTP enabled or not";
    }
    leaf clock-type {
      type Cem-recovered-clock;
      description
        "Clock Type";
    }
    leaf pass-through-node {
      type boolean;
      description
        "Pass through node";
    }
    leaf packet-replace-policy {
      type Cem-packet-replace-policy;
      description
        "Packet Replace policy";
    }
    leaf number-of-consecutive-missing-packets-to-enter-lops-state {
      type uint64;
      description
        "Number of Consecutive Missing Packets to enter
         LOPS state";
    }
    leaf number-of-consecutive-missing-packets-to-exit-lops-state {
      type uint64;
      description
        "Number of Consecutive Missing Packets to exit
         LOPS state";
    }
    leaf ingress-packets {
      type uint64;
      description
        "Ingress packets";
    }
    leaf ingress-drop-packets {
      type uint64;
      description
        "Ingress dropped packets";
    }
    leaf egress-packets {
      type uint64;
      description
        "Egress packets";
    }
    leaf egress-drop-packets {
      type uint64;
      description
        "Egress dropped packets";
    }
    leaf missing-packets {
      type uint64;
      description
        "Missing packets";
    }
    leaf reordered-packets {
      type uint64;
      description
        "Reordered packets";
    }
    leaf frames-fragmented {
      type uint64;
      description
        "Frames Fragmented";
    }
    leaf total-error-count {
      type uint64;
      description
        "Total Error count";
    }
    leaf malformed-packets {
      type uint64;
      description
        "Malformed packets";
    }
    leaf misordered-drops {
      type uint64;
      description
        "Misorder drops";
    }
    leaf jitter-buffer-under-runs {
      type uint64;
      description
        "Jitter buffer underruns";
    }
    leaf jitter-buffer-over-runs {
      type uint64;
      description
        "Jitter buffer Overruns";
    }
    leaf errored-seconds {
      type uint64;
      units "second";
      description
        "Number of errored seconds";
    }
    leaf severely-errored-seconds {
      type uint64;
      units "second";
      description
        "Number of severely errored secs";
    }
    leaf unavailable-seconds {
      type uint64;
      units "second";
      description
        "Number of Unavailable seconds";
    }
    leaf failure-counts {
      type uint64;
      description
        "Failure counts";
    }
  }
}
