module Cisco-IOS-XR-bfd-hw-offload-oper {
  namespace "http://cisco.com/ns/yang/Cisco-IOS-XR-bfd-hw-offload-oper";
  prefix bfd-hw-offload-oper;

  import cisco-semver {
    prefix semver;
  }
  include Cisco-IOS-XR-bfd-hw-offload-oper-sub1 {
    revision-date 2026-05-26;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR bfd-hw-offload package operational data.
     
     This module contains definitions
     for the following management objects:
       bfdhw-offload: BFD Hardware Offload operational data
     
     Copyright (c) 2013-2026 by Cisco Systems, Inc.
     All rights reserved.";

  revision 2026-05-26 {
    description
      "Added OFA info per-session summary with last packet and SDK object details";
    semver:module-version "1.0.0";
  }
  revision 2026-05-15 {
    description
      "Added VOQ usage operational data support for BFD HW offload sessions";
  }
  revision 2026-03-13 {
    description
      "Added session summary oper support with NPU and LC offload resource usage details";
  }
  revision 2026-03-09 {
    description
      "Added session summary statistics for NPU and LC offload resources";
  }
  revision 2026-02-08 {
    description
      "Initial version for BFD HW Offload operational data";
  }
  revision 2019-04-05 {
    description
      "Establish semantic version baseline.";
  }
  revision 2015-11-09 {
    description
      "IOS XR 6.0 revision.";
  }

  container bfdhw-offload {
    config false;
    description
      "BFD Hardware Offload operational data";
    container voq-usages {
      description
        "Table of BFD HW offload VOQ usage";
      list voq-usage {
        key "discriminator";
        description
          "BFD HW offload VOQ usage information";
        leaf discriminator {
          type uint32;
          description
            "Session discriminator";
        }
        uses BFD-HW-OFFLOAD-EDM-VOQ-USAGE;
      }
    }
    container ofa-infos {
      description
        "Table of BFD HW offload OFA session info";
      list ofa-info {
        key "discriminator";
        description
          "BFD HW offload OFA object info for a single
           session";
        leaf discriminator {
          type uint32;
          description
            "Session discriminator";
        }
        uses BFD-HW-OFFLOAD-EDM-OFA-INFO;
      }
    }
    container states {
      description
        "Table of BFD HW offload session states";
      list state {
        key "discriminator";
        description
          "BFD HW offload session state information";
        leaf discriminator {
          type uint32;
          description
            "Session discriminator";
        }
        uses BFD-HW-OFFLOAD-EDM-STATE;
      }
    }
  }
}
