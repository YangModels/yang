submodule Cisco-IOS-XR-icpe-infra-oper-sub9 {
  belongs-to Cisco-IOS-XR-icpe-infra-oper {
    prefix Cisco-IOS-XR-icpe-infra-oper;
  }

  import cisco-semver {
    prefix semver;
  }
  include Cisco-IOS-XR-icpe-infra-oper-sub4 {
    revision-date 2026-04-22;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR icpe-infra package operational data.
     
     Copyright (c) 2013-2026 by Cisco Systems, Inc.
     All rights reserved.";

  revision 2026-04-22 {
    description
      "Add Controller Optics FC data";
    semver:module-version "1.2.0";
  }
  revision 2024-09-06 {
    description
      "Use 64 bit number for timestamps";
    semver:module-version "1.1.0";
  }
  revision 2019-04-05 {
    description
      "Establish semantic version baseline.";
    semver:module-version "1.0.1";
  }
  revision 2015-11-09 {
    description
      "IOS XR 6.0 revision.";
  }

  grouping ICPE-GCO-PRIORITY-OPER-TYPE {
    description
      "Satellite priority information";
    leaf satellite-id-xr {
      type uint16;
      description
        "Satellite ID";
    }
    leaf rgid {
      type uint32;
      description
        "RG ID";
    }
    leaf best-path-hops {
      type uint32;
      description
        "Best path hops";
    }
    leaf configured-priority {
      type uint8;
      description
        "Configured priority";
    }
    leaf host-priority {
      type uint64;
      description
        "Host priority";
    }
    leaf partner-priority {
      type uint64;
      description
        "Partner priority";
    }
    leaf multichassis-redundancy {
      type Icpe-oper-multichassis-redundancy;
      description
        "Multichassis redundancy";
    }
  }
}
