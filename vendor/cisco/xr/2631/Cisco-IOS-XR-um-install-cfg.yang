module Cisco-IOS-XR-um-install-cfg {
  yang-version 1.1;
  namespace "http://cisco.com/ns/yang/Cisco-IOS-XR-um-install-cfg";
  prefix um-install-cfg;

  import Cisco-IOS-XR-um-types {
    prefix um-types;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions for Cisco IOS-XR
     Install configuration.
     
     Copyright (c) 2021-2026 by Cisco Systems, Inc., and/or its affiliates.
     All rights reserved.";

  revision 2026-03-25 {
    description
      "Update to align with latest IOS-XR YANG quality guidelines.";
    semver:module-version "3.0.0";
  }
  revision 2025-11-21 {
    description
      "Deprecated support for remote repositories (FTP, HTTP, and HTTPS URLs)
       2023-07-27
          Added 'enable' leaf to fingerprints config
       2022-07-14
          Added support for fingerprints frequency never
       2022-03-10
          Added configuration for RPM fingerprinting
       2022-01-19
          Updated length of url and description nodes";
    semver:module-version "2.0.0";
  }
  revision 2021-02-04 {
    description
      "Initial release";
    semver:module-version "1.0.0";
  }

  container install {
    description
      "Install configuration";
    container repositories {
      description
        "Per repository configuration";
      list repository {
        key "id";
        description
          "Per repository configuration";
        leaf id {
          type um-types:restricted-string {
            length "min..80";
            pattern "[-_.:A-Za-z0-9]+";
          }
          description
            "Repository ID (up to 80 characters)";
        }
        leaf url {
          type um-types:extended-restricted-string {
            length "min..900";
          }
          mandatory true;
          description
            "Repository URL.
             
             Path to local repository or directory or ftp, http, or https path
             to remote repository, optionally containing the name of a VRF for
             the repository.
             
             Must take one of the following forms:
             
             ftp://<server>[;<vrf>]/<full_path_to_repo>   -> FTP repository
             http://<server>[;<vrf>]/<full_path_to_repo>  -> HTTP repository
             https://<server>[;<vrf>]/<full_path_to_repo> -> HTTPS repository
             file:///<full_path_to_repo> -> Local file repository or directory.
                                            This must be a subdirectory of one
                                            of '/var/xr/disk1/', '/harddisk:/',
                                            or '/misc/disk1/'.
             
             Remote (FTP/HTTP/HTTPS) repositories are deprecated in 26.1.1.";
        }
        leaf description {
          type um-types:extended-freeform-string {
            length "min..900";
          }
          description
            "Description of this repository";
        }
      }
    }
    container fingerprints {
      presence "Enables RPM fingerprinting.";
      description
        "RPM fingerprinting configuration";
      leaf frequency {
        type uint8 {
          range "1..12";
        }
        units "hours";
        default "12";
        description
          "RPM fingerprint generation frequency.";
      }
    }
  }
}
