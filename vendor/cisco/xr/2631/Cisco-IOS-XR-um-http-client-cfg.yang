module Cisco-IOS-XR-um-http-client-cfg {
  yang-version 1.1;
  namespace "http://cisco.com/ns/yang/Cisco-IOS-XR-um-http-client-cfg";
  prefix um-http-client-cfg;

  import Cisco-IOS-XR-um-types {
    prefix um-types;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions for Cisco IOS-XR
     HTTP/HTTPS Client configuration.
     
     Copyright (c) 2020-2026 by Cisco Systems, Inc., and/or its affiliates.
     All rights reserved.";

  revision 2026-04-22 {
    description
      "Update to align with latest IOS-XR YANG quality guidelines.
       2026-04-13
         Removed TLSv1.0 and TLSv1.1 containers in YANG, as these versions are removed in libcurl 26.3.1";
    semver:module-version "2.0.0";
  }
  revision 2025-08-13 {
    description
      "Changed help string for tls1.1 and tls1.0 to indicate that they are deprecated
       2024-06-18
          Added tls1.3 option
       2023-08-01
          Added tcp-window-scale cli
       2022-02-10
          - Added secure-verify-peer and secure-verify-host. Updated ipv4 and ipv6 under source-interface";
    semver:module-version "1.1.0";
  }
  revision 2020-09-22 {
    description
      "Initial release";
    semver:module-version "1.0.0";
  }

  container http {
    description
      "HTTP Application";
    container client {
      description
        "HTTP Client Application";
      leaf vrf {
        type um-types:vrf-name;
        default "default";
        description
          "The name of the VRF to be used by the HTTP client";
      }
      container secure-verify-peer {
        description
          "Verify authenticity of the peer's certificate";
        leaf disable {
          type empty;
          description
            "Disable verifying peer's certificate";
        }
      }
      container secure-verify-host {
        description
          "Verify host in peer's certificate.";
        leaf disable {
          type empty;
          description
            "Disable verifying host in peer's certificate";
        }
      }
      container response {
        description
          "How long HTTP Client waits for a response from the server
           for a request message before giving up";
        leaf timeout {
          type uint16 {
            range "1..300";
          }
          units "seconds";
          default "30";
          description
            "Response timeout";
        }
      }
      container connection {
        description
          "HTTP Client connection configuration";
        leaf timeout {
          type uint8 {
            range "1..60";
          }
          units "seconds";
          default "10";
          description
            "How long HTTP Client waits for a server connection to
             establish before giving up";
        }
        leaf retry {
          type uint8 {
            range "1..5";
          }
          description
            "Number of times HTTP Client retries a connection request
             upon connection failure";
        }
      }
      container source-interface {
        description
          "The interface(s) from which HTTP client obtains its IPv4/IPv6
           source address";
        leaf ipv4 {
          type um-types:interface-name;
          description
            "Use the interface's IPv4 address";
        }
        leaf ipv6 {
          type um-types:interface-name;
          description
            "Use the interface's IPv6 address";
        }
      }
      leaf version {
        type enumeration {
          enum "default" {
            description
              "libcurl will pick HTTP version automatically";
          }
          enum "1.0" {
            description
              "Force HTTP1.0 to be used for all HTTP requests";
          }
          enum "1.1" {
            description
              "Force HTTP1.1 to be used for all HTTP requests";
          }
        }
        default "default";
        description
          "HTTP version to be used in HTTP requests";
        reference
          "RFC 1945 - Hypertext Transfer Protocol -- HTTP/1.0
           RFC 2616 - Hypertext Transfer Protocol -- HTTP/1.1";
      }
      leaf tcp-window-scale {
        type uint8 {
          range "1..14";
        }
        description
          "TCP window scale factor for high latency links";
      }
      container ssl {
        description
          "SSL configuration to be used for HTTPS requests";
        leaf version {
          type enumeration {
            enum "tls1.2" {
              description
                "Force TLSv1.2 to be used for HTTPS requests";
            }
            enum "tls1.3" {
              description
                "Force TLSv1.3 to be used for HTTPS requests";
            }
          }
          description
            "SSL version to be used for HTTPS requests";
          reference
            "RFC 5246 - The Transport Layer Security (TLS) Protocol Version 1.2
             RFC 8446 - The Transport Layer Security (TLS) Protocol Version 1.3";
        }
      }
    }
  }
}
