module Cisco-IOS-XR-infra-smartlicense-oper {
  namespace "http://cisco.com/ns/yang/Cisco-IOS-XR-infra-smartlicense-oper";
  prefix infra-smartlicense-oper;

  import cisco-semver {
    prefix semver;
  }
  include Cisco-IOS-XR-infra-smartlicense-oper-sub1 {
    revision-date 2019-04-05;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR infra-smartlicense package operational data.
     
     This module contains definitions
     for the following management objects:
       smart-agent: Information of Smart License list and operations
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  container smart-agent {
    config false;
    description
      "Information of Smart License list and operations";
    container licensing {
      description
        "Smart Licensing Module Information";
      uses SMARTAGENT-LICENSING-INFO;
    }
  }
}
