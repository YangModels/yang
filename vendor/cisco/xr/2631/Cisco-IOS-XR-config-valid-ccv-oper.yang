module Cisco-IOS-XR-config-valid-ccv-oper {
  namespace "http://cisco.com/ns/yang/Cisco-IOS-XR-config-valid-ccv-oper";
  prefix config-valid-ccv-oper;

  import cisco-semver {
    prefix semver;
  }
  import Cisco-IOS-XR-config-cfgmgr-oper {
    prefix a1;
  }
  include Cisco-IOS-XR-config-valid-ccv-oper-sub2 {
    revision-date 2026-07-02;
  }
  include Cisco-IOS-XR-config-valid-ccv-oper-sub1 {
    revision-date 2026-07-02;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR config-valid-ccv package operational data.
     
     This YANG module augments the
       Cisco-IOS-XR-config-cfgmgr-oper
     module with state data.
     
     Copyright (c) 2013-2026 by Cisco Systems, Inc.
     All rights reserved.";

  revision 2026-07-02 {
    description
      "Remove deprecated nodes specific to commit check.";
    semver:module-version "3.0.0";
  }
  revision 2021-06-16 {
    description
      "Deprecate nodes specific to commit check.";
    semver:module-version "2.1.0";
  }
  revision 2020-09-14 {
    description
      "Added Config Scripts operational data support.";
    semver:module-version "2.0.0";
  }
  revision 2019-04-05 {
    description
      "Establish semantic version baseline.";
    semver:module-version "1.0.1";
  }
  revision 2015-11-09 {
    description
      "IOS XR 6.0 revision.";
  }

  grouping CALLBACK-TABLE {
    description
      "Common node of last-validation, running-config";
    container callbacks {
      description
        "Execution information for callbacks registered
         by config scripts";
      list callback {
        key "script-name callback-name";
        description
          "Information about execution of a config
           script's callback";
        leaf script-name {
          type string;
          description
            "Script name";
        }
        leaf callback-name {
          type string;
          description
            "Callback name";
        }
        uses CCV-SCRIPT-EXECUTION-INFO-ITEM-BAG;
      }
    }
  }

  grouping SCRIPT-TABLE {
    description
      "Common node of last-validation, running-config";
    container scripts {
      description
        "Execution information for configured config
         scripts";
      list script {
        key "script-name";
        description
          "Information about execution of a config script";
        leaf script-name {
          type string;
          description
            "Script name";
        }
        uses CCV-SCRIPT-EXECUTION-INFO-ITEM-BAG;
      }
    }
  }

  augment "/a1:config/a1:global" {
    description
      "This augment extends the operational data of
       'Cisco-IOS-XR-config-cfgmgr-oper'";
    container validation {
      description
        "Configuration validation operational data";
      container persistent-failures {
        description
          "Validation failures present in running
           configuration";
        list persistent-failure {
          key "xpath";
          description
            "Information about a validation failure";
          leaf xpath {
            type string;
            description
              "XPath of the failed configuration";
          }
          uses CCV-YVE-VALIDATION-FAILURE-ITEM-BAG;
        }
      }
      container script-execution {
        description
          "Script execution operational data";
        container last-validation {
          description
            "Operational data for script execution in the
             last validation";
          uses SCRIPT-TABLE;
          uses CALLBACK-TABLE;
        }
        container running-config {
          description
            "Operational data for script execution against
             currently running config";
          uses SCRIPT-TABLE;
          uses CALLBACK-TABLE;
        }
      }
    }
  }
}
