submodule Cisco-IOS-XR-pbr-fwd-stats-oper-sub2 {
  belongs-to Cisco-IOS-XR-pbr-fwd-stats-oper {
    prefix Cisco-IOS-XR-pbr-fwd-stats-oper;
  }

  import cisco-semver {
    prefix semver;
  }
  include Cisco-IOS-XR-pbr-fwd-stats-oper-sub1 {
    revision-date 2025-01-16;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR pbr-fwd-stats package operational data.
     
     Copyright (c) 2013-2025 by Cisco Systems, Inc.
     All rights reserved.";

  revision 2025-01-16 {
    description
      "Stats feature update to support match rules";
    semver:module-version "1.1.0";
  }
  revision 2024-09-11 {
    description
      "Stats feature update";
  }
  revision 2024-05-08 {
    description
      "CSCwj03306 : Meta EBB - PBR Stats feature";
  }
  revision 2019-04-05 {
    description
      "Establish semantic version baseline.";
  }
  revision 2015-11-09 {
    description
      "IOS XR 6.0 revision.";
  }

  typedef Policy-sl-action {
    type enumeration {
      enum "path-grp" {
        value 1;
        description
          "path grp";
      }
      enum "stats" {
        value 2;
        description
          "stats";
      }
    }
    description
      "PBR sl policy actions";
  }

  typedef Path-group-name {
    type string {
      length "0..128";
    }
    description
      "Path group name";
  }

  typedef Policy-sl-match {
    type enumeration {
      enum "path-grp" {
        value 1;
        description
          "path grp";
      }
      enum "dscp" {
        value 2;
        description
          "dscp";
      }
    }
    description
      "PBR sl policy matches";
  }

  grouping POLICY-ACTION-UN {
    description
      "Union of actions";
    leaf type {
      type Policy-sl-action;
      description
        "type";
    }
    leaf stats-enabled {
      when "../type = 'stats'" {
        description
          "../type = 'Stats'";
      }
      type uint32;
      description
        "Stats Enabled";
    }
    leaf path-grp-name {
      when "../type = 'path-grp'" {
        description
          "../type = 'PATH_GRP'";
      }
      type Path-group-name;
      description
        "PathGrpName";
    }
  }

  grouping POLICY-MATCH-UN {
    description
      "Union of matches";
    leaf type {
      type Policy-sl-match;
      description
        "type";
    }
    leaf path-grp-name {
      when "../type = 'path-grp'" {
        description
          "../type = 'PATH_GRP'";
      }
      type Path-group-name;
      description
        "PathGrpName";
    }
    leaf dscp {
      when "../type = 'dscp'" {
        description
          "../type = 'Dscp'";
      }
      type uint32;
      description
        "Dscp";
    }
  }

  grouping PBR-POLICY-RULE-STATS {
    description
      "policy map rule stats info";
    container fib-stats {
      description
        "fib stats";
      uses FIB-INSIGHT-FWD-STATS;
    }
    list match {
      description
        "match";
      uses POLICY-MATCH-UN;
    }
    list action {
      description
        "action";
      uses POLICY-ACTION-UN;
    }
  }
}
