module Cisco-IOS-XR-health-oper {
  namespace "http://cisco.com/ns/yang/Cisco-IOS-XR-health-oper";
  prefix health-oper;

  import Cisco-IOS-XR-types {
    prefix xr;
  }
  import cisco-semver {
    prefix semver;
  }
  include Cisco-IOS-XR-health-oper-sub1 {
    revision-date 2026-02-27;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR health package operational data.
     
     This module contains definitions
     for the following management objects:
       health: health operational data.
     
     Copyright (c) 2013-2026 by Cisco Systems, Inc.
     All rights reserved.";

  revision 2026-02-27 {
    description
      "Moved existing data to a new status container and created new providers container for health provider augmented yang";
    semver:module-version "2.0.0";
  }
  revision 2025-09-22 {
    description
      "Added more fields to the Health component information";
    semver:module-version "1.0.0";
  }
  revision 2025-03-12 {
    description
      "Updated data type to enum for health status to make it descriptive";
  }
  revision 2024-05-29 {
    description
      "Initial native yang support for operational data related to Health functionality";
  }
  revision 2019-04-05 {
    description
      "Establish semantic version baseline.";
  }
  revision 2015-11-09 {
    description
      "IOS XR 6.0 revision.";
  }

  container health {
    config false;
    description
      "health operational data.";
    container components {
      description
        "List of components that have received health
         updates. Components not listed must be
         considered healthy.";
      list component {
        key "name";
        description
          "Individual Component.";
        container state {
          description
            "Component health state data (where component
             is any named entity within the device that can
             have a health declaration made for it)";
          uses XRHEALTH-STATE;
        }
        container providers {
          description
            "Providers container. Used for augmentation by
             health providers.";
        }
        leaf name {
          type xr:Cisco-ios-xr-string;
          description
            "Component name";
        }
      }
    }
  }
}
