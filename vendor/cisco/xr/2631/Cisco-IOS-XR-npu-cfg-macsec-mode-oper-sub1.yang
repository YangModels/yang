submodule Cisco-IOS-XR-npu-cfg-macsec-mode-oper-sub1 {
  belongs-to Cisco-IOS-XR-npu-cfg-macsec-mode-oper {
    prefix Cisco-IOS-XR-npu-cfg-macsec-mode-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR npu-cfg-macsec-mode package operational data.
     
     Copyright (c) 2013-2022 by Cisco Systems, Inc.
     All rights reserved.";

  revision 2022-06-30 {
    description
      "Yang Schema added MACSEC Mode";
    semver:module-version "1.0.0";
  }
  revision 2019-04-05 {
    description
      "Establish semantic version baseline.";
  }
  revision 2015-11-09 {
    description
      "IOS XR 6.0 revision.";
  }

  grouping MACSEC-MODE-INFO {
    description
      "macsec_mode info";
    leaf location {
      type string;
      description
        "macsec-mode location";
    }
    leaf configured {
      type string;
      description
        "macsec-mode is configured or not";
    }
    leaf running {
      type string;
      description
        "macsec-mode is running or not";
    }
    leaf action {
      type string;
      description
        "next required action";
    }
  }
}
