submodule Cisco-IOS-XR-sandbox-oper-sub1 {
  belongs-to Cisco-IOS-XR-sandbox-oper {
    prefix Cisco-IOS-XR-sandbox-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR sandbox package operational data.
     
     Copyright (c) 2013-2023 by Cisco Systems, Inc.
     All rights reserved.";

  revision 2023-07-28 {
    description
      "Modified Brief and Detail class pathname";
    semver:module-version "1.0.0";
  }
  revision 2023-07-27 {
    description
      "Added yang support to publish list of RPMs";
  }
  revision 2023-06-12 {
    description
      "Added support to publish list of RPMs and brief logs, detailed logs container renamed";
  }
  revision 2023-05-26 {
    description
      "Support added to list inner rpms and logs";
  }
  revision 2022-07-08 {
    description
      "sandbox show CLI added";
  }
  revision 2019-04-05 {
    description
      "Establish semantic version baseline.";
  }
  revision 2015-11-09 {
    description
      "IOS XR 6.0 revision.";
  }

  typedef Config-state {
    type enumeration {
      enum "disabled" {
        value 0;
        description
          "Sandbox disabled";
      }
      enum "enabled" {
        value 1;
        description
          "Sandbox enabled";
      }
      enum "unknown" {
        value 2;
        description
          "unknown";
      }
    }
    description
      "Sandbox Config State";
  }

  grouping SANDBOXMGR-SERVICES {
    description
      "SANDBOXMGR SERVICES";
    leaf output {
      type string {
        length "0..8000";
      }
      description
        "App Services";
    }
  }

  grouping SANDBOXMGR-RPMS-MDATA {
    description
      "Installed RPMs info";
    leaf index {
      type uint32;
      description
        "Index of installed RPMs";
    }
    leaf name {
      type string;
      description
        "Name of installed RPMs";
    }
    leaf version {
      type string;
      description
        "Version of installed RPMs";
    }
  }

  grouping SANDBOXMGR-RPMDETAILS {
    description
      "Installed RPMs Data structure";
    leaf count {
      type uint32;
      description
        "Count of installed RPMs";
    }
    leaf state {
      type Config-state;
      description
        "Configuration state of sandbox";
    }
    list rpm {
      description
        "Installed RPMs info array";
      uses SANDBOXMGR-RPMS-MDATA;
    }
  }

  grouping SANDBOXMGR-RPMINSTDETLOGS {
    description
      "SANDBOXMGR RPMINSTDETLOGS";
    leaf state {
      type Config-state;
      description
        "Configuration state sandbox";
    }
    leaf logs {
      type string;
      description
        "RPM install detailed trace";
    }
  }

  grouping SANDBOXMGR-RPMINSTLOGS {
    description
      "SANDBOXMGR RPMINSTLOGS";
    leaf state {
      type Config-state;
      description
        "Configuration state sandbox";
    }
    leaf logs {
      type string;
      description
        "RPM install trace";
    }
  }

  grouping SANDBOXMGR-STATS-INTERNAL-INFO {
    description
      "Container Statistics";
    leaf cpu-percentage {
      type string;
      units "percentage";
      description
        "CPU percentage";
    }
    leaf memory-usage {
      type string;
      description
        "Memory usage";
    }
    leaf net-io {
      type string;
      description
        "Net Io";
    }
    leaf block-io {
      type string;
      description
        "Block Io";
    }
    leaf mem-percentage {
      type string;
      units "percentage";
      description
        "Memory percentage";
    }
    leaf pids {
      type string;
      description
        "process PIDs";
    }
  }

  grouping SANDBOXMGR-DETAILS {
    description
      "SANDBOXMGR DETAILS";
    container app-info {
      description
        "app info";
      uses SANDBOXMGR-INTERNAL-INFO;
    }
    container stats-info {
      description
        "stats info";
      uses SANDBOXMGR-STATS-INTERNAL-INFO;
    }
    leaf state {
      type Config-state;
      description
        "Configuration state sandbox";
    }
  }

  grouping SANDBOXMGR-INTERNAL-INFO {
    description
      "Sandbox app internal info";
    leaf error-string {
      type string;
      description
        "App error string";
    }
    leaf state {
      type Config-state;
      description
        "Configuration state sandbox";
    }
    leaf app-config-state {
      type string;
      description
        "App config state";
    }
    leaf container-state {
      type string;
      description
        "App container state";
    }
    leaf image {
      type string;
      description
        "Image";
    }
    leaf run-options {
      type string;
      description
        "Run Options";
    }
  }
}
