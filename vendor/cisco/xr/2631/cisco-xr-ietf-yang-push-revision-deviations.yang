module cisco-xr-ietf-yang-push-revision-deviations {
  namespace "http://cisco.com/ns/yang/cisco-xr-ietf-yang-push-revision-deviations";
  prefix xr-ypr-d;

  import ietf-yang-push-revision {
    prefix ypr;
  }

  import ietf-subscribed-notifications {
    prefix sn;
  }

  organization "Cisco Systems, Inc.";

  contact
    "Cisco Systems, Inc.
     Customer Service

     Postal: 170 West Tasman Drive
     San Jose, CA 95134

     Tel: +1 800 553-NETS

     E-mail: cs-yang@cisco.com";

  description
    "This module contains a set of 'not-supported' deviations of:

        ietf-yang-push-revision@2025-08-29

     on Cisco IOS-XR devices.

     Copyright (c) 2025-2026 by Cisco Systems, Inc., and/or its affiliates.
     All rights reserved.";

  revision 2026-01-08 {
    description
      "Updates to support ietf-yang-push-revision@2025-08-29.";
  }

  revision 2025-01-20 {
    description
      "Initial version.";
  }

  /*
   * If in the future this deviations file only contains RPC or notification
   * nodes, it will stop appearing in Yang Library or capabilities/hello
   * output.
   * See CSCwn84289 for more details. This comment can be removed once the
   * issue is resolved.
   */

  // Support for version labels will be added in future.
  deviation /sn:subscriptions/sn:subscription/ypr:module-version-subs/ypr:revision-version/ypr:version {
    deviate not-supported;
  }

  // Remove the bits of the subscription started notification we don't support.
  deviation /sn:subscription-started/ypr:module-version/ypr:version {
    deviate not-supported;
  }
}
