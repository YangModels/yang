module Cisco-IOS-XR-um-hw-module-profile-cfg {
  namespace "http://cisco.com/ns/yang/Cisco-IOS-XR-um-hw-module-profile-cfg";
  prefix um-hw-module-profile-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR hw-module-profile package configuration.
     
     This YANG module augments the
     modules with configuration data.
     
     Copyright (c) 2021-2026 by Cisco Systems, Inc., and/or its affiliates.
     All rights reserved.";

  revision 2026-06-19 {
    description
      "Corrected the UDF name length field for fia_cfg key-format leaves
       2026-01-30
         Added container for qos egress-exp-mark-disable";
    semver:module-version "4.0.0";
  }
  revision 2025-08-18 {
    description
      "Added container bgp-pic/level-3/l2services to enable BGP PIC LEVEL-3 L2SERVICES
       2025-08-04
          Fixed yang-canonical error
       2025-04-25
          Added container for MPLS PHP DSCP preserve
       2025-03-20
          Added container QOS FADT CLI
       2025-02-04
          Added container bgp-pic/level-3/evpn to enable BGP PIC LEVEL-3 EVPN
       2025-01-20
          Added hw-module profile mdb l3max-srv6, l2max-srv6, l3max-se-srv6, l2max-se-srv6
       2024-10-15
          Added bgp-ip/if-peering/collapse to enable BGP interface peering collapse
       2024-06-17
          Added container for ttl/cos exception of ipttl-propagate-disable for mpls flow
       2024-06-07
          Added recycle bandwidth hw-module configuration support for li
       2024-04-09
          Updated description for ttl-match and interface-based, fixed typo in manditory
       2024-03-30
          Added container for FAT Based LB Profile
       2024-03-20
          Added container for etm-low-rate-connector to reserve connector range
       2024-03-06
          Added container for disable-trap
       2024-01-08
          Added container for PPPoE LB Profile
       2023-12-12
          Added container for policy-map-extend option in SRV6 CLI
       2023-08-30
          Added leaf hash-poly-index
       2023-06-22
          Added container lag-scheduler
       2023-05-19
          Added container bgp-mp-pic auto-protect enable
       2023-05-04
          Added container srv6 microsegment f3216 path-mtu
       2023-03-03
          Added container egress-compensation-setting-force
       2023-02-24
          Added container mpls-ext-dscp-preserve-v6
       2023-02-02
          Removed second location from hw-module profile tcam format access-list
       2023-01-31
          Added container for core replication optimization
       2023-01-05
          Modified max-class-size, ingress peering
        qosg-dscp-mark-enable, hqos-enable,
        wred-stats-enable, policer-scale,
        nif-hp-fifo-reserve and
        Added physical-hqos-enable
       2022-12-14
          Added container l2pt-extended-protocols-enable
       2022-11-26
          Added irb-recycle-bandwidth hw-module support under profile-qos
       2022-11-23
          Added new containers bgppa and stats-mode under it
       2022-11-13
          Added new container two-label-tcam-optimized under hw-module
       2022-10-17
          Added new enum value under leaf max-classmap-size
       2022-09-20
          Added new containers bgp-sr, ttl and urpf under hw-module
       2022-08-05
          Added container mpls-ext-dscp-preserve
       2022-07-11
          Added missing description statement to nodes
       2022-07-06
          Added containers nif-hp-fifo-reserve, four8byte-cfm-maid-enable and gue
       2022-07-04
          Added policer-scale support under qos
       2022-06-20
          Added new container multicast under hw-module
       2022-06-17
          Added container for qos-stats-collection
       2022-05-10
          Added traffic-class-with-hoplimit support under l3-traffic
       2022-04-29
          Added l2-l3-tx-enable support under span-filter
       2022-04-05
          Added container for egress acl compression
       2022-03-30
          Modified span-l2-filter node to span-filter
       2022-03-24
          Removed must statements under traffic-class nodes
       2022-03-07
          Added free-buffer-int-threshold and clear-value-in-percent
        support under profile-qos
       2022-02-22
          Added container span-l2-filter under profile-routing
       2022-01-26
          Added base-and-micro-segment-f3216 support under profile-segment-routing
       2022-01-25
          Updated container profile-segment-routing
       2022-01-20
          removed container j2-dynamic-stats
       2021-11-24
          Added container irb
       2021-11-23
          Added container gre-exp-classification-enable under profile-qos";
    semver:module-version "3.0.0";
  }
  revision 2021-10-18 {
    description
      "Removed base-and-micro-segment-f3216 support
       2021-08-30
           Added new enum value under leaf max-classmap-size
       2021-08-11
           Added new container arp-isis-priority-enable";
    semver:module-version "2.0.0";
  }
  revision 2021-04-29 {
    description
      "Initial release";
    semver:module-version "1.0.0";
  }

  container hw-module {
    description
      "Configure h/w module";
    container profile-tcam {
      description
        "Configure profile for TCAM LC cards";
      container fib {
        description
          "Forwarding table to configure";
        container ipv4 {
          description
            "Configure ipv4 addresses in TCAM";
          container unicast {
            description
              "Unicast address";
            leaf percent {
              type uint32 {
                range "1..100" {
                  description
                    "value in percent";
                }
              }
              description
                "percent to configure";
            }
            container prefixes {
              description
                "ip prefix length";
              list prefix {
                key "prefix-length";
                description
                  "ip prefix length";
                leaf prefix-length {
                  type uint32 {
                    range "0..32" {
                      description
                        "IPv4 prefix length.";
                    }
                  }
                  description
                    "ip prefix length";
                }
                leaf percent {
                  type xr:Cisco-ios-xr-string {
                    length "1..9" {
                      description
                        "prefix precent 0.0-100.00000";
                    }
                    pattern "100([.]0{0,5})?|([0-9]{1,2}[0]?)([.][0-9]{0,5})?";
                  }
                  mandatory true;
                  description
                    "prefix percentage to configure";
                }
              }
            }
          }
        }
        container ipv6 {
          description
            "Configure ipv6 addresses in TCAM";
          container unicast {
            description
              "Unicast address";
            leaf percent {
              type uint32 {
                range "0..100" {
                  description
                    "value in percent";
                }
              }
              description
                "percent to configure";
            }
            container prefixes {
              description
                "ip prefix length";
              list prefix {
                key "prefix-length";
                description
                  "ip prefix length";
                leaf prefix-length {
                  type uint32 {
                    range "0..128" {
                      description
                        "IPv6 prefix length.";
                    }
                  }
                  description
                    "ip prefix length";
                }
                leaf percent {
                  type xr:Cisco-ios-xr-string {
                    length "1..9" {
                      description
                        "prefix precent 0.0-100.00000";
                    }
                    pattern "100([.]0{0,5})?|([0-9]{1,2}[0]?)([.][0-9]{0,5})?";
                  }
                  mandatory true;
                  description
                    "prefix percentage to configure";
                }
              }
            }
          }
        }
        container v6mcast {
          description
            "Multicast address";
          leaf percent {
            type uint32 {
              range "0..100" {
                description
                  "value in percent";
              }
            }
            description
              "percent to configure";
          }
        }
      }
      container acl-prefix {
        description
          "ACL table to configure";
        leaf percent {
          type uint32 {
            range "0..100" {
              description
                "value in percent";
            }
          }
          description
            "percent to configure";
        }
      }
      container format {
        description
          "format of the tcam entry";
        container access-list {
          description
            "Access List format";
          container ipv4 {
            presence "Indicates a ipv4 node is configured.";
            description
              "IPv4";
            container src-addr {
              presence "Indicates a src-addr node is configured.";
              description
                "source address, 32 bit qualifier";
            }
            container dst-addr {
              presence "Indicates a dst-addr node is configured.";
              description
                "destination address, 32 bit qualifier";
            }
            container src-port {
              must "../frag-bit";
              presence "Indicates a src-port node is configured.";
              description
                "source L4 port, 16 bit qualifier";
            }
            container dst-port {
              must "../frag-bit";
              presence "Indicates a dst-port node is configured.";
              description
                "destination L4 Port, 16 bit qualifier";
            }
            container proto {
              presence "Indicates a proto node is configured.";
              description
                "protocol type, 8 bit qualifier";
            }
            container tcp-flags {
              must "../frag-bit";
              presence "Indicates a tcp-flags node is configured.";
              description
                "tcp-flags, 6 bit qualifier";
            }
            container packet-length {
              presence "Indicates a packet-length node is configured.";
              description
                "packet length, 16 bit qualifier";
            }
            container frag-bit {
              presence "Indicates a frag-bit node is configured.";
              description
                "fragment-bit, 1 bit qualifier";
            }
            container common-acl {
              presence "Indicates a common-acl node is configured.";
              description
                "enable common-acl, 1 bit qualifier";
            }
            container precedence {
              presence "Indicates a precedence node is configured.";
              description
                "precedence/dscp, 8 bit qualifier";
            }
            container port-range {
              must "../frag-bit";
              presence "Indicates a port-range node is configured.";
              description
                "ipv4 port range qualifier, 24 bit qualifier";
            }
            container enable-capture {
              presence "Indicates a enable-capture node is configured.";
              description
                "Enable ACL based mirroring (Included by default)";
            }
            container enable-set-ttl {
              presence "Indicates a enable-set-ttl node is configured.";
              description
                "Enable Setting TTL field (Included by default)";
            }
            container ttl-match {
              presence "Indicates a ttl-match node is configured.";
              description
                "Enable matching on TTL field, 8 bit qualifier";
            }
            container interface-based {
              presence "Indicates a interface-based node is configured.";
              description
                "Enable non-shared interface based ACL, 15 bit qualifier in Jericho and 16 bit qualifier in Jericho2";
            }
            leaf udf1 {
              type xr:Cisco-ios-xr-string {
                length "1..16" {
                  description
                    "UDF name";
                }
              }
              description
                "user defined filter";
            }
            leaf udf2 {
              type xr:Cisco-ios-xr-string {
                length "1..16" {
                  description
                    "UDF name";
                }
              }
              description
                "user defined filter";
            }
            leaf udf3 {
              type xr:Cisco-ios-xr-string {
                length "1..16" {
                  description
                    "UDF name";
                }
              }
              description
                "user defined filter";
            }
            leaf udf4 {
              type xr:Cisco-ios-xr-string {
                length "1..16" {
                  description
                    "UDF name";
                }
              }
              description
                "user defined filter";
            }
            leaf udf5 {
              type xr:Cisco-ios-xr-string {
                length "1..16" {
                  description
                    "UDF name";
                }
              }
              description
                "user defined filter";
            }
            leaf udf6 {
              type xr:Cisco-ios-xr-string {
                length "1..16" {
                  description
                    "UDF name";
                }
              }
              description
                "user defined filter";
            }
            leaf udf7 {
              type xr:Cisco-ios-xr-string {
                length "1..16" {
                  description
                    "UDF name";
                }
              }
              description
                "user defined filter";
            }
            leaf udf8 {
              type xr:Cisco-ios-xr-string {
                length "1..16" {
                  description
                    "UDF name";
                }
              }
              description
                "user defined filter";
            }
          }
          container ipv4-locations {
            description
              "Location of format access-list ipv4 config";
            list location {
              key "location-name";
              description
                "Location of format access-list ipv4 config";
              leaf location-name {
                type xr:Node-id;
                description
                  "Location of format access-list ipv4 config";
              }
              container src-addr {
                presence "Indicates a src-addr node is configured.";
                description
                  "source address, 32 bit qualifier";
              }
              container dst-addr {
                presence "Indicates a dst-addr node is configured.";
                description
                  "destination address, 32 bit qualifier";
              }
              container src-port {
                must "../frag-bit";
                presence "Indicates a src-port node is configured.";
                description
                  "source L4 port, 16 bit qualifier";
              }
              container dst-port {
                must "../frag-bit";
                presence "Indicates a dst-port node is configured.";
                description
                  "destination L4 Port, 16 bit qualifier";
              }
              container proto {
                presence "Indicates a proto node is configured.";
                description
                  "protocol type, 8 bit qualifier";
              }
              container tcp-flags {
                must "../frag-bit";
                presence "Indicates a tcp-flags node is configured.";
                description
                  "tcp-flags, 6 bit qualifier";
              }
              container packet-length {
                presence "Indicates a packet-length node is configured.";
                description
                  "packet length, 16 bit qualifier";
              }
              container frag-bit {
                presence "Indicates a frag-bit node is configured.";
                description
                  "fragment-bit, 1 bit qualifier";
              }
              container common-acl {
                presence "Indicates a common-acl node is configured.";
                description
                  "enable common-acl, 1 bit qualifier";
              }
              container precedence {
                presence "Indicates a precedence node is configured.";
                description
                  "precedence/dscp, 8 bit qualifier";
              }
              container port-range {
                must "../frag-bit";
                presence "Indicates a port-range node is configured.";
                description
                  "ipv4 port range qualifier, 24 bit qualifier";
              }
              container enable-capture {
                presence "Indicates a enable-capture node is configured.";
                description
                  "Enable ACL based mirroring (Included by default)";
              }
              container enable-set-ttl {
                presence "Indicates a enable-set-ttl node is configured.";
                description
                  "Enable Setting TTL field (Included by default)";
              }
              container ttl-match {
                presence "Indicates a ttl-match node is configured.";
                description
                  "Enable matching on TTL field, 8 bit qualifier";
              }
              container interface-based {
                presence "Indicates a interface-based node is configured.";
                description
                  "Enable non-shared interface based ACL, 15 bit qualifier in Jericho and 16 bit qualifier in Jericho2";
              }
              leaf udf1 {
                type xr:Cisco-ios-xr-string {
                  length "1..16" {
                    description
                      "UDF name";
                  }
                }
                description
                  "user defined filter";
              }
              leaf udf2 {
                type xr:Cisco-ios-xr-string {
                  length "1..16" {
                    description
                      "UDF name";
                  }
                }
                description
                  "user defined filter";
              }
              leaf udf3 {
                type xr:Cisco-ios-xr-string {
                  length "1..16" {
                    description
                      "UDF name";
                  }
                }
                description
                  "user defined filter";
              }
              leaf udf4 {
                type xr:Cisco-ios-xr-string {
                  length "1..16" {
                    description
                      "UDF name";
                  }
                }
                description
                  "user defined filter";
              }
              leaf udf5 {
                type xr:Cisco-ios-xr-string {
                  length "1..16" {
                    description
                      "UDF name";
                  }
                }
                description
                  "user defined filter";
              }
              leaf udf6 {
                type xr:Cisco-ios-xr-string {
                  length "1..16" {
                    description
                      "UDF name";
                  }
                }
                description
                  "user defined filter";
              }
              leaf udf7 {
                type xr:Cisco-ios-xr-string {
                  length "1..16" {
                    description
                      "UDF name";
                  }
                }
                description
                  "user defined filter";
              }
              leaf udf8 {
                type xr:Cisco-ios-xr-string {
                  length "1..16" {
                    description
                      "UDF name";
                  }
                }
                description
                  "user defined filter";
              }
            }
          }
          container ipv6 {
            must "src-port and next-hdr";
            presence "Indicates a ipv6 node is configured.";
            description
              "IPv6";
            container src-addr {
              presence "Indicates a src-addr node is configured.";
              description
                "source address, 128 bit qualifier";
            }
            container src-port {
              presence "Indicates a src-port node is configured.";
              description
                "source L4 Port, 16 bit qualifier (mandatory field)";
            }
            container dst-addr {
              presence "Indicates a dst-addr node is configured.";
              description
                "destination address, 128 bit qualifier";
            }
            container dst-port {
              presence "Indicates a dst-port node is configured.";
              description
                "destination L4 Port, 16 bit qualifier";
            }
            container next-hdr {
              presence "Indicates a next-hdr node is configured.";
              description
                "next header, 8 bit qualifier (mandatory field)";
            }
            container tcp-flags {
              presence "Indicates a tcp-flags node is configured.";
              description
                "tcp-flags, 8 bit qualifier";
            }
            container payload-length {
              presence "Indicates a payload-length node is configured.";
              description
                "payload length, 16 bit qualifier";
            }
            container frag-bit {
              presence "Indicates a frag-bit node is configured.";
              description
                "fragment-bit, 1 bit qualifier";
            }
            container traffic-class {
              presence "Indicates a traffic-class node is configured.";
              description
                "Traffic Class, 8 bit qualifier";
            }
            container enable-capture {
              presence "Indicates a enable-capture node is configured.";
              description
                "Enable ACL based mirroring (Included by default)";
            }
            container enable-set-ttl {
              presence "Indicates a enable-set-ttl node is configured.";
              description
                "Enable Setting TTL field (Included by default)";
            }
            container common-acl {
              presence "Indicates a common-acl node is configured.";
              description
                "enable common-acl, 1 bit qualifier";
            }
            container ttl-match {
              presence "Indicates a ttl-match node is configured.";
              description
                "Enable matching on TTL field, 8 bit qualifier";
            }
            container interface-based {
              presence "Indicates a interface-based node is configured.";
              description
                "Enable non-shared interface based ACL, 15 bit qualifier in Jericho and 16 bit qulifier in Jericho2";
            }
            leaf udf1 {
              type xr:Cisco-ios-xr-string {
                length "1..16" {
                  description
                    "UDF name";
                }
              }
              description
                "user defined filter";
            }
            leaf udf2 {
              type xr:Cisco-ios-xr-string {
                length "1..16" {
                  description
                    "UDF name";
                }
              }
              description
                "user defined filter";
            }
            leaf udf3 {
              type xr:Cisco-ios-xr-string {
                length "1..16" {
                  description
                    "UDF name";
                }
              }
              description
                "user defined filter";
            }
            leaf udf4 {
              type xr:Cisco-ios-xr-string {
                length "1..16" {
                  description
                    "UDF name";
                }
              }
              description
                "user defined filter";
            }
            leaf udf5 {
              type xr:Cisco-ios-xr-string {
                length "1..16" {
                  description
                    "UDF name";
                }
              }
              description
                "user defined filter";
            }
            leaf udf6 {
              type xr:Cisco-ios-xr-string {
                length "1..16" {
                  description
                    "UDF name";
                }
              }
              description
                "user defined filter";
            }
            leaf udf7 {
              type xr:Cisco-ios-xr-string {
                length "1..16" {
                  description
                    "UDF name";
                }
              }
              description
                "user defined filter";
            }
            leaf udf8 {
              type xr:Cisco-ios-xr-string {
                length "1..16" {
                  description
                    "UDF name";
                }
              }
              description
                "user defined filter";
            }
          }
          container ipv6-locations {
            description
              "Location of format access-list ipv6 config";
            list location {
              must "src-port and next-hdr";
              key "location-name";
              description
                "Location of format access-list ipv6 config";
              leaf location-name {
                type xr:Node-id;
                description
                  "Location of format access-list ipv6 config";
              }
              container src-addr {
                presence "Indicates a src-addr node is configured.";
                description
                  "source address, 32 bit qualifier";
              }
              container src-port {
                presence "Indicates a src-port node is configured.";
                description
                  "source L4 port, 16 bit qualifier";
              }
              container dst-addr {
                presence "Indicates a dst-addr node is configured.";
                description
                  "destination address, 32 bit qualifier";
              }
              container dst-port {
                presence "Indicates a dst-port node is configured.";
                description
                  "destination L4 Port, 16 bit qualifier";
              }
              container next-hdr {
                presence "Indicates a next-hdr node is configured.";
                description
                  "next header, 8 bit qualifier (mandatory field)";
              }
              container tcp-flags {
                presence "Indicates a tcp-flags node is configured.";
                description
                  "tcp-flags, 6 bit qualifier";
              }
              container payload-length {
                presence "Indicates a packet-length node is configured.";
                description
                  "packet length, 16 bit qualifier";
              }
              container frag-bit {
                presence "Indicates a frag-bit node is configured.";
                description
                  "fragment-bit, 1 bit qualifier";
              }
              container traffic-class {
                presence "Indicates a traffic-class node is configured.";
                description
                  "Traffic Class, 8 bit qualifier";
              }
              container enable-capture {
                presence "Indicates a enable-capture node is configured.";
                description
                  "Enable ACL based mirroring (Included by default)";
              }
              container enable-set-ttl {
                presence "Indicates a enable-set-ttl node is configured.";
                description
                  "Enable Setting TTL field (Included by default)";
              }
              container common-acl {
                presence "Indicates a common-acl node is configured.";
                description
                  "enable common-acl, 1 bit qualifier";
              }
              container ttl-match {
                presence "Indicates a ttl-match node is configured.";
                description
                  "Enable matching on TTL field, 8 bit qualifier";
              }
              container interface-based {
                presence "Indicates a interface-based node is configured.";
                description
                  "Enable non-shared interface based ACL, 15 bit qualifier in Jericho and 16 bit qualifier in Jericho2";
              }
              leaf udf1 {
                type xr:Cisco-ios-xr-string {
                  length "1..16" {
                    description
                      "UDF name";
                  }
                }
                description
                  "user defined filter";
              }
              leaf udf2 {
                type xr:Cisco-ios-xr-string {
                  length "1..16" {
                    description
                      "UDF name";
                  }
                }
                description
                  "user defined filter";
              }
              leaf udf3 {
                type xr:Cisco-ios-xr-string {
                  length "1..16" {
                    description
                      "UDF name";
                  }
                }
                description
                  "user defined filter";
              }
              leaf udf4 {
                type xr:Cisco-ios-xr-string {
                  length "1..16" {
                    description
                      "UDF name";
                  }
                }
                description
                  "user defined filter";
              }
              leaf udf5 {
                type xr:Cisco-ios-xr-string {
                  length "1..16" {
                    description
                      "UDF name";
                  }
                }
                description
                  "user defined filter";
              }
              leaf udf6 {
                type xr:Cisco-ios-xr-string {
                  length "1..16" {
                    description
                      "UDF name";
                  }
                }
                description
                  "user defined filter";
              }
              leaf udf7 {
                type xr:Cisco-ios-xr-string {
                  length "1..16" {
                    description
                      "UDF name";
                  }
                }
                description
                  "user defined filter";
              }
              leaf udf8 {
                type xr:Cisco-ios-xr-string {
                  length "1..16" {
                    description
                      "UDF name";
                  }
                }
                description
                  "user defined filter";
              }
            }
          }
        }
      }
    }
    container profile-acl {
      description
        "Configure acl profile";
      container egress {
        description
          "egress acl";
        container layer3 {
          description
            "egress layer3 acl";
          container interface-based {
            presence "Indicates a interface-based node is configured.";
            description
              "egress layer3 interface-based acl";
          }
        }
        container compress {
          description
            "Specify ACL compression in hardware";
          container enable {
            presence "Indicates a enable node is configured.";
            description
              "Enable ACL egress compression in hardware";
          }
          container enable-locations {
            description
              "Location of acl config";
            list location {
              key "location-name";
              description
                "Location of acl config";
              leaf location-name {
                type xr:Node-id;
                description
                  "Location of acl config";
              }
            }
          }
        }
      }
      container ipv6 {
        description
          "ipv6 protocol specific options";
        container ext-header {
          description
            "ipv6 extension header related options";
          container permit {
            presence "Indicates a permit node is configured.";
            description
              "allow permit of extension header packets";
          }
        }
      }
      container ingress {
        description
          "ingress acl";
        container compress {
          description
            "Specify ACL compression in hardware";
          container enable {
            presence "Indicates a enable node is configured.";
            description
              "Enable ACL ingress compression in hardware";
          }
          container enable-locations {
            description
              "Location of acl config";
            list location {
              key "location-name";
              description
                "Location of acl config";
              leaf location-name {
                type xr:Node-id;
                description
                  "Location of acl config";
              }
            }
          }
        }
      }
    }
    container profile-load-balance {
      description
        "Configure load balance parameters";
      container algorithm {
        description
          "Configure hashing algorithm profiles";
        container layer2 {
          must
            "not(../ip-tunnel or ../mpls-safe-speculative-parsing
             or ../l3-only or ../gtp
             or ../gtp-mpls or ../pppo-e or ../mpls-lsr-ler-optimized or ../mpls-lsr-ler
             or ../inner-l2-field)";
          presence "Indicates a layer2 node is configured.";
          description
            "Layer 2 optimized.";
        }
        container ip-tunnel {
          must
            "not(../layer2 or ../mpls-safe-speculative-parsing
             or ../l3-only or ../gtp
             or ../gtp-mpls or ../pppo-e or ../mpls-lsr-ler-optimized or ../mpls-lsr-ler
             or ../inner-l2-field)";
          presence "Indicates a ip-tunnel node is configured.";
          description
            "IP tunnel optimized.";
        }
        container mpls-safe-speculative-parsing {
          must
            "not(../layer2 or ../ip-tunnel
             or ../l3-only or ../gtp
             or ../gtp-mpls or ../pppo-e or ../mpls-lsr-ler-optimized or ../mpls-lsr-ler
             or ../inner-l2-field)";
          presence "Indicates a mpls-safe-speculative-parsing node is configured.";
          description
            "MPLS safe Speculative parsing.";
        }
        container l3-only {
          must
            "not(../layer2 or ../ip-tunnel
             or ../mpls-safe-speculative-parsing or ../gtp
             or ../gtp-mpls or ../pppo-e or ../mpls-lsr-ler-optimized or ../mpls-lsr-ler
             or ../inner-l2-field)";
          presence "Indicates a l3-only node is configured.";
          description
            "L3 Header only Hash.";
        }
        container gtp {
          must
            "not(../layer2 or ../ip-tunnel
             or ../mpls-safe-speculative-parsing or ../l3-only
             or ../gtp-mpls or ../pppo-e or ../mpls-lsr-ler-optimized or ../mpls-lsr-ler
             or ../inner-l2-field)";
          presence "Indicates a gtp node is configured.";
          description
            "GTP optimized.";
        }
        container gtp-mpls {
          must
            "not(../layer2 or ../ip-tunnel
             or ../mpls-safe-speculative-parsing or ../l3-only
             or ../gtp or ../pppo-e or ../mpls-lsr-ler-optimized or ../mpls-lsr-ler
             or ../inner-l2-field)";
          presence "Indicates a gtp-mpls node is configured.";
          description
            "GTP over MPLS optimized hash.";
        }
        container mpls-lsr-ler {
          must
            "not(../layer2 or ../ip-tunnel
             or ../mpls-safe-speculative-parsing or ../l3-only
             or ../gtp or ../pppo-e or ../gtp-mpls or ../mpls-lsr-ler-optimized
             or ../inner-l2-field)";
          presence "Indicates a mpls-lsr-ler is configured.";
          description
            "mpls-lsr-ler.";
        }
        container mpls-lsr-ler-optimized {
          must
            "not(../layer2 or ../ip-tunnel
             or ../mpls-safe-speculative-parsing or ../l3-only
             or ../gtp or ../pppo-e or ../gtp-mpls or ../mpls-lsr-ler
             or ../inner-l2-field)";
          presence "Indicates a mpls-lsr-ler-optimized is configured.";
          description
            "mpls-lsr-ler-optimized.";
        }
        container fat-based-hash {
          must
            "not(../layer2 or ../ip-tunnel
             or ../mpls-safe-speculative-parsing or ../l3-only
             or ../gtp or ../pppo-e or ../gtp-mpls or ../mpls-lsr-ler
             or ../mpls-lsr-ler-optimized or ../inner-l2-field )";
          presence "Indicates a fat-based is configured.";
          description
            "FAT label based hash in l2vpn session on decap node. Reload is required for this option";
        }
        container pppo-e {
          must
            "not(../layer2 or ../ip-tunnel
             or ../mpls-safe-speculative-parsing or ../l3-only
             or ../gtp or ../gtp-mpls or ../mpls-lsr-ler-optimized
             or ../mpls-lsr-ler or ../inner-l2-field or ../fat-based-hash)";
          presence "Indicates a pppo-e node is configured.";
          description
            "PPPoE session based optimized hash. Reload is required for this option";
          container decap-fatbased-hashing {
            presence "Indicates a pppo-e node with fat based hash is configured.";
            description
              "PPPoE session based optimized hash with FAT label based hash. Reload is required for this option";
          }
        }
        container inner-l2-field {
          must
            "not(../layer2 or ../ip-tunnel
             or ../mpls-safe-speculative-parsing or ../l3-only
             or ../gtp or ../pppo-e or ../gtp-mpls or ../mpls-lsr-ler
             or ../mpls-lsr-ler-optimized)";
          presence "Indicates a inner-l2-field is configured.";
          description
            "inner-l2-field.";
        }
        leaf hash-polynomial-index {
          type uint32 {
            range "1..6" {
              description
                "hash polynomial index";
            }
          }
          description
            "hash polynomial index";
        }
      }
    }
    container profile-bundle-hash {
      description
        "Adjust bundle-hash algorithm";
      container hash-index {
        description
          "configure which polynomial to use in bundle-hash";
        container locations {
          description
            "Location of bundle-hash polynomial config";
          list location {
            key "location-name location-name2";
            description
              "Location of bundle-hash polynomial config";
            leaf location-name {
              type xr:Node-id;
              description
                "Location of bundle-hash polynomial config";
            }
            leaf location-name2 {
              type xr:Node-id;
              description
                "Location of bundle-hash polynomial config";
            }
            leaf index {
              type enumeration {
                enum "1" {
                  value 1;
                  description
                    "Use Polynomial value 0x8011";
                }
                enum "2" {
                  value 2;
                  description
                    "Use Polynomial value 0x8423";
                }
                enum "3" {
                  value 3;
                  description
                    "Use Polynomial value 0x8101";
                }
                enum "4" {
                  value 4;
                  description
                    "Use Polynomial value 0x84A1";
                }
                enum "5" {
                  value 5;
                  description
                    "Use Polynomial value 0x9019";
                }
                enum "10" {
                  value 10;
                  description
                    "Use LB-Key-Pkt-Data directly";
                }
                enum "11" {
                  value 11;
                  description
                    "Use counter incremented every packet";
                }
                enum "12" {
                  value 12;
                  description
                    "Use counter incremented every two clocks";
                }
              }
              mandatory true;
              description
                "Configure hash index";
            }
          }
        }
      }
      container ignore-ingress-port {
        presence "Indicates a ignore-ingress-port node is configured.";
        description
          "Disable ingress port during bundle hash computation";
      }
      container per-packet-round-robin {
        presence "Indicates a per-packet-round-robin node is configured.";
        description
          "Enable per-packet round robin loadbalancing for all bundles in system";
      }
    }
    container profile-qos {
      description
        "Configure qos profile";
      container max-classmap-sizes {
        description
          "max class map size";
        leaf max-classmap-size {
          type enumeration {
            enum "32" {
              value 32;
              description
                "Max 32 class-maps per policy";
            }
            enum "16" {
              value 16;
              description
                "Max 16 class-maps per policy";
            }
            enum "8" {
              value 8;
              description
                "Max 8 class-maps per policy";
            }
            enum "4" {
              value 4;
              description
                "Max 4 class-maps per policy";
            }
            enum "2" {
              value 2;
              description
                "Max 2 class-maps per policy";
            }
            enum "1" {
              value 1;
              description
                "Max 1 class-maps per policy";
            }
          }
          description
            "max class map size";
        }
        container locations {
          description
            "Location of QoS config";
          list location {
            key "location-name";
            description
              "Location of QoS config";
            leaf location-name {
              type xr:Node-id;
              description
                "Location of QoS config";
            }
            leaf max-classmap-size {
              type enumeration {
                enum "32" {
                  value 32;
                  description
                    "Max 32 class-maps per policy";
                }
                enum "16" {
                  value 16;
                  description
                    "Max 16 class-maps per policy";
                }
                enum "8" {
                  value 8;
                  description
                    "Max 8 class-maps per policy";
                }
                enum "4" {
                  value 4;
                  description
                    "Max 4 class-maps per policy";
                }
                enum "2" {
                  value 2;
                  description
                    "Max 2 class-maps per policy";
                }
                enum "1" {
                  value 1;
                  description
                    "Max 1 class-maps per policy";
                }
              }
              mandatory true;
              description
                "max class map size";
            }
          }
        }
      }
      container ingress-fadt-sets {
        description
          "configure qos fadt values";
        leaf ingress-fadt-set {
          type enumeration {
            enum "disable" {
              value 8;
              description
                "Disable FADT. No fair distribution of buffer descriptors among VoQs, not recommended.";
            }
            enum "high" {
              value 4;
              description
                "Set high drop threshold for VoQs. Congested VoQs are allowed to consume more buffer descriptors.";
            }
            enum "medium" {
              value 2;
              description
                "Set moderate drop threshold for VoQs. Congested VoQs are allowed to consume more buffer descriptors than default configuration.";
            }
            enum "low" {
              value 1;
              description
                "Set low drop threshold for VoQs. Congested VoQs are not allowed to consume more buffer descriptors.";
            }
          }
          description
            "Change the adaptive drop threshold parameter for VoQ";
        }
      }
      container locations {
        description
          "Location of QoS config";
        list location {
          key "location-name";
          description
            "Location of QoS config";
          leaf location-name {
            type xr:Node-id;
            description
              "Location of QoS config";
          }
          leaf ingress-fadt-set {
            type enumeration {
              enum "disable" {
                value 8;
                description
                  "Disable FADT, No fair distribution of buffer descriptors among VoQs, not recommended.";
              }
              enum "high" {
                value 4;
                description
                  "Set high drop threshold for VoQs. Congested VoQs are allowed to consume more buffer descriptors.";
              }
              enum "medium" {
                value 2;
                description
                  "Set medium drop threshold for VoQs. Congested VoQs are allowed to consume more buffer descriptors than default configuration.";
              }
              enum "low" {
                value 1;
                description
                  "Set low drop threshold for VoQs. Congested VoQs are not allowed to consume more buffer descriptors.";
              }
            }
            mandatory true;
            description
              "set ingress fadt";
          }
        }
      }
      container ingress-model {
        description
          "QoS model for ingress feature";
        leaf model {
          type enumeration {
            enum "peering" {
              value 1;
              description
                "Peering model for ingress QoS";
            }
          }
          description
            "Peering model for ingress QoS";
        }
        container peering-locations {
          description
            "Peering model for ingress QoS with location";
          list location {
            key "location-name";
            description
              "Location of QoS config";
            leaf location-name {
              type xr:Node-id;
              description
                "Location of QoS config";
            }
            leaf model {
              type enumeration {
                enum "peering" {
                  value 1;
                  description
                    "Peering model for ingress QoS";
                }
              }
              description
                "Peering model for ingress QoS";
            }
          }
        }
      }
      container qosg-dscp-mark-enable {
        presence "Indicates a qosg-dscp-mark-enable node is configured.";
        description
          "Enable both 'set qos-group' and 'set dscp/precedence' actions in the same ingress QoS policy";
        leaf first-dscp-precedence-value {
          type uint32 {
            range "0..63" {
              description
                "First DSCP/Precedence value";
            }
          }
          mandatory true;
          description
            "Enable both 'set qos-group' and 'set dscp/precedence' actions in the same ingress QoS policy";
        }
        leaf second-dscp-precedence-value {
          type uint32 {
            range "0..63" {
              description
                "Second DSCP/Precedence value";
            }
          }
          must "../first-dscp-precedence-value";
          description
            "Second DSCP/Precedence value";
        }
        leaf third-dscp-precedence-value {
          type uint32 {
            range "0..63" {
              description
                "Third DSCP/Precedence value";
            }
          }
          must "../second-dscp-precedence-value";
          must "../second-dscp-precedence-value";
          description
            "Third DSCP/Precedence value";
        }
        leaf fourth-dscp-precedence-value {
          type uint32 {
            range "0..63" {
              description
                "Fourth DSCP/Precedence value";
            }
          }
          must "../third-dscp-precedence-value";
          must "../third-dscp-precedence-value";
          description
            "Fourth DSCP/Precedence value";
        }
        leaf fifth-dscp-precedence-value {
          type uint32 {
            range "0..63" {
              description
                "Fifth DSCP/Precedence value";
            }
          }
          must "../fourth-dscp-precedence-value";
          must "../fourth-dscp-precedence-value";
          description
            "Fifth DSCP/Precedence value";
        }
        leaf sixth-dscp-precedence-value {
          type uint32 {
            range "0..63" {
              description
                "Sixth DSCP/Precedence value";
            }
          }
          must "../fifth-dscp-precedence-value";
          must "../fifth-dscp-precedence-value";
          description
            "Sixth DSCP/Precedence value";
        }
        leaf seventh-dscp-precedence-value {
          type uint32 {
            range "0..63" {
              description
                "Seventh DSCP/Precedence value";
            }
          }
          must "../sixth-dscp-precedence-value";
          must "../sixth-dscp-precedence-value";
          description
            "Seventh DSCP/Precedence value";
        }
        leaf eighth-dscp-precedence-value {
          type uint32 {
            range "0..63" {
              description
                "Eighth DSCP/Precedence value";
            }
          }
          must "../seventh-dscp-precedence-value";
          must "../seventh-dscp-precedence-value";
          description
            "Eighth DSCP/Precedence value";
        }
      }
      leaf free-buffer-int-threshold {
        type uint32 {
          range "0..100" {
            description
              "set value in percent (must be less than clear value)";
          }
        }
        must "../clear-value-in-percent";
        description
          "Configure free buffer interrupt threshold";
      }
      leaf clear-value-in-percent {
        type uint32 {
          range "0..100" {
            description
              "clear value in percent (must be more than set value)";
          }
        }
        must "../free-buffer-int-threshold";
        description
          "clear value in percent (must be more than set value)";
      }
      container hqos-enable {
        presence "Indicates a hqos-enable node is configured.";
        description
          "Enable Hierarchical QoS";
      }
      container physical-hqos-enable {
        presence "Indicates a hqos-enable node is configured.";
        description
          "Enable Hierarchical QoS";
      }
      container qos-stats-collection {
        presence "Indicates a qos-stats-collection node is configured.";
        description
          "Enable QoS stats push model";
      }
      container ecn-marking-stats {
        presence "Indicates a ecn-marking-stats node is configured.";
        description
          "Enable ECN marking stats mode";
      }
      container egress-exp-mark-disable {
        presence "Indicates a egress-exp-mark-disable node is configured.";
        description
          "Disable egress EXP marking";
      }
      container shared-policer-per-class-stats {
        presence "Indicates a shared-policer-per-class-stats node is configured.";
        description
          "Enable shared policer (per class stats) mode";
      }
      container wred-stats-enable {
        presence "Indicates a wred-stats-enable node is configured.";
        description
          "Enable Wred egress stats";
      }
      container lag-scheduler {
        presence "Indicates a lag-scheduler node is configured.";
        description
          "Enable QoS Lag Scheduler";
      }
      container ipv6 {
        description
          "Configure ipv6 protocol";
        container short {
          presence "Indicates a short node is configured.";
          description
            "Configure ipv6 source short address tcam lookup";
        }
        container short-l2qos-enable {
          presence "Indicates a short-l2qos-enable node is configured.";
          description
            "Enable l2qos feature which requires to reduce ipv6 dest mask to 96 bits";
        }
        container short-etm {
          presence "Indicates a short-etm node is configured.";
          description
            "Enable TC matching feature in ETM which requires reduction of IPv6 dest mask to 96 bits";
        }
      }
      container conform-aware-policer {
        presence "Indicates a conform-aware-policer node is configured.";
        description
          "Configure Conform Aware Policer mode";
      }
      container arp-isis-priority-enable {
        presence "Indicates a arp-isis-priority-enable node is configured.";
        description
          "Prioritize ISIS and ARP packets";
      }
      container gre-exp-classification-enable {
        presence "Indicates a gre-exp-classification-enable node is configured.";
        description
          "Enable Ingress EXP classification for MPLSoGRE";
      }
      container egress-compensation-setting-force {
        presence "Indicates a egress-compensation-setting-force node is configured.";
        description
          "Forcefully allows to configure non-unique egress compensation values ignoring ASIC limitation (not recommended).";
      }
      container policer-scale {
        description
          "Max policer scale";
        leaf scale-value {
          type enumeration {
            enum "48000" {
              value 48000;
              description
                "Max policer scale 48000";
            }
            enum "64000" {
              value 64000;
              description
                "Max policer scale 64000";
            }
          }
          description
            "Max policer scale [48000, 64000]";
        }
      }
      container nif-hp-fifo-reserve {
        description
          "Indicates a nif-hp-fifo-reserve node is configured.";
        leaf percent {
          type uint32 {
            range "0..100" {
              description
                "Setting 0 will disable the feature.";
            }
          }
          description
            "Reserve NIF FIFOs (percentage) for High Priority traffic.";
        }
      }
      container nif-hp-fifo-reserve-locations {
        description
          "Location of QoS config";
        list location {
          key "location-name";
          description
            "Location of QoS config";
          leaf location-name {
            type xr:Node-id;
            description
              "Location of QoS config";
          }
          leaf percent {
            type uint32 {
              range "0..100" {
                description
                  "Setting 0 will disable the feature.";
              }
            }
            mandatory true;
            description
              "Reserve NIF FIFOs (percentage) for High Priority traffic.";
          }
        }
      }
      container irb-recycle-bandwidth {
        description
          "IRB Recycle Port Bandwidth [400, 600] Gbps";
        leaf bandwidth {
          type enumeration {
            enum "400" {
              value 400;
              description
                "IRB Recycle Bandwidth 400 Gbps";
            }
            enum "600" {
              value 600;
              description
                "IRB Recycle Bandwidth 600 Gbps";
            }
          }
          description
            "IRB Recycle Port Bandwidth [400, 600] Gbps";
        }
        container locations {
          description
            "Location of QoS config";
          list location {
            key "location-name";
            description
              "Location of QoS config";
            leaf location-name {
              type xr:Node-id;
              description
                "Location of QoS config";
            }
            leaf bandwidth {
              type enumeration {
                enum "400" {
                  value 400;
                  description
                    "IRB Recycle Bandwidth 400 Gbps";
                }
                enum "600" {
                  value 600;
                  description
                    "IRB Recycle Bandwidth 600 Gbps";
                }
              }
              mandatory true;
              description
                "IRB Recycle Port Bandwidth [400, 600] Gbps";
            }
          }
        }
      }
      container etm-low-rate-connector {
        description
          "Low rate connector allocation for ETM interfaces on SE platforms with J2 family of ASICs";
        container locations {
          description
            "Location to apply qos configuration";
          list location {
            must "npu-ids/npu-id";
            key "location-name";
            description
              "Location to apply qos configuration";
            leaf location-name {
              type xr:Node-id;
              description
                "Location to apply qos configuration";
            }
            container npu-ids {
              description
                "NPU ID <0-5> to apply qos configuration";
              list npu-id {
                key "npu-id";
                description
                  "NPU ID <0-5> to apply qos configuration";
                leaf npu-id {
                  type uint32 {
                    range "0..5" {
                      description
                        "NPU id value in decimal";
                    }
                  }
                  description
                    "NPU ID <0-5> to apply qos configuration";
                }
                leaf reserve-conn-range {
                  type uint32 {
                    range "0..64" {
                      description
                        "Number of connector range (1024 connectors per range) to be reserved (0 indicates no reservation/feature disabled)";
                    }
                  }
                  mandatory true;
                  description
                    "connector range value in decimal Jericho2C(P): <0-64> and Jericho2: <0-32>";
                }
              }
            }
          }
        }
        container all {
          must "npu-ids/npu-id";
          presence "Indicates a reserve-conn-range node is configured.";
          description
            "Configuration for all locations";
          container npu-ids {
            description
              "NPU ID <0-5> to apply qos configuration";
            list npu-id {
              key "npu-id";
              description
                "NPU ID <0-5> to apply qos configuration";
              leaf npu-id {
                type uint32 {
                  range "0..5" {
                    description
                      "NPU id value in decimal";
                  }
                }
                description
                  "NPU ID <0-5> to apply qos configuration";
              }
              leaf reserve-conn-range {
                type uint32 {
                  range "0..64" {
                    description
                      "Number of connector range (1024 connectors per range) to be reserved (0 indicates no reservation/feature disabled)";
                  }
                }
                mandatory true;
                description
                  "connector range value in decimal Jericho2C(P): <0-64> and Jericho2: <0-32>";
              }
            }
          }
        }
      }
    }
    leaf profile-bundle-scale {
      type enumeration {
        enum "256" {
          value 256;
          description
            "Max 256 trunks, Max 64 members";
        }
        enum "512" {
          value 512;
          description
            "Max 512 trunks, Max 32 members";
        }
        enum "1024" {
          value 1024;
          description
            "Max 1024 trunks, Max 16 members";
        }
      }
      description
        "Max number of bundles supported";
    }
    container profile-npu {
      description
        "Configure operating profiles for NPUs";
      container native-mode-enable {
        presence "Indicates a native-mode-enable node is configured.";
        description
          "Enable NPUs to operate in native mode";
      }
    }
    container l2pt-extended-protocols-enable {
      presence "Indicates a l2pt-extended-protocols-enable node is configured.";
      description
        "Enable extended protocol set for L2PT Tunnelling";
    }
    container profile-mdb {
      description
        "Different MDB profiles supported";
      container l3max {
        must
          "not(../l3max-se or ../l2max
           or ../l2max-se or ../balanced)";
        presence "Indicates a l3max node is configured.";
        description
          "l3max profile for router containing non-TCAM cards";
      }
      container l3max-se {
        must
          "not(../l3max or ../l2max
           or ../l2max-se or ../balanced)";
        presence "Indicates a l3max-se node is configured.";
        description
          "l3max-se profile for router containing only TCAM cards";
      }
      container l2max {
        must
          "not(../l3max or ../l3max-se
           or ../l2max-se or ../balanced)";
        presence "Indicates a l2max node is configured.";
        description
          "l2max profile for router containing non-TCAM cards";
      }
      container l2max-se {
        must
          "not(../l3max or ../l3max-se
           or ../l2max or ../balanced)";
        presence "Indicates a l2max-se node is configured.";
        description
          "l2max-se profile for router containing only TCAM cards";
      }
      container l3max-srv6 {
        must
          "not(../l3max-se-srv6 or ../l2max-srv6
           or ../l2max-se-srv6 or ../balanced)";
        presence "Indicates a l3max-srv6 node is configured.";
        description
          "l3max-srv6 profile for router containing non-TCAM cards";
      }
      container l3max-se-srv6 {
        must
          "not(../l3max-srv6 or ../l2max-srv6
           or ../l2max-se-srv6 or ../balanced)";
        presence "Indicates a l3max-se-srv6 node is configured.";
        description
          "l3max-se-srv6 profile for router containing only TCAM cards";
      }
      container l2max-srv6 {
        must
          "not(../l3max-srv6 or ../l3max-se-srv6
           or ../l2max-se-srv6 or ../balanced)";
        presence "Indicates a l2max-srv6 node is configured.";
        description
          "l2max-srv6 profile for router containing non-TCAM cards";
      }
      container l2max-se-srv6 {
        must
          "not(../l3max-srv6 or ../l3max-se-srv6
           or ../l2max-srv6 or ../balanced)";
        presence "Indicates a l2max-se-srv6 node is configured.";
        description
          "l2max-se-srv6 profile for router containing only TCAM cards";
      }
      container balanced {
        must
          "not(../l3max or ../l3max-se
           or ../l2max or ../l2max-se)";
        presence "Indicates a balanced node is configured.";
        description
          "balanced profile for router containing non-TCAM cards";
      }
    }
    container profile-netflow {
      description
        "Configure Netflow profile.";
      container ipfix315-enable {
        presence "Indicates a ipfix315-enable node is configured.";
        description
          "IPFIX 315 enable ";
      }
      container ipfix315-enable-locations {
        description
          "Location of NETFLOW config";
        list location {
          key "location-name location-name2";
          description
            "Location of NETFLOW config";
          leaf location-name {
            type xr:Node-id;
            description
              "Location of NETFLOW config";
          }
          leaf location-name2 {
            type xr:Node-id;
            description
              "Location of NETFLOW config";
          }
        }
      }
      container sflow-enable {
        presence "Indicates a sflow-enable node is configured.";
        description
          "SFLOW enable ";
      }
      container sflow-enable-locations {
        description
          "Location of NETFLOW config";
        list location {
          key "location-name location-name2";
          description
            "Location of NETFLOW config";
          leaf location-name {
            type xr:Node-id;
            description
              "Location of NETFLOW config";
          }
          leaf location-name2 {
            type xr:Node-id;
            description
              "Location of NETFLOW config";
          }
        }
      }
      container fpc-enable {
        presence "Indicates a fpc-enable node is configured.";
        description
          "Netflow full packet capture enable ";
      }
      container fpc-enable-locations {
        description
          "Location of NETFLOW config";
        list location {
          key "location-name location-name2";
          description
            "Location of NETFLOW config";
          leaf location-name {
            type xr:Node-id;
            description
              "Location of NETFLOW config";
          }
          leaf location-name2 {
            type xr:Node-id;
            description
              "Location of NETFLOW config";
          }
        }
      }
    }
    container profile-stats {
      description
        "Configure stats profile.";
      container acl-permit {
        must
          "not(../qos-enhanced or ../ingress-sr or
               ../enh-sr-policy or ../ingress-sr-mspw or
               ../tx-scale-enhanced)";
        presence "Indicates a acl-permit node is configured.";
        description
          "Enable ACL permit stats.";
      }
      container qos-enhanced {
        must
          "not(../acl-permit or ../ingress-sr or
               ../enh-sr-policy or ../ingress-sr-mspw or
               ../tx-scale-enhanced)";
        presence "Indicates a qos-enhanced node is configured.";
        description
          "Enable enhanced QoS stats.";
      }
      container ingress-sr {
        must
          "not(../acl-permit or ../qos-enhanced or
               ../enh-sr-policy or ../ingress-sr-mspw or
               ../tx-scale-enhanced)";
        presence "Indicates a ingress-sr node is configured.";
        description
          "Enable ingress SR stats profile counter.";
      }
      container enh-sr-policy {
        must
          "not(../acl-permit or ../qos-enhanced or
               ../ingress-sr or ../ingress-sr-mspw or
               ../tx-scale-enhanced)";
        presence "Indicates a enh-sr-policy node is configured.";
        description
          "Enable Enhanced_SR_Policy_Scale stats profile counter.";
      }
      container ingress-sr-mspw {
        must
          "not(../acl-permit or ../qos-enhanced or
               ../ingress-sr or ../enh-sr-policy or
               ../tx-scale-enhanced)";
        presence "Indicates a ingress-sr-mspw node is configured.";
        description
          "Enable ingress SR & MSPW stats profile counter.";
      }
      container tx-scale-enhanced {
        must
          "not(../qos-enhanced or ../ingress-sr or
               ../enh-sr-policy or ../ingress-sr-mspw or
               ../acl-permit)";
        presence "Indicates a tx-scale-enhanced node is configured.";
        description
          "Enable enhanced TX stats scale (Non L2 stats).";
        container acl-permit {
          must "not(../qos-enhanced or ../ingress-sr)";
          presence "Indicates a acl-permit node is configured.";
          description
            "Enable ACL permit stats.";
        }
        container qos-enhanced {
          must "not(../acl-permit or ../ingress-sr)";
          presence "Indicates a qos-enhanced node is configured.";
          description
            "Enable enhanced QoS stats.";
        }
        container ingress-sr {
          must "not(../qos-enhanced or ../acl-permit)";
          presence "Indicates a ingress-sr node is configured.";
          description
            "Enable ingress SR stats profile counter.";
        }
      }
    }
    container profile-flowspec {
      description
        "Configure support for v6 flowspec";
      container v6-enable {
        presence "Indicates a v6-enable node is configured.";
        description
          "Configure support for v6 flowspec";
      }
      container v6-enable-locations {
        description
          "Location of flowspec config";
        list location {
          key "location-name location-name2";
          description
            "Location of flowspec config";
          leaf location-name {
            type xr:Node-id;
            description
              "Location of flowspec config";
          }
          leaf location-name2 {
            type xr:Node-id;
            description
              "Location of flowspec config";
          }
        }
      }
    }
    container profile-segment-routing {
      description
        "Segment routing options";
      container srv6 {
        description
          "Configure support for SRv6 and its paramaters";
        container mode {
          description
            "Mode of operation";
          container base {
            must "not(../micro-segment/format/f3216 or ../base-and-micro-segment-f3216)";
            presence "Indicates a base node is configured.";
            description
              "Base SRv6 (Format-1) support only";
          }
          container base-and-micro-segment-f3216 {
            must "not(../micro-segment/format/f3216 or ../base)";
            presence "Indicates a base-and-micro-segment-f3216 node is configured.";
            description
              "Base (F1) and F3216 co-existence support";
          }
          container micro-segment {
            description
              "Micro-segment support only";
            container format {
              description
                "Specify carrier format";
              container f3216 {
                must "not(../../../base or ../../../base-and-micro-segment-f3216)";
                presence "Indicates a f3216 node is configured.";
                description
                  "32-bit block and 16-bit IDs";
              }
              container path-mtu {
                must "../f3216";
                presence "Indicates a path-mtu node is configured.";
                description
                  "Path MTU Discovery for the SRv6 profile";
              }
            }
          }
          container encapsulation {
            description
              "Encapsulation parameters";
            container l2-traffic {
              description
                "SRv6 parameters for L2 traffic type";
              container traffic-class {
                description
                  "Control traffic-class field of SRv6 IPv6 header";
                container propagate {
                  must "not(../traffic-class-value)";
                  presence "Indicates a propagate node is configured.";
                  description
                    "Propagate traffic-class from incoming packet/frame or use qos-group from input policy-map";
                }
                container policy-map-extend {
                  must "not(../propagate or ../traffic-class-value)";
                  presence "Indicates a policy-map node is configured.";
                  description
                    "Set traffic-class DSCP to set ip encap cos <val> selected by input policy-map";
                }
                leaf traffic-class-value {
                  type uint32 {
                    range "0..255" {
                      description
                        "Traffic-class value (specified as 2 hexadecimal nibbles)";
                    }
                  }
                  must "not(../propagate)";
                  description
                    "Traffic-class value (specified as 2 hexadecimal nibbles)";
                }
              }
            }
            container l3-traffic {
              description
                "SRv6 parameters for L3 traffic type";
              container traffic-class {
                description
                  "Control traffic-class field of SRv6 IPv6 header";
                container propagate {
                  must "not(../policy-map or ../traffic-class-value)";
                  presence "Indicates a propagate node is configured.";
                  description
                    "Propagate traffic-class from incoming packet";
                }
                container policy-map {
                  must "not(../propagate or ../traffic-class-value)";
                  presence "Indicates a policy-map node is configured.";
                  description
                    "Set traffic-class DSCP to qos-group selected by input policy-map";
                }
                container policy-map-extend {
                  must "not(../propagate or ../traffic-class-value)";
                  presence "Indicates a policy-map node is configured.";
                  description
                    "Set traffic-class DSCP to set ip encap cos <val> selected by input policy-map";
                }
                leaf traffic-class-value {
                  type uint32 {
                    range "0..255" {
                      description
                        "Traffic-class value (specified as 2 hexadecimal nibbles)";
                    }
                  }
                  must "not(../propagate or ../policy-map)";
                  description
                    "Traffic-class value (specified as 2 hexadecimal nibbles)";
                }
              }
              container traffic-class-with-hoplimit {
                description
                  "Control traffic-class and hop-limit of SRv6 IPv6 header";
                container propagate {
                  must "not(../../traffic-class/propagate or ../../traffic-class/policy-map or ../../traffic-class/traffic-class-value)";
                  presence "Indicates a propagate node is configured.";
                  description
                    "Propagate traffic-class and hop-limit from incoming packet";
                }
              }
            }
          }
        }
      }
    }
    container profile-offload {
      description
        "Offload profile in NCS5501-SE";
      container one {
        must "not(../two or ../three or ../four)";
        presence "Indicates a one node is configured.";
        description
          "BFDv6 and Bsync";
      }
      container two {
        must "not(../one or ../three or ../four)";
        presence "Indicates a two node is configured.";
        description
          "BFDv6 and Route download";
      }
      container three {
        must "not(../one or ../two or ../four)";
        presence "Indicates a three node is configured.";
        description
          "Route download and Bsync";
      }
      container four {
        must "not(../one or ../two or ../three)";
        presence "Indicates a four node is configured.";
        description
          "BFDv6 and PM-HW-Offload";
      }
    }
    container profile-sr-policy {
      description
        "SR Policy options";
      container v6-null-label-autopush {
        presence "Indicates a v6-null-label-autopush node is configured.";
        description
          "Configure IPV6 NULL label autopush for SR policy";
      }
    }
    leaf profile-bw-threshold {
      type xr:Cisco-ios-xr-string {
        length "1..3" {
          description
            "value in percent: 0-100,in increments of 10";
        }
        pattern "(100|[1-9]?0|0)";
      }
      description
        "Asic Fabric Link Bandwidth Availability Threshold";
    }
    container profile-oam {
      description
        "Configure oam profile";
      container sat-enable {
        presence "Indicates a sat-enable node is configured.";
        description
          "enable SAT feature";
      }
      container four8byte-cfm-maid-enable {
        presence "Indicates a four8byte-cfm-maid-enable node is configured.";
        description
          "Enable 48byte cfm maid feature";
      }
    }
    container mpls-ext-dscp-preserve {
      description
        "Preserve dscp with large label stack";
      container v4uc-enable {
        presence "Indicates a v4uc-enable node is configured.";
        description
          "Enable to preseve dscp for ipv4 unicast traffic";
      }
      container v6uc-enable {
        presence "Indicates a v6uc-enable node is configured.";
        description
          "Enable to preseve dscp for ipv6 unicast traffic";
      }
    }
    container profile-priority-flow-control {
      description
        "Configure priority-flow-control parameters";
      container traffic-classes {
        description
          "configure traffic-class";
        list traffic-class {
          key "traffic-class-id";
          description
            "configure traffic-class";
          leaf traffic-class-id {
            type uint32 {
              range "0..7" {
                description
                  "Traffic-class";
              }
            }
            description
              "configure traffic-class";
          }
          leaf pause-threshold {
            type uint32 {
              range "1..4294967295" {
                description
                  "pause-threshold (bytes)";
              }
            }
            mandatory true;
            description
              "configure pause-threshold";
          }
          leaf resume-threshold {
            type uint32 {
              range "1..4294967295" {
                description
                  "resume-threshold (bytes)";
              }
            }
            mandatory true;
            description
              "configure resume-threshold";
          }
          leaf headroom {
            type uint32 {
              range "1..4294967295" {
                description
                  "headroom (bytes)";
              }
            }
            mandatory true;
            description
              "configure headroom";
          }
        }
      }
      container traffic-class-locations {
        description
          "Location to apply PFC configuration";
        list traffic-class-location {
          key "location-name location-name2 traffic-class-id";
          description
            "Location to apply PFC configuration";
          leaf location-name {
            type xr:Node-id;
            description
              "Location to apply PFC configuration";
          }
          leaf location-name2 {
            type xr:Node-id;
            description
              "Location to apply PFC configuration";
          }
          leaf traffic-class-id {
            type uint32 {
              range "0..7" {
                description
                  "Traffic-class";
              }
            }
            description
              "configure traffic-class";
          }
          leaf pause-threshold {
            type uint32 {
              range "1..4294967295" {
                description
                  "pause-threshold (bytes)";
              }
            }
            mandatory true;
            description
              "configure pause-threshold";
          }
          leaf resume-threshold {
            type uint32 {
              range "1..4294967295" {
                description
                  "resume-threshold (bytes)";
              }
            }
            mandatory true;
            description
              "configure resume-threshold";
          }
          leaf headroom {
            type uint32 {
              range "1..4294967295" {
                description
                  "headroom (bytes)";
              }
            }
            mandatory true;
            description
              "configure headroom";
          }
        }
      }
    }
    container profile-routing {
      description
        "Configure the node's routing profile";
      container role {
        description
          "Configure the node's routing role";
        container core {
          presence "Indicates a core node is configured.";
          description
            "Configure the routing role as a core router";
        }
      }
      container span-filter {
        description
          "Configure span filter profile for DNS, HTTP, HTTPS and TLS packet mirror filtering";
        container l2-rx-enable {
          presence "Indicates a l2-rx-enable node is configured.";
          description
            "enable the l2 traffic rx span filtering profile";
        }
        container l2-l3-tx-enable {
          presence "Indicates a l2-l3-tx-enable node is configured.";
          description
            "enable the l2 l3 traffic tx span filtering profile";
        }
      }
    }
    container bundle-pindown-bum-optimization {
      description
        "To configure bundle-pindown-bum-optimization";
      container enable {
        presence "Indicates a enable node is configured.";
        description
          "Enable bundle pindown bum-optimization mode";
      }
    }
    container storm-control-combine-policer-bw {
      description
        "To configure combine policer for storm control of BUM Traffic";
      container enable {
        presence "Indicates a enable node is configured.";
        description
          "Enable storm-control-combine-policer-bw mode";
      }
    }
    container l2-replication {
      description
        "Enable core replication optimization for L2 BUM Traffic";
      container core-optimized {
        presence "Indicates a core-optimized node is configured.";
        description
          "Enable core replication optimization for L2 BUM Traffic";
      }
    }
    container tcam {
      description
        "Configure profile for TCAM LC cards";
      container fib {
        description
          "Forwarding table to configure";
        container ipv4 {
          description
            "Configure ipv4 protocol";
          container scaledisable {
            presence "Indicates a scaledisable node is configured.";
            description
              "Configure scale mode for TCAM card";
          }
        }
      }
    }
    container fib {
      description
        "Forwarding table to configure";
      container ipv4 {
        description
          "Configure ipv4 protocol";
        container scale {
          description
            "Configure scale mode for no-TCAM card";
          container host-optimized-disable {
            must "not(../internet-optimized)";
            presence "Indicates a host-optimized-disable node is configured.";
            description
              "Configure Host optimization by default";
          }
          container internet-optimized {
            must "not(../host-optimized-disable)";
            presence "Indicates a internet-optimized node is configured.";
            description
              "Configure Internet optimized (DEPRECATED)";
          }
        }
      }
      container ipv6 {
        description
          "Configure ipv6 protocol";
        container scale {
          description
            "Configure scale mode for no-TCAM card";
          container internet-optimized-disable {
            presence "Indicates a internet-optimized-disable node is configured.";
            description
              "Configure by default Intetrnet optimized";
          }
          leaf custom-lem {
            type uint32 {
              range "40..64" {
                description
                  "IPv6 prefix length.";
              }
            }
            description
              "Customise the prefix distribution to LEM";
          }
        }
      }
      container mpls {
        description
          "Configure mpls protocol";
        container ldp {
          presence "Indicates a ldp node is configured.";
          description
            "Configure signalling protocol for MPLS";
          container lsr-optimized {
            presence "Indicates a lsr-optimized node is configured.";
            description
              "Configure optimization for LSR role";
          }
        }
        container label {
          description
            "Configure MPLS label convergence optimization for LDP/SR labels";
          container lsr-optimized {
            presence "Indicates a lsr-optimized node is configured.";
            description
              "Configure LSR optimization";
          }
          container tcam-optimized {
            presence "Indicates a tcam-optimized node is configured.";
            description
              "Configure push label in tcam optimization";
          }
        }
        container bgp-sr {
          presence "Indicates a bgp-sr node is configured.";
          description
            "Configure BGP label convergence optimization for SR labels. Applicable only for Jericho based routers.";
          container lsr-optimized {
            presence "Indicates a lsr-optimized node is configured.";
            description
              "Configure optimization for LSR role";
          }
        }
        container ttl {
          presence "Indicates a ttl node is configured.";
          description
            "Configure ttl propagation behaviour";
          container propagate-exception {
            presence "Indicates a propagate-exception node is configured.";
            description
              "Propagate TTL on disposition in mixed paths use case";
          }
        }
        container two-label-tcam-optimized {
          description
            "Keep L3VPN BGP PIC push labels in OP2 TCAM for NCS57xx/IOSXRBD";
          container all {
            must "not(../selective)";
            presence "Indicates a all node is configured.";
            description
              "Two-label-tcam for all VRF";
          }
          container selective {
            must "not(../all)";
            presence "Indicates a selective node is configured.";
            description
              "Selectively apply two-label-tcam based on per-vrf CLI option under vrf";
          }
        }
        container ip-ttl-propagate-disable {
          description
            "Exception of IP TTL Propagate disable configuration";
          container exclude {
            description
              "Exclude the behaviour for various MPLS label operations";
            container mpls-push {
              description
                "MPLS PUSH label operation";
              container ttl {
                presence "Indicates a ttl node is configured.";
                description
                  "Configure for TTL behaviour";
              }
            }
            container mpls-pop {
              description
                "MPLS POP label operation";
              container ttl-and-cos {
                presence "Indicates a ttl-and-cos node is configured.";
                description
                  "Configure for TTL and COS behaviour";
              }
            }
            container mpls-pop-penultimate-hop {
              description
                "MPLS Penultimate-Hop label operation";
              container ttl-and-cos {
                presence "Indicates a ttl-and-cos node is configured.";
                description
                  "Configure for TTL and COS behaviour";
              }
              container cos {
                presence "Indicates a cos node is configured.";
                description
                  "Configure for COS behaviour";
              }
              container ttl {
                presence "Indicates a ttl node is configured.";
                description
                  "Configure for TTL behaviour";
              }
            }
          }
        }
        container php {
          description
            "Preserve DSCP for MPLS penultimate hop node";
          container dscp-preserve {
            presence "Indicates a dscp-preserve node is configured.";
            description
              "Preserve IPv4.DSCP and IPv6.TC in MPLS PHP flow with TTL being propagated";
          }
        }
      }
      container bgppa {
        description
          "BGP policy accounting";
        container stats-mode {
          description
            "stats accounting mode";
          container main-intf {
            must "not(../sub-intf)";
            presence "Indicates a main-intf node is configured.";
            description
              "Account the BGP-PA stats for main interface";
          }
          container sub-intf {
            must "not(../main-intf)";
            presence "Indicates a sub-intf node is configured.";
            description
              "Account the BGP-PA stats for sub interface";
          }
        }
      }
      container recycle {
        description
          "Recycle traffic";
        container service-over-rsvpte {
          presence "Indicates a service-over-rsvpte node is configured.";
          description
            "Recycle traffic for BGP services going over RSVP TE";
        }
      }
      container urpf {
        description
          "Unicast Reverse Path Forwarding";
        container disable {
          presence "Indicates a disable node is configured.";
          description
            "Disable uRPF";
        }
      }
    }
    container bgp-ip {
      description
        "BGP IP";
      container if-peering {
        description
          "Interface Peering";
        container collapse {
          presence "Indicates a collapse node is configured.";
          description
            "Collapse";
        }
      }
    }
    container oversubscription {
      description
        "Configure oversubscription";
      container prioritize {
        description
          "Setting prioritization of CoS values";
        list interface {
          must "cos/cos-value or untagged";
          key "interface-name";
          description
            "Setting prioritization of CoS values";
          leaf interface-name {
            type xr:Interface-name;
            description
              "Interface name";
          }
          container cos {
            description
              "CoS values between 0-5";
            list cos-value {
              key "value";
              description
                "CoS values between 0-5";
              leaf value {
                type uint32 {
                  range "0..5" {
                    description
                      "configure CoS number 0-5";
                  }
                }
                description
                  "CoS values between 0-5";
              }
            }
          }
          container untagged {
            presence "Indicates a untagged node is configured.";
            description
              "Prioritize untagged packets";
          }
        }
      }
    }
    container vrrpscale {
      description
        "to scale VRRP sessions";
      container enable {
        presence "Indicates a enable node is configured.";
        description
          "enable VRRP scaling";
      }
    }
    container fib-bgp-pic {
      description
        "Prefix Independent Convergnce";
      container multipath-core {
        description
          "Multipath pic core in forwarding chain";
        container enable {
          presence "Indicates a enable node is configured.";
          description
            "Enable pic core in forwarding chain";
        }
      }
      container level-3 {
        description
          "level-3: BGP service over BGP Labelled Unicast";
        container l2services {
          presence "Indicates a l2services(EVPN) node is configured.";
          description
            "Enable BGP-PIC for l2services over BGP Labelled Unicast (only EVPN is supported)";
        }
      }
    }
    container bgp-mp-pic {
      description
        "Multipath Prefix Independent Convergence";
      container auto-protect {
        description
          "Multipath Auto Protection";
        container enable {
          presence "Indicates a enable node is configured.";
          description
            "Enable pic core in forwarding chain";
        }
      }
    }
    container fib-dlb {
      description
        "Destination Based Load balancing";
      container level-1 {
        description
          "DLB at level 1 of forwarding chain";
        container enable {
          presence "Indicates a enable node is configured.";
          description
            "DLB at level 1 of forwarding chain";
        }
      }
    }
    container disable-trap {
      description
        "Disable h/w trap";
      container rx-trap-ip-comp-mc-invalid-ip {
        presence "Indicates a rx-trap-ip-comp-mc-invalid-ip node is configured.";
        description
          "Disable RxTrapIpCompMcInvalidIp in hw";
      }
    }
    container irb {
      description
        "Configure IRB Forwarding model";
      container l2-l3 {
        description
          "IRB L2-L3 options";
        container one-pass {
          must "not(../two-pass)";
          presence "Indicates a one-pass node is configured.";
          description
            "Move IRB processing to 1 pass on ingress";
        }
        container two-pass {
          must "not(../one-pass)";
          presence "Indicates a two-pass node is configured.";
          description
            "Move IRB processing to 2 pass on ingress";
        }
      }
      container l3-l2 {
        description
          "IRB L3-L2 options";
        container two-pass {
          presence "Indicates a two-pass node is configured.";
          description
            "Move IRB processing to 2 pass on egress";
        }
      }
    }
    container multicast {
      description
        "Configure multicast properties";
      container access-pw-enable {
        presence "Indicates a access-pw-enable node is configured.";
        description
          "Enable Multicast Access PW [L3L2 IRB 2Pass Processing]";
      }
    }
    container gue {
      description
        "GUE Version 1 Port Configuration";
      container udp {
        description
          "UDP Decap";
        container dest-port-ipv4s {
          description
            "Configure unreserved udp port number for Ipv4 payload";
          list dest-port-ipv4 {
            key "dest-port-ipv4-number dest-port-ipv6-number";
            description
              "Configure unreserved udp port number for Ipv4 payload";
            leaf dest-port-ipv4-number {
              type uint32 {
                range "0..64000" {
                  description
                    "value in decimal";
                }
              }
              description
                "Configure unreserved udp port number for Ipv4 payload";
            }
            leaf dest-port-ipv6-number {
              type uint32 {
                range "0..64000" {
                  description
                    "value in decimal";
                }
              }
              description
                "Configure unreserved udp port number for Ipv6 payload";
            }
            leaf dest-port-mpls {
              type uint32 {
                range "0..64000" {
                  description
                    "value in decimal";
                }
              }
              mandatory true;
              description
                "Configure unreserved udp port number for Mpls payload";
            }
          }
        }
      }
    }
    leaf li-recycle-bw {
      type uint32 {
        range "10..200" {
          description
            "LI Recycle Bandwidth in Gbps";
        }
      }
      description
        "Configure LI profile for recycle bandwidth";
    }
  }
}
