module Cisco-IOS-XR-envmon-oper {
  namespace "http://cisco.com/ns/yang/Cisco-IOS-XR-envmon-oper";
  prefix envmon-oper;

  import Cisco-IOS-XR-types {
    prefix xr;
  }
  import cisco-semver {
    prefix semver;
  }
  include Cisco-IOS-XR-envmon-oper-sub2 {
    revision-date 2025-08-07;
  }
  include Cisco-IOS-XR-envmon-oper-sub1 {
    revision-date 2025-08-07;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR envmon package operational data.
     
     This module contains definitions
     for the following management objects:
       environmental-monitoring: Environmental Monitoring Operational
         data space
       power-management: Power tray and power module management
     
     Copyright (c) 2013-2025 by Cisco Systems, Inc.
     All rights reserved.";

  revision 2025-08-07 {
    description
      "IOS XR 25.4.1 revision. Addition of port related data";
    semver:module-version "2.1.0";
  }
  revision 2021-06-10 {
    description
      "IOS XR 7.5.1 revision. Decoupled chassis sensors from being reported as part of RP card";
    semver:module-version "1.2.0";
  }
  revision 2020-09-25 {
    description
      "IOS XR 7.3.1 revision. Added alarm port oper commands.";
    semver:module-version "1.1.0";
  }
  revision 2020-04-07 {
    description
      "IOS XR 7.2.1 revision. Added extra description to interpret Threshold Value -32768.";
    semver:module-version "1.1.0";
  }
  revision 2019-04-05 {
    description
      "Establish semantic version baseline.";
    semver:module-version "1.0.0";
  }
  revision 2015-11-09 {
    description
      "IOS XR 6.0 revision.";
  }

  container environmental-monitoring {
    config false;
    description
      "Environmental Monitoring Operational data space";
    list rack {
      key "name";
      description
        "Information about rack";
      container nodes {
        description
          "Information on nodes under a rack";
        list node {
          key "node";
          description
            "List of nodes under a rack";
          container sensor-types {
            description
              "Information related to sensors organised by
               type";
            list sensor-type {
              key "type";
              description
                "Information per sensor type";
              container sensor-names {
                description
                  "Information about sensors of the specified
                   type";
                list sensor-name {
                  key "name";
                  description
                    "Information about sensors of the specified
                     type, by name";
                  leaf name {
                    type string;
                    description
                      "Sensor name";
                  }
                  uses SPI-ENVMON-SENSOR-DATA-B;
                }
              }
              leaf type {
                type xr:Cisco-ios-xr-string;
                description
                  "Sensor Type";
              }
            }
          }
          container ports {
            description
              "Information on ports under a node";
            list port {
              key "name";
              description
                "List of ports under node";
              container port-sensor-types {
                description
                  "Information related to sensors organised by
                   type";
                list port-sensor-type {
                  key "type";
                  description
                    "Information per sensor type";
                  container sensor-name-ports {
                    description
                      "Information about sensors of the
                       specified type";
                    list sensor-name-port {
                      key "name";
                      description
                        "Information about sensors of the
                         specified type, by name";
                      leaf name {
                        type string;
                        description
                          "Sensor name";
                      }
                      uses SPI-ENVMON-SENSOR-DATA-B;
                    }
                  }
                  leaf type {
                    type xr:Cisco-ios-xr-string;
                    description
                      "Sensor Type";
                  }
                }
              }
              leaf name {
                type xr:Cisco-ios-xr-string;
                description
                  "Port name";
              }
            }
          }
          leaf node {
            type xr:Node-id;
            description
              "Node ID";
          }
        }
      }
      leaf name {
        type xr:Cisco-ios-xr-string;
        description
          "Rack name";
      }
    }
  }
  container power-management {
    config false;
    description
      "Power tray and power module management";
    list rack {
      key "name";
      description
        "Rack identifiers for power modules";
      container producers {
        description
          "Power producers information";
        container producer-nodes {
          description
            "Table of power producer nodes";
          list producer-node {
            key "node";
            description
              "Power producer node identifier";
            leaf node {
              type xr:Node-id;
              description
                "Node ID";
            }
            uses PRODUCER-PWR-PT-INFO-B;
          }
        }
      }
      container chassis {
        description
          "Chassis level information";
        uses CHASSIS-PWR-INFO-B;
      }
      container consumers {
        description
          "Power consumers information";
        container consumer-nodes {
          description
            "Table of power consumer nodes";
          list consumer-node {
            key "node";
            description
              "Consumer node identifier";
            leaf node {
              type xr:Node-id;
              description
                "Node ID";
            }
            uses CONSUMER-PWR-INFO-B;
          }
        }
      }
      leaf name {
        type xr:Cisco-ios-xr-string;
        description
          "Rack name";
      }
    }
  }
}
