module Cisco-IOS-XR-ip-rib-cfg {
  namespace "http://cisco.com/ns/yang/Cisco-IOS-XR-ip-rib-cfg";
  prefix ip-rib-cfg;

  import Cisco-IOS-XR-types {
    prefix xr;
  }
  import cisco-semver {
    prefix semver;
  }
  import Cisco-IOS-XR-infra-rsi-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ip-rib package configuration.
     
     This model is deprecated and is replaced by
     Cisco-IOS-XR-um-router-rib-cfg.yang which will provide the
     compatible functionalities.
     
     This module contains definitions
     for the following management objects:
       rib: RIB configuration.
     
     This YANG module augments the
       Cisco-IOS-XR-infra-rsi-cfg
     module with configuration data.
     
     Copyright (c) 2013-2026 by Cisco Systems, Inc.
     All rights reserved.";

  revision 2026-03-01 {
    description
      "Added config for rib path viability frr-reversion disable";
    semver:module-version "1.2.0";
  }
  revision 2024-06-27 {
    description
      "Added vrf default topo default node and nodes for tag-map feature
       2024-03-04
          Updated ip-only config to store vrf name in activate leaf
       2024-01-29
          Updated ip-only config to include vrf name
       2023-09-21
          Added ip-only config
       2023-07-12
          Added sr-mpls-preserve-label-forwarding config";
    semver:module-version "1.1.0";
  }
  revision 2019-05-12 {
    description
      "Deprecated the native model, replaced by UM model.";
    semver:module-version "1.0.1";
  }
  revision 2019-04-05 {
    description
      "Establish semantic version baseline.";
  }
  revision 2017-07-31 {
    description
      "Fixed missing augmentation from multiple MDA parent.";
  }
  revision 2015-11-09 {
    description
      "IOS XR 6.0 revision.";
  }

  typedef Sr-mpls-preserve-label-forwarding-mode {
    type enumeration {
      enum "sr-mpls-preserve-disable" {
        value 0;
        description
          "Disable";
      }
      enum "sr-mpls-preserve-acl" {
        value 2;
        description
          "Access-list to limit the behavior to set of
           prefixes";
      }
      enum "sr-mpls-preserve-acl-inverse" {
        value 3;
        description
          "Apply ACL inversely (permit becomes deny and
           vice versa)";
      }
    }
    description
      "Sr mpls preserve label forwarding mode";
  }

  typedef Tag-mapping-flag-name-enum {
    type enumeration {
      enum "level-2-used-as-nexthop" {
        value 1;
        description
          "The flag to set on routes with matching tag";
      }
    }
    description
      "Tag mapping flag name enum";
  }

  grouping NEXT-HOP-DAMPENING-DISABLE {
    description
      "Common node of ipv4, ipv6";
    leaf next-hop-dampening-disable {
      type empty;
      description
        "Disable next-hop dampening";
    }
  }

  grouping REDISTRIBUTION-HISTORY {
    description
      "Common node of ipv4, ipv6";
    container redistribution-history {
      description
        "Redistribution history related configs";
      container keep {
        description
          "Retain redistribution history after disconnect.";
        leaf bcdl {
          type empty;
          description
            "Enable retain BCDL history";
        }
      }
      leaf bcdl-client {
        type uint32 {
          range "10..2000000";
        }
        description
          "Maximum BCDL redistribution history size.";
      }
      leaf protocol-client {
        type uint32 {
          range "10..250000";
        }
        description
          "Maximum protocol redistribution history size.";
      }
    }
  }

  grouping SR-MPLS-PRESERVE-LABEL-FORWARDING {
    description
      "Common node of ipv4, ipv6";
    container sr-mpls-preserve-label-forwarding {
      description
        "Maintain SR label forwarding entry in FIB even
         if another source is preferred for the prefix";
      leaf sr-mpls-preserve-mode {
        type Sr-mpls-preserve-label-forwarding-mode;
        description
          "SR-MPLS label forwarding preserve mode";
      }
      leaf name {
        type string;
        description
          "Name of ACL/RPL to limit SR Label Forwarding
           preserve behavior";
      }
    }
  }

  augment "/a1:vrfs/a1:vrf/a1:afs/a1:af" {
    description
      "This augment extends the configuration data of
       'Cisco-IOS-XR-infra-rsi-cfg'";
    container maximum-prefix {
      presence "Indicates a maximum-prefix node is configured.";
      status deprecated;
      description
        "This model is deprecated and is replaced by
         Cisco-IOS-XR-um-router-rib-cfg.yang which will
         provide the compatible functionalities.  Set
         maximum prefix limits";
      leaf prefix-limit {
        type uint32 {
          range "32..10000000";
        }
        mandatory true;
        description
          "Set table's maximum prefix limit";
      }
      leaf mid-threshold {
        type uint32 {
          range "1..100";
        }
        description
          "Mid-threshold (% of maximum)";
      }
    }
  }
  augment "/a1:global-af/a1:afs/a1:af" {
    description
      "This augment extends the configuration data of
       'Cisco-IOS-XR-infra-rsi-cfg'";
    container maximum-prefix {
      presence "Indicates a maximum-prefix node is configured.";
      status deprecated;
      description
        "This model is deprecated and is replaced by
         Cisco-IOS-XR-um-router-rib-cfg.yang which will
         provide the compatible functionalities.  Set
         maximum prefix limits";
      leaf prefix-limit {
        type uint32 {
          range "32..10000000";
        }
        mandatory true;
        description
          "Set table's maximum prefix limit";
      }
      leaf mid-threshold {
        type uint32 {
          range "1..100";
        }
        description
          "Mid-threshold (% of maximum)";
      }
    }
  }
  container rib {
    status deprecated;
    description
      "This model is deprecated and is replaced by
       Cisco-IOS-XR-um-router-rib-cfg.yang which will
       provide the compatible functionalities.  RIB
       configuration.";
    container default-vrf {
      description
        "Default VRF";
      container address-family {
        description
          "Address family";
        container afi-all {
          description
            "Address family";
          container table {
            description
              "RIB special routing-table";
            container ip-only {
              description
                "Table of routes with IP-only nexthop(s)";
              leaf activate {
                type xr:Cisco-ios-xr-string {
                  length "1..32";
                }
                description
                  "Name of ip-only VRF to be activated";
              }
            }
            container default {
              description
                "RIB default table/topo";
              container tags {
                description
                  "Mapping of route tags to route flags";
                list tag {
                  key "tag";
                  description
                    "A configured route tag mapping";
                  leaf tag {
                    type uint32 {
                      range "1..4294967295";
                    }
                    description
                      "Tag";
                  }
                  leaf flag {
                    type Tag-mapping-flag-name-enum;
                    mandatory true;
                    description
                      "Name of the flag to set for routes with
                       matching tag configured";
                  }
                }
              }
            }
          }
        }
      }
    }
    container af {
      description
        "RIB address family configuration";
      container ipv4 {
        description
          "IPv4 configuration";
        uses SR-MPLS-PRESERVE-LABEL-FORWARDING;
        uses NEXT-HOP-DAMPENING-DISABLE;
        uses REDISTRIBUTION-HISTORY;
      }
      container ipv6 {
        description
          "IPv6 configuration";
        uses SR-MPLS-PRESERVE-LABEL-FORWARDING;
        uses NEXT-HOP-DAMPENING-DISABLE;
        uses REDISTRIBUTION-HISTORY;
      }
    }
    container path-viability {
      description
        "Configure path-viability feature related
         parameters";
      container frr-reversion {
        description
          "Configure FRR-Reversion related parameters";
        leaf disable {
          type empty;
          description
            "Disable the FRR-Reversion upon a
             viability-tracked down path comes back up";
        }
      }
    }
    leaf max-recursion-depth {
      type uint32 {
        range "5..16";
      }
      description
        "Set maximum depth for route recursion check";
    }
  }
}
