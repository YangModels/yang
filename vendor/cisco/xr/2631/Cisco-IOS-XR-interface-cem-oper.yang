module Cisco-IOS-XR-interface-cem-oper {
  namespace "http://cisco.com/ns/yang/Cisco-IOS-XR-interface-cem-oper";
  prefix interface-cem-oper;

  import Cisco-IOS-XR-types {
    prefix xr;
  }
  import cisco-semver {
    prefix semver;
  }
  include Cisco-IOS-XR-interface-cem-oper-sub2 {
    revision-date 2024-04-19;
  }
  include Cisco-IOS-XR-interface-cem-oper-sub1 {
    revision-date 2024-04-19;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR interface-cem package operational data.
     
     This module contains definitions
     for the following management objects:
       cem: CEM operational data
     
     Copyright (c) 2013-2024 by Cisco Systems, Inc.
     All rights reserved.";

  revision 2024-04-19 {
    description
      "Added leaf for CEM interface to support the Packet loss threshold timer value.";
    semver:module-version "2.1.0";
  }
  revision 2021-08-18 {
    description
      "Configured, operational, in-use fields for dejitter and configured, operational fields for payload are added.
       2021-07-20
           CEM interface payload-dejitter-mapping and capabilities command added.
       2021-06-06
           CEM interface oper command added.";
    semver:module-version "2.0.0";
  }
  revision 2019-04-05 {
    description
      "Establish semantic version baseline.";
    semver:module-version "1.0.0";
  }
  revision 2015-11-09 {
    description
      "IOS XR 6.0 revision.";
  }

  container cem {
    config false;
    description
      "CEM operational data";
    container cem-controllers {
      description
        "List of CEM interfaces";
      list cem-controller {
        key "interface-name";
        description
          "CEM interface name";
        container cem-recovered-clock-info {
          description
            "CEM Recovered clock information";
          uses CEM-RECOVERED-CLOCK-DATA;
        }
        container cem-info {
          description
            "CEM controller information";
          uses CEM-INFO;
        }
        container cem-client-capabilites-info {
          description
            "CEM client capabilities information";
          uses CEM-CLIENT-CAPABILITIES-INFO;
        }
        container cem-payload-dejitter-mapping-info {
          description
            "CEM Payload dejitter Mapping information";
          uses CEM-PAYLOAD-DEJITTER-MAPPING-INFO;
        }
        leaf interface-name {
          type xr:Interface-name;
          description
            "Name of the CEM Interface";
        }
      }
    }
  }
}
