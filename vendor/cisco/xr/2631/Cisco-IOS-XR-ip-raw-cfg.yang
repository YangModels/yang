module Cisco-IOS-XR-ip-raw-cfg {
  namespace "http://cisco.com/ns/yang/Cisco-IOS-XR-ip-raw-cfg";
  prefix ip-raw-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ip-raw package configuration.
     
     This module contains definitions
     for the following management objects:
       ip-raw: Global IP RAW configuration
     
     Copyright (c) 2013-2026 by Cisco Systems, Inc.
     All rights reserved.";

  revision 2026-06-17 {
    description
      "Removed debug directory config from production model.";
    semver:module-version "2.0.0";
  }
  revision 2019-04-05 {
    description
      "Establish semantic version baseline.";
    semver:module-version "1.0.1";
  }
  revision 2015-11-09 {
    description
      "IOS XR 6.0 revision.";
  }

  container ip-raw {
    description
      "Global IP RAW configuration";
    container num-thread {
      presence "Indicates a num-thread node is configured.";
      description
        "RAW InQueue and OutQueue threads";
      leaf raw-in-q-threads {
        type uint32 {
          range "1..16";
        }
        mandatory true;
        description
          "InQ Threads";
      }
      leaf raw-out-q-threads {
        type uint32 {
          range "1..16";
        }
        mandatory true;
        description
          "OutQ Threads";
      }
    }
    leaf receive-q {
      type uint32 {
        range "40..800";
      }
      description
        "RAW receive Queue Size";
    }
  }
}
