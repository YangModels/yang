module Cisco-IOS-XR-um-config-commit-cfg {
  namespace "http://cisco.com/ns/yang/Cisco-IOS-XR-um-config-commit-cfg";
  prefix um-config-commit-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR config-commit package configuration.
     
     This YANG module augments the
     modules with configuration data.
     
     Copyright (c) 2022-2025 by Cisco Systems, Inc., and/or its affiliates.
     All rights reserved.";

  revision 2023-01-20 {
    description
      "Fix aes password datatype.";
    semver:module-version "2.0.0";
  }
  revision 2021-04-14 {
    description
      "Initial release";
    semver:module-version "1.0.0";
  }

  container configuration {
    description
      "Configuration related settings ";
    container commit {
      description
        "auto-save the running configuration";
      container auto-save {
        presence "Indicates a auto-save node is configured.";
        description
          "auto-save the running configuration";
        container filename {
          presence "Indicates a filename node is configured.";
          description
            "filename to auto-save";
          leaf protocol {
            type string {
              length "1..800" {
                description
                  "protocol (e.g. sftp:, /disk0:/, PWD, etc...)";
              }
            }
            mandatory true;
            description
              "protocol (e.g. sftp:, /disk0:/, PWD, etc...)";
          }
          leaf url-remainder {
            type string {
              length "1..800" {
                description
                  "url remainder";
              }
            }
            mandatory true;
            description
              "url remainder";
          }
        }
        container password {
          description
            "The password for the remote url";
          container encrypted {
            description
              "Specifies an ENCRYPTED password";
            leaf encryption-default {
              type xr:Proprietary-password;
              must "not(../encryption-aes)";
              description
                "Specifies password in default encrypted form";
            }
            leaf encryption-aes {
              type xr:Type6-password;
              must "not(../encryption-default)";
              description
                "Specifies the password in aes encrypted form";
            }
          }
        }
        leaf maximum {
          type uint32 {
            range "1..4294967295" {
              description
                "How many rotating autosaves to keep";
            }
          }
          description
            "How many rotating autosaves to keep";
        }
        container wait-time {
          presence "Indicates a wait-time node is configured.";
          description
            "How long to wait after a commit is done to start the next autosave";
          leaf days {
            type uint32 {
              range "0..365" {
                description
                  "Days";
              }
            }
            mandatory true;
            description
              "Days";
          }
          leaf hours {
            type uint32 {
              range "0..23" {
                description
                  "Hours";
              }
            }
            mandatory true;
            description
              "Hours";
          }
          leaf minutes {
            type uint32 {
              range "0..59" {
                description
                  "Minutes";
              }
            }
            mandatory true;
            description
              "Minutes";
          }
          leaf seconds {
            type uint32 {
              range "0..59" {
                description
                  "Seconds";
              }
            }
            mandatory true;
            description
              "Seconds";
          }
        }
        container timestamp {
          presence "Indicates a timestamp node is configured.";
          description
            "Include the timestamp in the autosave filename";
        }
      }
    }
  }
}
