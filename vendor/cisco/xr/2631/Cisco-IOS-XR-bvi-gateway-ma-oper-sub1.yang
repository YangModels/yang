submodule Cisco-IOS-XR-bvi-gateway-ma-oper-sub1 {
  belongs-to Cisco-IOS-XR-bvi-gateway-ma-oper {
    prefix Cisco-IOS-XR-bvi-gateway-ma-oper;
  }

  import ietf-yang-types {
    prefix yang;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR bvi-gateway-ma package operational data.
     
     Copyright (c) 2013-2026 by Cisco Systems, Inc.
     All rights reserved.";

  revision 2026-05-08 {
    description
      "Added: leaf mtu, leaf state";
    semver:module-version "1.0.0";
  }
  revision 2026-05-07 {
    description
      "Added: leaf mapped-l3ac-count, list mapped-l3ac";
  }
  revision 2026-04-13 {
    description
      "Initial revision.";
  }
  revision 2019-04-05 {
    description
      "Establish semantic version baseline.";
  }
  revision 2015-11-09 {
    description
      "IOS XR 6.0 revision.";
  }

  typedef Im-state-enum {
    type enumeration {
      enum "im-state-not-ready" {
        description
          "im state not ready";
      }
      enum "im-state-admin-down" {
        description
          "im state admin down";
      }
      enum "im-state-down" {
        description
          "im state down";
      }
      enum "im-state-up" {
        description
          "im state up";
      }
      enum "im-state-shutdown" {
        description
          "im state shutdown";
      }
      enum "im-state-err-disable" {
        description
          "im state err disable";
      }
      enum "im-state-down-immediate" {
        description
          "im state down immediate";
      }
      enum "im-state-down-immediate-admin" {
        description
          "im state down immediate admin";
      }
      enum "im-state-down-graceful" {
        description
          "im state down graceful";
      }
      enum "im-state-begin-shutdown" {
        description
          "im state begin shutdown";
      }
      enum "im-state-end-shutdown" {
        description
          "im state end shutdown";
      }
      enum "im-state-begin-error-disable" {
        description
          "im state begin error disable";
      }
      enum "im-state-end-error-disable" {
        description
          "im state end error disable";
      }
      enum "im-state-begin-down-graceful" {
        description
          "im state begin down graceful";
      }
      enum "im-state-reset" {
        description
          "im state reset";
      }
      enum "im-state-operational" {
        description
          "im state operational";
      }
      enum "im-state-not-operational" {
        description
          "im state not operational";
      }
      enum "im-state-unknown" {
        description
          "im state unknown";
      }
      enum "im-state-last" {
        description
          "im state last";
      }
    }
    description
      "Im state enum";
  }

  grouping BVI-GATEWAY-L3AC-INFO {
    description
      "BVI GATEWAY L3AC INFO";
    leaf l3ac-interface-handle {
      type uint32;
      description
        "L3AC Interface Handle";
    }
  }

  grouping BVI-GATEWAY-INFO {
    description
      "BVI GATEWAY INFO";
    leaf interface-handle {
      type uint32;
      description
        "BVI-Gateway Interface Handle";
    }
    leaf mtu {
      type uint32;
      description
        "BVI-Gateway MTU";
    }
    leaf state {
      type Im-state-enum;
      description
        "BVI-Gateway IM State";
    }
    leaf mac-address {
      type yang:mac-address;
      description
        "BVI-Gateway MAC Address";
    }
    leaf is-mac-configured {
      type boolean;
      description
        "Is MAC Configured";
    }
    leaf mapped-l3ac-count {
      type uint32;
      description
        "Mapped L3AC count";
    }
    list mapped-l3ac {
      description
        "Mapped L3ACs";
      uses BVI-GATEWAY-L3AC-INFO;
    }
  }
}
