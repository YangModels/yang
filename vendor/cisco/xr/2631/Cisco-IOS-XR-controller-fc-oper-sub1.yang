submodule Cisco-IOS-XR-controller-fc-oper-sub1 {
  belongs-to Cisco-IOS-XR-controller-fc-oper {
    prefix Cisco-IOS-XR-controller-fc-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR controller-fc package operational data.
     
     Copyright (c) 2013-2023 by Cisco Systems, Inc.
     All rights reserved.";

  revision 2023-01-10 {
    description
      "Added tts-enabled leaf";
    semver:module-version "2.0.0";
  }
  revision 2021-06-30 {
    description
      "sf-ber-threshold and sd-ber-threshold added in fc_ctrlr_port_info bag";
    semver:module-version "1.0.0";
  }
  revision 2021-04-20 {
    description
      "Fibre Channel controller oper model added";
  }
  revision 2019-04-05 {
    description
      "Establish semantic version baseline.";
  }
  revision 2015-11-09 {
    description
      "IOS XR 6.0 revision.";
  }

  typedef Fc-ctrlr-prbs-err-inject {
    type enumeration {
      enum "none" {
        description
          "None";
      }
      enum "single" {
        description
          "Single";
      }
      enum "continuous" {
        description
          "Continuous";
      }
    }
    description
      "Fc ctrlr prbs err inject";
  }

  typedef Fc-ctrlr-prbs-dir {
    type enumeration {
      enum "none" {
        description
          "None";
      }
      enum "line" {
        description
          "Line";
      }
      enum "system" {
        description
          "System";
      }
    }
    description
      "Fc ctrlr prbs dir";
  }

  typedef Fc-ctrlr-prbs-framing {
    type enumeration {
      enum "none" {
        description
          "Framing None";
      }
      enum "framed" {
        description
          "Framed";
      }
      enum "unframed" {
        description
          "Unframed";
      }
    }
    description
      "Fc ctrlr prbs framing";
  }

  typedef Fc-ctrlr-prbs-status {
    type enumeration {
      enum "locked" {
        value 0;
        description
          "Locked";
      }
      enum "unlocked" {
        value 1;
        description
          "Unlocked";
      }
      enum "not-applicable" {
        value 2;
        description
          "Not Applicable";
      }
    }
    description
      "Fc ctrlr prbs status";
  }

  typedef Fc-ctrlr-prbs-pattern {
    type enumeration {
      enum "pn-none" {
        value 0;
        description
          "PNNONE";
      }
      enum "pn31" {
        value 1;
        description
          "PN31";
      }
      enum "pn23" {
        value 2;
        description
          "PN23";
      }
      enum "pn15" {
        value 3;
        description
          "PN15";
      }
      enum "pn11" {
        value 4;
        description
          "PN11";
      }
      enum "pn9" {
        value 5;
        description
          "PN9";
      }
      enum "pn7" {
        value 6;
        description
          "PN7";
      }
      enum "user-defined" {
        value 7;
        description
          "User Defined Pattern";
      }
    }
    description
      "Fc ctrlr prbs pattern";
  }

  typedef Fc-ctrlr-prbs-mode {
    type enumeration {
      enum "none" {
        value 0;
        description
          "None";
      }
      enum "source" {
        value 1;
        description
          "Source";
      }
      enum "sink" {
        value 2;
        description
          "Sink";
      }
      enum "source-sink" {
        value 3;
        description
          "Source Sink";
      }
    }
    description
      "Fc ctrlr prbs mode";
  }

  typedef Fc-ctrlr-prbs-test {
    type enumeration {
      enum "disable" {
        value 0;
        description
          "Disable";
      }
      enum "enable" {
        value 1;
        description
          "Enable";
      }
    }
    description
      "Fc ctrlr prbs test";
  }

  typedef Fc-ains-status {
    type enumeration {
      enum "ains-soak-status-none" {
        description
          "AINS Soak timer not running";
      }
      enum "ains-soak-status-pending" {
        description
          "AINS Soak timer pending";
      }
      enum "ains-soak-status-running" {
        description
          "AINS Soak timer running";
      }
    }
    description
      "Fc ains status";
  }

  typedef Fc-fec {
    type enumeration {
      enum "none" {
        description
          "None";
      }
      enum "not-configured" {
        description
          "Not Configured";
      }
      enum "standard" {
        description
          "Standard";
      }
      enum "disabled" {
        description
          "Disabled";
      }
    }
    description
      "FEC Type";
  }

  typedef Fc-loopback-info {
    type enumeration {
      enum "none" {
        description
          "None";
      }
      enum "line" {
        description
          "LoopBack Line ";
      }
      enum "loop-back-internal" {
        description
          "LoopBack Internal";
      }
    }
    description
      "loopback info";
  }

  typedef Fc-led-state {
    type enumeration {
      enum "off" {
        value 0;
        description
          "Off";
      }
      enum "green-on" {
        value 1;
        description
          "Green On";
      }
      enum "green-flashing" {
        value 2;
        description
          "Green Flashing";
      }
      enum "yellow-on" {
        value 3;
        description
          "Yellow On";
      }
      enum "yellow-flashing" {
        value 4;
        description
          "Yellow Flashing";
      }
      enum "red-on" {
        value 5;
        description
          "Red On";
      }
      enum "red-flashing" {
        value 6;
        description
          "Red Flashing";
      }
      enum "not-applicable" {
        value 7;
        description
          "Not Applicable";
      }
    }
    description
      "Fc led state";
  }

  typedef Fc-state-et {
    type enumeration {
      enum "not-ready" {
        value 0;
        description
          "Not Ready";
      }
      enum "admin-down" {
        value 1;
        description
          "Admin Down";
      }
      enum "down" {
        value 2;
        description
          "Down";
      }
      enum "up" {
        value 3;
        description
          "Up";
      }
      enum "shutdown" {
        value 4;
        description
          "Shutdown";
      }
      enum "error-disable" {
        value 5;
        description
          "Error Disable";
      }
      enum "down-immediate" {
        value 6;
        description
          "Down Immediate";
      }
      enum "down-immediate-admin" {
        value 7;
        description
          "Down Immediate Admin";
      }
      enum "down-graceful" {
        value 8;
        description
          "Down Graceful";
      }
      enum "begin-shutdown" {
        value 9;
        description
          "Begin Shutdown";
      }
      enum "end-shutdown" {
        value 10;
        description
          "End Shutdown";
      }
      enum "begin-error-disable" {
        value 11;
        description
          "Begin Error Disable";
      }
      enum "end-error-disable" {
        value 12;
        description
          "End Error Disable";
      }
      enum "begin-down-graceful" {
        value 13;
        description
          "Begin Down Graceful";
      }
      enum "reset" {
        value 14;
        description
          "Reset";
      }
      enum "operational" {
        value 15;
        description
          "Operational";
      }
      enum "not-operational" {
        value 16;
        description
          "Not Operational";
      }
      enum "unknown" {
        value 17;
        description
          "Unknown";
      }
      enum "last" {
        value 18;
        description
          "Last";
      }
    }
    description
      "Fc state et";
  }

  typedef Fc-sa-state {
    type enumeration {
      enum "normal" {
        description
          "Normal";
      }
      enum "maintenance" {
        description
          "Maintenance";
      }
      enum "ains" {
        description
          "AINS";
      }
    }
    description
      "Secondary admin state";
  }

  grouping FC-CTRLR-PRBS-INFO {
    description
      "PRBS";
    leaf test {
      type Fc-ctrlr-prbs-test;
      description
        "PRBS test";
    }
    leaf mode {
      type Fc-ctrlr-prbs-mode;
      description
        "PRBS mode";
    }
    leaf pattern {
      type Fc-ctrlr-prbs-pattern;
      description
        "PRBS pattern";
    }
    leaf status {
      type Fc-ctrlr-prbs-status;
      description
        "PRBS status";
    }
    leaf framing {
      type Fc-ctrlr-prbs-framing;
      description
        "PRBS framing";
    }
    leaf direction {
      type Fc-ctrlr-prbs-dir;
      description
        "PRBS direction";
    }
    leaf err-inject {
      type Fc-ctrlr-prbs-err-inject;
      description
        "PRBS error injection";
    }
    leaf user-pattern {
      type uint64;
      description
        "PRBS user pattern configured";
    }
  }

  grouping FC-EXTENDED-LOOPBACK-TYPE {
    description
      "FC EXTENDED LOOPBACK TYPE";
    leaf level {
      type uint32;
      description
        "Level";
    }
    leaf loopback {
      type Fc-loopback-info;
      description
        "Port operational loopback";
    }
  }

  grouping FC-CTLR-AINS-INFO {
    description
      "FC CTLR AINS INFO";
    leaf ains-status {
      type Fc-ains-status;
      description
        "AINS Soak status";
    }
    leaf total-duration {
      type uint32;
      units "minute";
      description
        "Total duration (minutes) of AINS soak timer";
    }
    leaf remaining-duration {
      type uint32;
      units "second";
      description
        "Remaining duration (seconds) of AINS soak timer";
    }
  }

  grouping FC-OPER-ALARMS {
    description
      "FC alarms structure";
    leaf los {
      type boolean;
      description
        "Loss of signal Alarm";
    }
    leaf local-fault {
      type boolean;
      description
        "Local Fault Alarm";
    }
    leaf remote-fault {
      type boolean;
      description
        "Remote Fault Alarm";
    }
    leaf pcs-error {
      type boolean;
      description
        "PCS Error";
    }
    leaf high-ber {
      type boolean;
      description
        "High BER Error Alarm";
    }
    leaf syncloss {
      type boolean;
      description
        "Loss of synchronization Alarm";
    }
    leaf nos {
      type boolean;
      description
        "Not-Operational primitive Sequence Alarm";
    }
    leaf squelch {
      type boolean;
      description
        "Squelch Alarm";
    }
  }

  grouping FC-BER-THRESHOLDS {
    description
      "FC BER THRESHOLDS";
    leaf signal-degrade-ber-threshold {
      type uint32;
      description
        "Signal Degrade BER Threshold";
    }
    leaf signal-failure-ber-threshold {
      type uint32;
      description
        "Signal Failure BER Threshold";
    }
  }

  grouping FC-CTRLR-PORT-INFO {
    description
      "FC port operational info";
    container ber-thresholds {
      description
        "BER thresholds";
      uses FC-BER-THRESHOLDS;
    }
    container current-alarms {
      description
        "Current Alarms info";
      uses FC-OPER-ALARMS;
    }
    container previous-alarms {
      description
        "Previous Alarms info";
      uses FC-OPER-ALARMS;
    }
    container ains-info {
      description
        "AINS information ";
      uses FC-CTLR-AINS-INFO;
    }
    leaf secondary-admin-state {
      type Fc-sa-state;
      description
        "Secondary Admin State";
    }
    leaf operational-state {
      type Fc-state-et;
      description
        "Port's IM state";
    }
    leaf led-state {
      type Fc-led-state;
      description
        "LED state";
    }
    leaf loopback {
      type Fc-loopback-info;
      description
        "Loopback info";
    }
    leaf perf-mon-disabled {
      type boolean;
      description
        "Perf mon disabled";
    }
    leaf fec {
      type Fc-fec;
      description
        "FEC type";
    }
    leaf fec-method {
      type string {
        length "0..64";
      }
      description
        "FEC method";
    }
    leaf laser-squelch-enabled {
      type boolean;
      description
        "Laser squelch enabled";
    }
    leaf holdoff-time {
      type uint32;
      description
        "Hold off Time";
    }
    leaf tts-enabled {
      type boolean;
      description
        "TTS enabled";
    }
    list extended-loopback {
      description
        "Extended Loopback info";
      uses FC-EXTENDED-LOOPBACK-TYPE;
    }
  }
}
