module Cisco-IOS-XR-sysadmin-rmon {
  namespace "http://www.cisco.com/ns/yang/Cisco-IOS-XR-sysadmin-rmon";
  prefix rmon;

  import cisco-semver {
    prefix semver;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains a collection of YANG
     definitions for Cisco IOS-XR SysAdmin configuration.
     
     Copyright (c) 2013-2020 by Cisco Systems, Inc.
     All rights reserved.";

  revision 2021-02-15 {
    description
      "Removed unused imports";
    semver:module-version "1.0.0";
  }
  revision 2020-09-24 {
    description
      "Initial Version";
  }

  grouping rmon_cli_history_option_grouping {
    container rack-loss-history {
      list hist_entries {
        key "hist_index";
        leaf hist_index {
          type uint32;
        }
        leaf hist_serial {
          type string;
        }
        leaf hist_rack_num {
          type string;
        }
        leaf hist_time_stamp {
          type string;
        }
      }
    }
  }

  grouping rmon_cli_db_option_grouping {
    container db {
      config false;
      list rack {
        key "rack_num";
        leaf serial {
          type string;
          description
            "Serial number of the rack";
        }
        leaf rack_type {
          type string;
          description
            "Rack Type";
        }
        leaf rack_num {
          type string;
          description
            "Rack Number";
        }
        leaf rack_state {
          type string;
          description
            "Rack State";
        }
        leaf n_adj {
          type uint32;
          description
            "Number of adjacent racks";
        }
        list adj-info {
          key "remote_serial";
          leaf remote_serial {
            type string;
            description
              "Serial number of the remote rack";
          }
          list adj-link-info {
            key "my_slot my_port";
            leaf my_slot {
              type uint32;
              description
                "Local Slot number";
            }
            leaf my_port {
              type uint32;
              description
                "Local Port number";
            }
            leaf remote_slot {
              type uint32;
              description
                "Remote Slot number";
            }
            leaf remote_port {
              type uint32;
              description
                "Remote Port number";
            }
            leaf link_state {
              type string;
              description
                "Link State";
            }
            leaf adj_serial {
              type string;
              description
                "Remote serial";
            }
            leaf adj_rack_num {
              type string;
              description
                "Remote rack num";
            }
          }
        }
      }
    }
  }

  container rmon {
    config false;
    list location {
      key "loc";
      leaf loc {
        type string;
      }
      uses rmon_cli_db_option_grouping;
      uses rmon_cli_history_option_grouping;
    }
  }
}
