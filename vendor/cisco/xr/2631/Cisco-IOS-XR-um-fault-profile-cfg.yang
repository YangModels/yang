module Cisco-IOS-XR-um-fault-profile-cfg {
  namespace "http://cisco.com/ns/yang/Cisco-IOS-XR-um-fault-profile-cfg";
  prefix um-fault-profile-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR fault-profile package configuration.
     
     This YANG module augments the
     modules with configuration data.
     
     Copyright (c) 2021-2025 by Cisco Systems, Inc., and/or its affiliates.
     All rights reserved.";

  revision 2021-12-15 {
    description
      "Updated leaf fault-type-name pattern to support additional fault types";
    semver:module-version "1.1.0";
  }
  revision 2021-02-24 {
    description
      "Initial release";
    semver:module-version "1.0.0";
  }

  container fault-profile {
    description
      "Fault profile name";
    container fault-profiles {
      description
        "Fault profile";
      list fault-profile {
        key "fault-profile-name";
        description
          "Fault profile";
        leaf fault-profile-name {
          type xr:Cisco-ios-xr-string {
            length "1..32" {
              description
                "Fault profile";
            }
            pattern "[a-zA-Z0-9]+";
          }
          description
            "Fault profile";
        }
        container fault-identifier {
          description
            "Fault identifier";
          container subsystem {
            description
              "Subsystem name";
            container xr {
              description
                "Subsystem XR";
              list fault-type {
                must "fault-tag";
                key "fault-type-name";
                description
                  "Fault type name";
                leaf fault-type-name {
                  type string {
                    pattern
                      "[HW_CEM|HW_E1|HW_GFP|HW_ETHERNET|HW_SDH_CONTROLLER|HW_SONET|
                                                    HW_OPTICS|HW_G709|HW_FIBRE_CHANNEL|HW_CPRI|
                                                    HW_OTS]+";
                  }
                  description
                    "Fault type name";
                }
                list fault-tag {
                  key "fault-tag-name";
                  description
                    "Fault tag name";
                  leaf fault-tag-name {
                    type xr:Cisco-ios-xr-string {
                      length "1..800";
                    }
                    description
                      "Fault tag name. Supported tag names are:
                       GFP_RX_CSF_NE_30_SEC
                       GFP_RX_LFD_NE_30_SEC
                       GFP_RX_CRC_NE_30_SEC
                       GFP_RX_INV_TYP_NE_30_SEC
                       GFP_RX_BIT_ERR_NE_30_SEC
                       GFP_RX_CSF_NE_1_DAY
                       GFP_RX_LFD_NE_1_DAY
                       GFP_RX_CRC_NE_1_DAY
                       GFP_RX_INV_TYP_NE_1_DAY
                       GFP_RX_BIT_ERR_NE_1_DAY
                       GFP_RX_CSF_NE_15_MINS
                       GFP_RX_LFD_NE_15_MINS
                       GFP_RX_CRC_NE_15_MINS
                       GFP_RX_INV_TYP_NE_15_MINS
                       GFP_RX_BIT_ERR_NE_15_MINS
                       GFP_UPM
                       GFP_LOCCS
                       GFP_LOCS
                       GFP_LFD
                       PCS_UAS_FE_15_MINS
                       PCS_UAS_FE_30_SEC
                       PCS_UAS_NE_1_DAY
                       PCS_UAS_NE_15_MINS
                       PCS_UAS_NE_30_SEC
                       PCS_SES_FE_1_DAY
                       PCS_SES_FE_15_MINS
                       PCS_SES_FE_30_SEC
                       PCS_SES_NE_1_DAY
                       PCS_SES_NE_15_MINS
                       PCS_SES_NE_30_SEC
                       PCS_ES_FE_1_DAY
                       PCS_ES_FE_15_MINS
                       PCS_ES_FE_30_SEC
                       PCS_ES_NE_1_DAY
                       PCS_ES_NE_15_MINS
                       PCS_ES_NE_30_SEC
                       PCS_BAD_SH_LANE0_NE_1_DAY
                       PCS_BAD_SH_LANE0_NE_15_MINS
                       PCS_BAD_SH_LANE0_NE_30_SEC
                       PCS_FRM_ERR_LANE0_NE_1_DAY
                       PCS_FRM_ERR_LANE0_NE_15_MINS
                       PCS_FRM_ERR_LANE0_NE_30_SEC
                       PCS_BIP_LANE0_NE_1_DAY
                       PCS_BIP_LANE0_NE_15_MINS
                       PCS_BIP_LANE0_NE_30_SEC
                       PCS_BAD_SH_LANE39_NE_1_DAY
                       PCS_BAD_SH_LANE39_NE_15_MINS
                       PCS_BAD_SH_LANE39_NE_30_SEC
                       PCS_FRM_ERR_LANE39_NE_1_DAY
                       PCS_FRM_ERR_LANE39_NE_15_MINS
                       PCS_FRM_ERR_LANE39_NE_30_SEC
                       PCS_BIP_LANE39_NE_1_DAY
                       PCS_BIP_LANE39_NE_15_MINS
                       PCS_BIP_LANE39_NE_30_SEC
                       PCS_BAD_SH_LANE38_NE_1_DAY
                       PCS_BAD_SH_LANE38_NE_15_MINS
                       PCS_BAD_SH_LANE38_NE_30_SEC
                       PCS_FRM_ERR_LANE38_NE_1_DAY
                       PCS_FRM_ERR_LANE38_NE_15_MINS
                       PCS_FRM_ERR_LANE38_NE_30_SEC
                       PCS_BIP_LANE38_NE_1_DAY
                       PCS_BIP_LANE38_NE_15_MINS
                       PCS_BIP_LANE38_NE_30_SEC
                       PCS_BAD_SH_LANE37_NE_1_DAY
                       PCS_BAD_SH_LANE37_NE_15_MINS
                       PCS_BAD_SH_LANE37_NE_30_SEC
                       PCS_FRM_ERR_LANE37_NE_1_DAY
                       PCS_FRM_ERR_LANE37_NE_15_MINS
                       PCS_FRM_ERR_LANE37_NE_30_SEC
                       PCS_BIP_LANE37_NE_1_DAY
                       PCS_BIP_LANE37_NE_15_MINS
                       PCS_BIP_LANE37_NE_30_SEC
                       PCS_BAD_SH_LANE36_NE_1_DAY
                       PCS_BAD_SH_LANE36_NE_15_MINS
                       PCS_BAD_SH_LANE36_NE_30_SEC
                       PCS_FRM_ERR_LANE36_NE_1_DAY
                       PCS_FRM_ERR_LANE36_NE_15_MINS
                       PCS_FRM_ERR_LANE36_NE_30_SEC
                       PCS_BIP_LANE36_NE_1_DAY
                       PCS_BIP_LANE36_NE_15_MINS
                       PCS_BIP_LANE36_NE_30_SEC
                       PCS_BAD_SH_LANE35_NE_1_DAY
                       PCS_BAD_SH_LANE35_NE_15_MINS
                       PCS_BAD_SH_LANE35_NE_30_SEC
                       PCS_FRM_ERR_LANE35_NE_1_DAY
                       PCS_FRM_ERR_LANE35_NE_15_MINS
                       PCS_FRM_ERR_LANE35_NE_30_SEC
                       PCS_BIP_LANE35_NE_1_DAY
                       PCS_BIP_LANE35_NE_15_MINS
                       PCS_BIP_LANE35_NE_30_SEC
                       PCS_BAD_SH_LANE34_NE_1_DAY
                       PCS_BAD_SH_LANE34_NE_15_MINS
                       PCS_BAD_SH_LANE34_NE_30_SEC
                       PCS_FRM_ERR_LANE34_NE_1_DAY
                       PCS_FRM_ERR_LANE34_NE_15_MINS
                       PCS_FRM_ERR_LANE34_NE_30_SEC
                       PCS_BIP_LANE34_NE_1_DAY
                       PCS_BIP_LANE34_NE_15_MINS
                       PCS_BIP_LANE34_NE_30_SEC
                       PCS_BAD_SH_LANE33_NE_1_DAY
                       PCS_BAD_SH_LANE33_NE_15_MINS
                       PCS_BAD_SH_LANE33_NE_30_SEC
                       PCS_FRM_ERR_LANE33_NE_1_DAY
                       PCS_FRM_ERR_LANE33_NE_15_MINS
                       PCS_FRM_ERR_LANE33_NE_30_SEC
                       PCS_BIP_LANE33_NE_1_DAY
                       PCS_BIP_LANE33_NE_15_MINS
                       PCS_BIP_LANE33_NE_30_SEC
                       PCS_BAD_SH_LANE32_NE_1_DAY
                       PCS_BAD_SH_LANE32_NE_15_MINS
                       PCS_BAD_SH_LANE32_NE_30_SEC
                       PCS_FRM_ERR_LANE32_NE_1_DAY
                       PCS_FRM_ERR_LANE32_NE_15_MINS
                       PCS_FRM_ERR_LANE32_NE_30_SEC
                       PCS_BIP_LANE32_NE_1_DAY
                       PCS_BIP_LANE32_NE_15_MINS
                       PCS_BIP_LANE32_NE_30_SEC
                       PCS_BAD_SH_LANE31_NE_1_DAY
                       PCS_BAD_SH_LANE31_NE_15_MINS
                       PCS_BAD_SH_LANE31_NE_30_SEC
                       PCS_FRM_ERR_LANE31_NE_1_DAY
                       PCS_FRM_ERR_LANE31_NE_15_MINS
                       PCS_FRM_ERR_LANE31_NE_30_SEC
                       PCS_BIP_LANE31_NE_1_DAY
                       PCS_BIP_LANE31_NE_15_MINS
                       PCS_BIP_LANE31_NE_30_SEC
                       PCS_BAD_SH_LANE30_NE_1_DAY
                       PCS_BAD_SH_LANE30_NE_15_MINS
                       PCS_BAD_SH_LANE30_NE_30_SEC
                       PCS_FRM_ERR_LANE30_NE_1_DAY
                       PCS_FRM_ERR_LANE30_NE_15_MINS
                       PCS_FRM_ERR_LANE30_NE_30_SEC
                       PCS_BIP_LANE30_NE_1_DAY
                       PCS_BIP_LANE30_NE_15_MINS
                       PCS_BIP_LANE30_NE_30_SEC
                       PCS_BAD_SH_LANE29_NE_1_DAY
                       PCS_BAD_SH_LANE29_NE_15_MINS
                       PCS_BAD_SH_LANE29_NE_30_SEC
                       PCS_FRM_ERR_LANE29_NE_1_DAY
                       PCS_FRM_ERR_LANE29_NE_15_MINS
                       PCS_FRM_ERR_LANE29_NE_30_SEC
                       PCS_BIP_LANE29_NE_1_DAY
                       PCS_BIP_LANE29_NE_15_MINS
                       PCS_BIP_LANE29_NE_30_SEC
                       PCS_BAD_SH_LANE28_NE_1_DAY
                       PCS_BAD_SH_LANE28_NE_15_MINS
                       PCS_BAD_SH_LANE28_NE_30_SEC
                       PCS_FRM_ERR_LANE28_NE_1_DAY
                       PCS_FRM_ERR_LANE28_NE_15_MINS
                       PCS_FRM_ERR_LANE28_NE_30_SEC
                       PCS_BIP_LANE28_NE_1_DAY
                       PCS_BIP_LANE28_NE_15_MINS
                       PCS_BIP_LANE28_NE_30_SEC
                       PCS_BAD_SH_LANE27_NE_1_DAY
                       PCS_BAD_SH_LANE27_NE_15_MINS
                       PCS_BAD_SH_LANE27_NE_30_SEC
                       PCS_FRM_ERR_LANE27_NE_1_DAY
                       PCS_FRM_ERR_LANE27_NE_15_MINS
                       PCS_FRM_ERR_LANE27_NE_30_SEC
                       PCS_BIP_LANE27_NE_1_DAY
                       PCS_BIP_LANE27_NE_15_MINS
                       PCS_BIP_LANE27_NE_30_SEC
                       PCS_BAD_SH_LANE26_NE_1_DAY
                       PCS_BAD_SH_LANE26_NE_15_MINS
                       PCS_BAD_SH_LANE26_NE_30_SEC
                       PCS_FRM_ERR_LANE26_NE_1_DAY
                       PCS_FRM_ERR_LANE26_NE_15_MINS
                       PCS_FRM_ERR_LANE26_NE_30_SEC
                       PCS_BIP_LANE26_NE_1_DAY
                       PCS_BIP_LANE26_NE_15_MINS
                       PCS_BIP_LANE26_NE_30_SEC
                       PCS_BAD_SH_LANE25_NE_1_DAY
                       PCS_BAD_SH_LANE25_NE_15_MINS
                       PCS_BAD_SH_LANE25_NE_30_SEC
                       PCS_FRM_ERR_LANE25_NE_1_DAY
                       PCS_FRM_ERR_LANE25_NE_15_MINS
                       PCS_FRM_ERR_LANE25_NE_30_SEC
                       PCS_BIP_LANE25_NE_1_DAY
                       PCS_BIP_LANE25_NE_15_MINS
                       PCS_BIP_LANE25_NE_30_SEC
                       PCS_BAD_SH_LANE24_NE_1_DAY
                       PCS_BAD_SH_LANE24_NE_15_MINS
                       PCS_BAD_SH_LANE24_NE_30_SEC
                       PCS_FRM_ERR_LANE24_NE_1_DAY
                       PCS_FRM_ERR_LANE24_NE_15_MINS
                       PCS_FRM_ERR_LANE24_NE_30_SEC
                       PCS_BIP_LANE24_NE_1_DAY
                       PCS_BIP_LANE24_NE_15_MINS
                       PCS_BIP_LANE24_NE_30_SEC
                       PCS_BAD_SH_LANE23_NE_1_DAY
                       PCS_BAD_SH_LANE23_NE_15_MINS
                       PCS_BAD_SH_LANE23_NE_30_SEC
                       PCS_FRM_ERR_LANE23_NE_1_DAY
                       PCS_FRM_ERR_LANE23_NE_15_MINS
                       PCS_FRM_ERR_LANE23_NE_30_SEC
                       PCS_BIP_LANE23_NE_1_DAY
                       PCS_BIP_LANE23_NE_15_MINS
                       PCS_BIP_LANE23_NE_30_SEC
                       PCS_BAD_SH_LANE22_NE_1_DAY
                       PCS_BAD_SH_LANE22_NE_15_MINS
                       PCS_BAD_SH_LANE22_NE_30_SEC
                       PCS_FRM_ERR_LANE22_NE_1_DAY
                       PCS_FRM_ERR_LANE22_NE_15_MINS
                       PCS_FRM_ERR_LANE22_NE_30_SEC
                       PCS_BIP_LANE22_NE_1_DAY
                       PCS_BIP_LANE22_NE_15_MINS
                       PCS_BIP_LANE22_NE_30_SEC
                       PCS_BAD_SH_LANE21_NE_1_DAY
                       PCS_BAD_SH_LANE21_NE_15_MINS
                       PCS_BAD_SH_LANE21_NE_30_SEC
                       PCS_FRM_ERR_LANE21_NE_1_DAY
                       PCS_FRM_ERR_LANE21_NE_15_MINS
                       PCS_FRM_ERR_LANE21_NE_30_SEC
                       PCS_BIP_LANE21_NE_1_DAY
                       PCS_BIP_LANE21_NE_15_MINS
                       PCS_BIP_LANE21_NE_30_SEC
                       PCS_BAD_SH_LANE20_NE_1_DAY
                       PCS_BAD_SH_LANE20_NE_15_MINS
                       PCS_BAD_SH_LANE20_NE_30_SEC
                       PCS_FRM_ERR_LANE20_NE_1_DAY
                       PCS_FRM_ERR_LANE20_NE_15_MINS
                       PCS_FRM_ERR_LANE20_NE_30_SEC
                       PCS_BIP_LANE20_NE_1_DAY
                       PCS_BIP_LANE20_NE_15_MINS
                       PCS_BIP_LANE20_NE_30_SEC
                       PCS_BAD_SH_LANE19_NE_1_DAY
                       PCS_BAD_SH_LANE19_NE_15_MINS
                       PCS_BAD_SH_LANE19_NE_30_SEC
                       PCS_FRM_ERR_LANE19_NE_1_DAY
                       PCS_FRM_ERR_LANE19_NE_15_MINS
                       PCS_FRM_ERR_LANE19_NE_30_SEC
                       PCS_BIP_LANE19_NE_1_DAY
                       PCS_BIP_LANE19_NE_15_MINS
                       PCS_BIP_LANE19_NE_30_SEC
                       PCS_BAD_SH_LANE18_NE_1_DAY
                       PCS_BAD_SH_LANE18_NE_15_MINS
                       PCS_BAD_SH_LANE18_NE_30_SEC
                       PCS_FRM_ERR_LANE18_NE_1_DAY
                       PCS_FRM_ERR_LANE18_NE_15_MINS
                       PCS_FRM_ERR_LANE18_NE_30_SEC
                       PCS_BIP_LANE18_NE_1_DAY
                       PCS_BIP_LANE18_NE_15_MINS
                       PCS_BIP_LANE18_NE_30_SEC
                       PCS_BAD_SH_LANE17_NE_1_DAY
                       PCS_BAD_SH_LANE17_NE_15_MINS
                       PCS_BAD_SH_LANE17_NE_30_SEC
                       PCS_FRM_ERR_LANE17_NE_1_DAY
                       PCS_FRM_ERR_LANE17_NE_15_MINS
                       PCS_FRM_ERR_LANE17_NE_30_SEC
                       PCS_BIP_LANE17_NE_1_DAY
                       PCS_BIP_LANE17_NE_15_MINS
                       PCS_BIP_LANE17_NE_30_SEC
                       PCS_BAD_SH_LANE16_NE_1_DAY
                       PCS_BAD_SH_LANE16_NE_15_MINS
                       PCS_BAD_SH_LANE16_NE_30_SEC
                       PCS_FRM_ERR_LANE16_NE_1_DAY
                       PCS_FRM_ERR_LANE16_NE_15_MINS
                       PCS_FRM_ERR_LANE16_NE_30_SEC
                       PCS_BIP_LANE16_NE_1_DAY
                       PCS_BIP_LANE16_NE_15_MINS
                       PCS_BIP_LANE16_NE_30_SEC
                       PCS_BAD_SH_LANE15_NE_1_DAY
                       PCS_BAD_SH_LANE15_NE_15_MINS
                       PCS_BAD_SH_LANE15_NE_30_SEC
                       PCS_FRM_ERR_LANE15_NE_1_DAY
                       PCS_FRM_ERR_LANE15_NE_15_MINS
                       PCS_FRM_ERR_LANE15_NE_30_SEC
                       PCS_BIP_LANE15_NE_1_DAY
                       PCS_BIP_LANE15_NE_15_MINS
                       PCS_BIP_LANE15_NE_30_SEC
                       PCS_BAD_SH_LANE14_NE_1_DAY
                       PCS_BAD_SH_LANE14_NE_15_MINS
                       PCS_BAD_SH_LANE14_NE_30_SEC
                       PCS_FRM_ERR_LANE14_NE_1_DAY
                       PCS_FRM_ERR_LANE14_NE_15_MINS
                       PCS_FRM_ERR_LANE14_NE_30_SEC
                       PCS_BIP_LANE14_NE_1_DAY
                       PCS_BIP_LANE14_NE_15_MINS
                       PCS_BIP_LANE14_NE_30_SEC
                       PCS_BAD_SH_LANE13_NE_1_DAY
                       PCS_BAD_SH_LANE13_NE_15_MINS
                       PCS_BAD_SH_LANE13_NE_30_SEC
                       PCS_FRM_ERR_LANE13_NE_1_DAY
                       PCS_FRM_ERR_LANE13_NE_15_MINS
                       PCS_FRM_ERR_LANE13_NE_30_SEC
                       PCS_BIP_LANE13_NE_1_DAY
                       PCS_BIP_LANE13_NE_15_MINS
                       PCS_BIP_LANE13_NE_30_SEC
                       PCS_BAD_SH_LANE12_NE_1_DAY
                       PCS_BAD_SH_LANE12_NE_15_MINS
                       PCS_BAD_SH_LANE12_NE_30_SEC
                       PCS_FRM_ERR_LANE12_NE_1_DAY
                       PCS_FRM_ERR_LANE12_NE_15_MINS
                       PCS_FRM_ERR_LANE12_NE_30_SEC
                       PCS_BIP_LANE12_NE_1_DAY
                       PCS_BIP_LANE12_NE_15_MINS
                       PCS_BIP_LANE12_NE_30_SEC
                       PCS_BAD_SH_LANE11_NE_1_DAY
                       PCS_BAD_SH_LANE11_NE_15_MINS
                       PCS_BAD_SH_LANE11_NE_30_SEC
                       PCS_FRM_ERR_LANE11_NE_1_DAY
                       PCS_FRM_ERR_LANE11_NE_15_MINS
                       PCS_FRM_ERR_LANE11_NE_30_SEC
                       PCS_BIP_LANE11_NE_1_DAY
                       PCS_BIP_LANE11_NE_15_MINS
                       PCS_BIP_LANE11_NE_30_SEC
                       PCS_BAD_SH_LANE10_NE_1_DAY
                       PCS_BAD_SH_LANE10_NE_15_MINS
                       PCS_BAD_SH_LANE10_NE_30_SEC
                       PCS_FRM_ERR_LANE10_NE_1_DAY
                       PCS_FRM_ERR_LANE10_NE_15_MINS
                       PCS_FRM_ERR_LANE10_NE_30_SEC
                       PCS_BIP_LANE10_NE_1_DAY
                       PCS_BIP_LANE10_NE_15_MINS
                       PCS_BIP_LANE10_NE_30_SEC
                       PCS_BAD_SH_LANE9_NE_1_DAY
                       PCS_BAD_SH_LANE9_NE_15_MINS
                       PCS_BAD_SH_LANE9_NE_30_SEC
                       PCS_FRM_ERR_LANE9_NE_1_DAY
                       PCS_FRM_ERR_LANE9_NE_15_MINS
                       PCS_FRM_ERR_LANE9_NE_30_SEC
                       PCS_BIP_LANE9_NE_1_DAY
                       PCS_BIP_LANE9_NE_15_MINS
                       PCS_BIP_LANE9_NE_30_SEC
                       PCS_BAD_SH_LANE8_NE_1_DAY
                       PCS_BAD_SH_LANE8_NE_15_MINS
                       PCS_BAD_SH_LANE8_NE_30_SEC
                       PCS_FRM_ERR_LANE8_NE_1_DAY
                       PCS_FRM_ERR_LANE8_NE_15_MINS
                       PCS_FRM_ERR_LANE8_NE_30_SEC
                       PCS_BIP_LANE8_NE_1_DAY
                       PCS_BIP_LANE8_NE_15_MINS
                       PCS_BIP_LANE8_NE_30_SEC
                       PCS_BAD_SH_LANE7_NE_1_DAY
                       PCS_BAD_SH_LANE7_NE_15_MINS
                       PCS_BAD_SH_LANE7_NE_30_SEC
                       PCS_FRM_ERR_LANE7_NE_1_DAY
                       PCS_FRM_ERR_LANE7_NE_15_MINS
                       PCS_FRM_ERR_LANE7_NE_30_SEC
                       PCS_BIP_LANE7_NE_1_DAY
                       PCS_BIP_LANE7_NE_15_MINS
                       PCS_BIP_LANE7_NE_30_SEC
                       PCS_BAD_SH_LANE6_NE_1_DAY
                       PCS_BAD_SH_LANE6_NE_15_MINS
                       PCS_BAD_SH_LANE6_NE_30_SEC
                       PCS_FRM_ERR_LANE6_NE_1_DAY
                       PCS_FRM_ERR_LANE6_NE_15_MINS
                       PCS_FRM_ERR_LANE6_NE_30_SEC
                       PCS_BIP_LANE6_NE_1_DAY
                       PCS_BIP_LANE6_NE_15_MINS
                       PCS_BIP_LANE6_NE_30_SEC
                       PCS_BAD_SH_LANE5_NE_1_DAY
                       PCS_BAD_SH_LANE5_NE_15_MINS
                       PCS_BAD_SH_LANE5_NE_30_SEC
                       PCS_FRM_ERR_LANE5_NE_1_DAY
                       PCS_FRM_ERR_LANE5_NE_15_MINS
                       PCS_FRM_ERR_LANE5_NE_30_SEC
                       PCS_BIP_LANE5_NE_1_DAY
                       PCS_BIP_LANE5_NE_15_MINS
                       PCS_BIP_LANE5_NE_30_SEC
                       PCS_BAD_SH_LANE4_NE_1_DAY
                       PCS_BAD_SH_LANE4_NE_15_MINS
                       PCS_BAD_SH_LANE4_NE_30_SEC
                       PCS_FRM_ERR_LANE4_NE_1_DAY
                       PCS_FRM_ERR_LANE4_NE_15_MINS
                       PCS_FRM_ERR_LANE4_NE_30_SEC
                       PCS_BIP_LANE4_NE_1_DAY
                       PCS_BIP_LANE4_NE_15_MINS
                       PCS_BIP_LANE4_NE_30_SEC
                       PCS_BAD_SH_LANE3_NE_1_DAY
                       PCS_BAD_SH_LANE3_NE_15_MINS
                       PCS_BAD_SH_LANE3_NE_30_SEC
                       PCS_FRM_ERR_LANE3_NE_1_DAY
                       PCS_FRM_ERR_LANE3_NE_15_MINS
                       PCS_FRM_ERR_LANE3_NE_30_SEC
                       PCS_BIP_LANE3_NE_1_DAY
                       PCS_BIP_LANE3_NE_15_MINS
                       PCS_BIP_LANE3_NE_30_SEC
                       PCS_BAD_SH_LANE2_NE_1_DAY
                       PCS_BAD_SH_LANE2_NE_15_MINS
                       PCS_BAD_SH_LANE2_NE_30_SEC
                       PCS_FRM_ERR_LANE2_NE_1_DAY
                       PCS_FRM_ERR_LANE2_NE_15_MINS
                       PCS_FRM_ERR_LANE2_NE_30_SEC
                       PCS_BIP_LANE2_NE_1_DAY
                       PCS_BIP_LANE2_NE_15_MINS
                       PCS_BIP_LANE2_NE_30_SEC
                       PCS_BAD_SH_LANE1_NE_1_DAY
                       PCS_BAD_SH_LANE1_NE_15_MINS
                       PCS_BAD_SH_LANE1_NE_30_SEC
                       PCS_FRM_ERR_LANE1_NE_1_DAY
                       PCS_FRM_ERR_LANE1_NE_15_MINS
                       PCS_FRM_ERR_LANE1_NE_30_SEC
                       PCS_BIP_LANE1_NE_1_DAY
                       PCS_BIP_LANE1_NE_15_MINS
                       PCS_BIP_LANE1_NE_30_SEC
                       TX_UTILIZATION_NE_1_DAY
                       TX_UTILIZATION_NE_15_MINS
                       TX_UTILIZATION_NE_30_SEC
                       RX_UTILIZATION_NE_1_DAY
                       RX_UTILIZATION_NE_15_MINS
                       RX_UTILIZATION_NE_30_SEC
                       TX_BAD_FCS_NE_30_SEC
                       TX_JABBER_NE_30_SEC
                       TX_FRAGMENTS_NE_30_SEC
                       TX_OVERSIZED_PKT_NE_30_SEC
                       TX_UNDERSIZED_PKT_NE_30_SEC
                       OUT_PKTS_1024_1518_OCTETS_NE_30_SEC
                       OUT_PKTS_512_1023_OCTETS_NE_30_SEC
                       OUT_PKTS_256_511_OCTETS_NE_30_SEC
                       OUT_PKTS_128_255_OCTETS_NE_30_SEC
                       OUT_PKTS_65_127OCTETS_NE_30_SEC
                       OUT_PKT_64_OCTET_NE_30_SEC
                       IN_PKTS_1024_1518_OCTETS_NE_30_SEC
                       IN_PKTS_512_1023_OCTETS_NE_30_SEC
                       IN_PKTS_256_511_OCTETS_NE_30_SEC
                       IN_PKTS_128_255_OCTETS_NE_30_SEC
                       IN_PKTS_65_127OCTETS_NE_30_SEC
                       IN_PKT_64_OCTET_NE_30_SEC
                       IN_ERROR_OTHER_NE_30_SEC
                       IN_ERROR_FRAGMENTS_NE_30_SEC
                       IN_ERROR_JABBERS_NE_30_SEC
                       IN_ERROR_RUNT_NE_30_SEC
                       IN_ERROR_GIANT_NE_30_SEC
                       OUT_ERROR_OTHER_NE_30_SEC
                       OUT_DROP_OTHER_NE_30_SEC
                       OUT_DROP_ABORT_NE_30_SEC
                       OUT_DROP_UNDERRUN_NE_30_SEC
                       OUT_GOOD_PKTS_NE_30_SEC
                       OUT_PKTS_1519_MAX_OCTETS_NE_30_SEC
                       OUT_PAUSE_FRAMES_NE_30_SEC
                       OUT_802_1Q_FRAMES_NE_30_SEC
                       OUT_GOOD_BYTES_NE_30_SEC
                       TX_BAD_FCS_NE_15_MINS
                       TX_JABBER_NE_15_MINS
                       TX_FRAGMENTS_NE_15_MINS
                       TX_OVERSIZED_PKT_NE_15_MINS
                       TX_UNDERSIZED_PKT_NE_15_MINS
                       OUT_PKTS_1024_1518_OCTETS_NE_15_MINS
                       OUT_PKTS_512_1023_OCTETS_NE_15_MINS
                       OUT_PKTS_256_511_OCTETS_NE_15_MINS
                       OUT_PKTS_128_255_OCTETS_NE_15_MINS
                       OUT_PKTS_65_127OCTETS_NE_15_MINS
                       OUT_PKT_64_OCTET_NE_15_MINS
                       IN_PKTS_1024_1518_OCTETS_NE_15_MINS
                       IN_PKTS_512_1023_OCTETS_NE_15_MINS
                       IN_PKTS_256_511_OCTETS_NE_15_MINS
                       IN_PKTS_128_255_OCTETS_NE_15_MINS
                       IN_PKTS_65_127OCTETS_NE_15_MINS
                       IN_PKT_64_OCTET_NE_15_MINS
                       IN_ERROR_OTHER_NE_15_MINS
                       IN_ERROR_FRAGMENTS_NE_15_MINS
                       IN_ERROR_JABBERS_NE_15_MINS
                       IN_ERROR_RUNT_NE_15_MINS
                       IN_ERROR_GIANT_NE_15_MINS
                       OUT_ERROR_OTHER_NE_15_MINS
                       OUT_DROP_OTHER_NE_15_MINS
                       OUT_DROP_ABORT_NE_15_MINS
                       OUT_DROP_UNDERRUN_NE_15_MINS
                       OUT_GOOD_PKTS_NE_15_MINS
                       OUT_PKTS_1519_MAX_OCTETS_NE_15_MINS
                       OUT_PAUSE_FRAMES_NE_15_MINS
                       OUT_802_1Q_FRAMES_NE_15_MINS
                       OUT_GOOD_BYTES_NE_15_MINS
                       TX_BAD_FCS_NE_1_DAY
                       TX_JABBER_NE_1_DAY
                       TX_FRAGMENTS_NE_1_DAY
                       TX_OVERSIZED_PKT_NE_1_DAY
                       TX_UNDERSIZED_PKT_NE_1_DAY
                       OUT_PKTS_1024_1518_OCTETS_NE_1_DAY
                       OUT_PKTS_512_1023_OCTETS_NE_1_DAY
                       OUT_PKTS_256_511_OCTETS_NE_1_DAY
                       OUT_PKTS_128_255_OCTETS_NE_1_DAY
                       OUT_PKTS_65_127OCTETS_NE_1_DAY
                       OUT_PKT_64_OCTET_NE_1_DAY
                       IN_PKTS_1024_1518_OCTETS_NE_1_DAY
                       IN_PKTS_512_1023_OCTETS_NE_1_DAY
                       IN_PKTS_256_511_OCTETS_NE_1_DAY
                       IN_PKTS_128_255_OCTETS_NE_1_DAY
                       IN_PKTS_65_127OCTETS_NE_1_DAY
                       IN_PKT_64_OCTET_NE_1_DAY
                       IN_ERROR_OTHER_NE_1_DAY
                       IN_ERROR_FRAGMENTS_NE_1_DAY
                       IN_ERROR_JABBERS_NE_1_DAY
                       IN_ERROR_RUNT_NE_1_DAY
                       IN_ERROR_GIANT_NE_1_DAY
                       OUT_ERROR_OTHER_NE_1_DAY
                       OUT_DROP_OTHER_NE_1_DAY
                       OUT_DROP_ABORT_NE_1_DAY
                       OUT_DROP_UNDERRUN_NE_1_DAY
                       OUT_GOOD_PKTS_NE_1_DAY
                       OUT_PKTS_1519_MAX_OCTETS_NE_1_DAY
                       OUT_PAUSE_FRAMES_NE_1_DAY
                       OUT_802_1Q_FRAMES_NE_1_DAY
                       OUT_GOOD_BYTES_NE_1_DAY
                       IN_ERROR_SYMBOL_NE_30_SEC
                       IN_ERROR_COLLISIONS_NE_30_SEC
                       IN_MIB_CRC_NE_30_SEC
                       IN_MIB_JABBER_NE_30_SEC
                       IN_MIB_GIANT_NE_30_SEC
                       IN_DROP_OTHER_NE_30_SEC
                       IN_DROP_INVALID_ENCAP_NE_30_SEC
                       IN_DROP_INVALID_DMAC_NE_30_SEC
                       IN_DROP_INVALID_VLAN_NE_30_SEC
                       IN_DROP_ABORT_NE_30_SEC
                       IN_DROP_OVERRUN_NE_30_SEC
                       IN_GOOD_PKTS_NE_30_SEC
                       IN_PKTS_1519_MAX_OCTETS_NE_30_SEC
                       IN_802_1Q_FRAMES_NE_30_SEC
                       IN_GOOD_BYTES_NE_30_SEC
                       IN_PAUSE_FRAME_NE_30_SEC
                       IN_ERROR_SYMBOL_NE_15_MINS
                       IN_ERROR_COLLISIONS_NE_15_MINS
                       IN_MIB_CRC_NE_15_MINS
                       IN_MIB_JABBER_NE_15_MINS
                       IN_MIB_GIANT_NE_15_MINS
                       IN_DROP_OTHER_NE_15_MINS
                       IN_DROP_INVALID_ENCAP_NE_15_MINS
                       IN_DROP_INVALID_DMAC_NE_15_MINS
                       IN_DROP_INVALID_VLAN_NE_15_MINS
                       IN_DROP_ABORT_NE_15_MINS
                       IN_DROP_OVERRUN_NE_15_MINS
                       IN_GOOD_PKTS_NE_15_MINS
                       IN_PKTS_1519_MAX_OCTETS_NE_15_MINS
                       IN_802_1Q_FRAMES_NE_15_MINS
                       IN_GOOD_BYTES_NE_15_MINS
                       IN_PAUSE_FRAME_NE_15_MINS
                       IN_ERROR_SYMBOL_NE_1_DAY
                       IN_ERROR_COLLISIONS_NE_1_DAY
                       IN_MIB_CRC_NE_1_DAY
                       IN_MIB_JABBER_NE_1_DAY
                       IN_MIB_GIANT_NE_1_DAY
                       IN_DROP_OTHER_NE_1_DAY
                       IN_DROP_INVALID_ENCAP_NE_1_DAY
                       IN_DROP_INVALID_DMAC_NE_1_DAY
                       IN_DROP_INVALID_VLAN_NE_1_DAY
                       IN_DROP_ABORT_NE_1_DAY
                       IN_DROP_OVERRUN_NE_1_DAY
                       IN_GOOD_PKTS_NE_1_DAY
                       IN_PKTS_1519_MAX_OCTETS_NE_1_DAY
                       IN_802_1Q_FRAMES_NE_1_DAY
                       IN_GOOD_BYTES_NE_1_DAY
                       IN_PAUSE_FRAME_NE_1_DAY
                       OUT_BCAST_PKTS_NE_30_SEC
                       Tx_PKTS_NE_30_SEC
                       IFIN_ERRORS_NE_30_SEC
                       IFIN_OCTETS_NE_30_SEC
                       ETHER_STAT_MULTICAST_PKT_NE_30_SEC
                       ETHER_STAT_BROADCAST_PKT_NE_30_SEC
                       ETHER_STAT_UNDERSIZED_PKT_NE_30_SEC
                       OUT_OCTETS_NE_30_SEC
                       LONG_FRAME_NE_30_SEC
                       FCS_ERR_NE_30_SEC
                       OVERSIZE_PKTS_NE_30_SEC
                       STATS_OCTETS_NE_30_SEC
                       STAT_PKTS_NE_30_SEC
                       RX_PKTS_NE_30_SEC
                       JABBERS_STATS_NE_30_SEC
                       PKT_65_127_OCTETS_NE_30_SEC
                       PKT_64_OCTETS_NE_30_SEC
                       PKT_512_1023_OCTETS_NE_30_SEC
                       PKT_256_511_OCTETS_NE_30_SEC
                       PKT_128_255_OCTETS_NE_30_SEC
                       PKT_1024_1518_OCTETS_NE_30_SEC
                       OUT_UCAST_PKTS_NE_30_SEC
                       OUT_MCAST_PKTS_NE_30_SEC
                       IN_UCAST_PKTS_NE_30_SEC
                       IN_MCAST_PKTS_NE_30_SEC
                       IN_BCAST_PKTS_NE_30_SEC
                       OUT_BCAST_PKTS_NE_1_DAY
                       OUT_BCAST_PKTS_NE_15_MINS
                       Tx_PKTS_NE_1_DAY
                       Tx_PKTS_NE_15_MINS
                       IFIN_ERRORS_NE_1_DAY
                       IFIN_ERRORS_NE_15_MINS
                       IFIN_OCTETS_NE_1_DAY
                       IFIN_OCTETS_NE_15_MINS
                       ETHER_STAT_MULTICAST_PKT_NE_1_DAY
                       ETHER_STAT_MULTICAST_PKT_NE_15_MINS
                       ETHER_STAT_BROADCAST_PKT_NE_1_DAY
                       ETHER_STAT_BROADCAST_PKT_NE_15_MINS
                       ETHER_STAT_UNDERSIZED_PKT_NE_1_DAY
                       ETHER_STAT_UNDERSIZED_PKT_NE_15_MINS
                       OUT_OCTETS_NE_15_MINS
                       OUT_OCTETS_NE_1_DAY
                       LONG_FRAME_NE_1_DAY
                       LONG_FRAME_NE_15_MINS
                       FCS_ERR_NE_1_DAY
                       FCS_ERR_NE_15_MINS
                       OVERSIZE_PKTS_NE_1_DAY
                       OVERSIZE_PKTS_NE_15_MINS
                       STATS_OCTETS_NE_1_DAY
                       STATS_OCTETS_NE_15_MINS
                       STAT_PKTS_NE_1_DAY
                       STAT_PKTS_NE_15_MINS
                       RX_PKTS_NE_1_DAY
                       RX_PKTS_NE_15_MINS
                       JABBERS_STATS_NE_1_DAY
                       JABBERS_STATS_NE_15_MINS
                       PKT_65_127_OCTETS_NE_1_DAY
                       PKT_65_127_OCTETS_NE_15_MINS
                       PKT_64_OCTETS_NE_1_DAY
                       PKT_64_OCTETS_NE_15_MINS
                       PKT_512_1023_OCTETS_NE_1_DAY
                       PKT_512_1023_OCTETS_NE_15_MINS
                       PKT_256_511_OCTETS_NE_1_DAY
                       PKT_256_511_OCTETS_NE_15_MINS
                       PKT_128_255_OCTETS_NE_1_DAY
                       PKT_128_255_OCTETS_NE_15_MINS
                       PKT_1024_1518_OCTETS_NE_1_DAY
                       PKT_1024_1518_OCTETS_NE_15_MINS
                       OUT_UCAST_PKTS_NE_1_DAY
                       OUT_UCAST_PKTS_NE_15_MINS
                       OUT_MCAST_PKTS_NE_1_DAY
                       OUT_MCAST_PKTS_NE_15_MINS
                       IN_UCAST_PKTS_NE_1_DAY
                       IN_UCAST_PKTS_NE_15_MINS
                       IN_MCAST_PKTS_NE_1_DAY
                       IN_MCAST_PKTS_NE_15_MINS
                       IN_BCAST_PKTS_NE_1_DAY
                       IN_BCAST_PKTS_NE_15_MINS
                       ETHER_AS_MT
                       ETHER_REMOTE_DEG_SER
                       ETHER_LOCAL_DEG_SER
                       ETHER_DEG_SER
                       ETHER_HI_SER
                       ETHER_SYNCLOSS
                       ETHER_SIGLOSS
                       ETHER_RF
                       ETHER_LF
                       ETHER_SQUELCHED
                       ETHER_HIBER
                       STM_UAS_L_NE_1_DAY
                       STM_UAS_L_NE_15_MINS
                       STM_BBER_L_NE_1_DAY
                       STM_BBER_L_NE_15_MINS
                       STM_BBE_L_NE_1_DAY
                       STM_BBE_L_NE_15_MINS
                       STM_SESR_L_NE_1_DAY
                       STM_SESR_L_NE_15_MINS
                       STM_SES_L_NE_1_DAY
                       STM_SES_L_NE_15_MINS
                       STM_ESR_L_NE_1_DAY
                       STM_ESR_L_NE_15_MINS
                       STM_ES_L_NE_1_DAY
                       STM_ES_L_NE_15_MINS
                       STM_EB_L_NE_1_DAY
                       STM_EB_L_NE_15_MINS
                       STM_UAS_L_FE_1_DAY
                       STM_UAS_L_FE_15_MINS
                       STM_BBER_L_FE_1_DAY
                       STM_BBER_L_FE_15_MINS
                       STM_BBE_L_FE_1_DAY
                       STM_BBE_L_FE_15_MINS
                       STM_SESR_L_FE_1_DAY
                       STM_SESR_L_FE_15_MINS
                       STM_SES_L_FE_1_DAY
                       STM_SES_L_FE_15_MINS
                       STM_ESR_L_FE_1_DAY
                       STM_ESR_L_FE_15_MINS
                       STM_ES_L_FE_1_DAY
                       STM_ES_L_FE_15_MINS
                       STM_EB_L_FE_1_DAY
                       STM_EB_L_FE_15_MINS
                       STM_UAS_S_NE_1_DAY
                       STM_UAS_S_NE_15_MINS
                       STM_BBE_S_NE_1_DAY
                       STM_BBE_S_NE_15_MINS
                       STM_SESR_S_NE_1_DAY
                       STM_SESR_S_NE_15_MINS
                       STM_ESR_S_NE_1_DAY
                       STM_ESR_S_NE_15_MINS
                       STM_ES_S_NE_1_DAY
                       STM_ES_S_NE_15_MINS
                       STM_SES_S_NE_1_DAY
                       STM_SES_S_NE_15_MINS
                       STM_EB_S_NE_1_DAY
                       STM_EB_S_NE_15_MINS
                       STM_BBER_S_NE_1_DAY
                       STM_BBER_S_NE_15_MINS
                       HO_VC_UASP_NE_1_DAY
                       HO_VC_UASP_NE_15_MINS
                       HO_VC_BBERP_NE_1_DAY
                       HO_VC_BBERP_NE_15_MINS
                       HO_VC_BBEP_NE_1_DAY
                       HO_VC_BBEP_NE_15_MINS
                       HO_VC_SESP_NE_1_DAY
                       HO_VC_SESP_NE_15_MINS
                       HO_VC_ESRP_NE_1_DAY
                       HO_VC_ESRP_NE_15_MINS
                       HO_VC_ESP_NE_1_DAY
                       HO_VC_SESRP_NE_1_DAY
                       HO_VC_SESRP_NE_15_MINS
                       HO_VC_ESP_NE_15_MINS
                       HO_VC_EBP_NE_1_DAY
                       HO_VC_EBP_NE_15_MINS
                       SDH_HO_SQUELCHED
                       SDH_SQUELCHED
                       SDH_HO_AS_MT
                       SDH_AS_MT
                       SDH_TIM_RS
                       SDH_MS_DEG
                       SDH_MS_EXC
                       SDH_TIM_HP
                       SDH_RDI_HP
                       SDH_PLM_HP
                       SDH_UNEQ_HP
                       SDH_AIS_AU
                       SDH_LOP_AU
                       SDH_RDI_MS
                       SDH_AIS_MS
                       SDH_LOF_RS
                       SDH_LOS_RS
                       OCN_UAS_L_FE_1_DAY
                       OCN_UAS_L_FE_15_MINS
                       OCN_BBE_L_FE_1_DAY
                       OCN_BBE_L_FE_15_MINS
                       OCN_SES_L_FE_1_DAY
                       OCN_SES_L_FE_15_MINS
                       OCN_ES_L_FE_1_DAY
                       OCN_ES_L_FE_15_MINS
                       OCN_CV_L_FE_1_DAY
                       OCN_CV_L_FE_15_MINS
                       OCN_FC_L_FE_1_DAY
                       OCN_FC_L_FE_15_MINS
                       OCN_FC_L_NE_1_DAY
                       OCN_FC_L_NE_15_MINS
                       OCN_UAS_L_NE_1_DAY
                       OCN_UAS_L_NE_15_MINS
                       OCN_BBE_L_NE_1_DAY
                       OCN_BBE_L_NE_15_MINS
                       OCN_SES_L_NE_1_DAY
                       OCN_SES_L_NE_15_MINS
                       OCN_ES_L_NE_1_DAY
                       OCN_ES_L_NE_15_MINS
                       OCN_CV_L_NE_1_DAY
                       OCN_CV_L_NE_15_MINS
                       OCN_SES_S_NE_1_DAY
                       OCN_SES_S_NE_15_MINS
                       OCN_ES_S_NE_1_DAY
                       OCN_ES_S_NE_15_MINS
                       OCN_CV_S_NE_1_DAY
                       OCN_CV_S_NE_15_MINS
                       OCN_SEFS_S_NE_1_DAY
                       OCN_UAS_S_NE_1_DAY
                       OCN_UAS_S_NE_15_MINS
                       OCN_SEFS_S_NE_15_MINS
                       STS_UASP_FE_15_MINS
                       STS_UASP_NE_15_MINS
                       STS_UASP_FE_1_DAY
                       STS_UASP_NE_1_DAY
                       STS_SESP_FE_15_MINS
                       STS_SESP_NE_15_MINS
                       STS_SESP_FE_1_DAY
                       STS_SESP_NE_1_DAY
                       STS_ESP_FE_15_MINS
                       STS_ESP_NE_15_MINS
                       STS_ESP_FE_1_DAY
                       STS_ESP_NE_1_DAY
                       STS_CVP_FE_15_MINS
                       STS_CVP_NE_15_MINS
                       STS_CVP_FE_1_DAY
                       STS_CVP_NE_1_DAY
                       SONET_PATH_SQUELCHED
                       SONET_PATH_AS_MT
                       SONET_TIM_S
                       SONET_SD_BER
                       SONET_SF_BER
                       SONET_TIM_P
                       SONET_RDI_P
                       SONET_PLM_P
                       SONET_UNEQ_P
                       SONET_AIS_P
                       SONET_LOP_P
                       SONET_RDI_L
                       SONET_SQUELCHED
                       SONET_AS_MT
                       SONET_AIS_L
                       SONET_LOF_S
                       SONET_LOS_S
                       AMPLI_GAIN_TILT_MAX_NE_1_DAY
                       AMPLI_GAIN_TILT_MIN_NE_1_DAY
                       AMPLI_GAIN_MAX_NE_1_DAY
                       AMPLI_GAIN_MIN_NE_1_DAY
                       LOW_FREQ_OFF_MAX_NE_1_DAY
                       LOW_FREQ_OFF_MIN_NE_1_DAY
                       RX_SIG_POW_MAX_NE_1_DAY
                       RX_SIG_POW_MIN_NE_1_DAY
                       AMPLI_GAIN_TILT_MAX_NE_15_MINS
                       AMPLI_GAIN_TILT_MIN_NE_15_MINS
                       AMPLI_GAIN_MAX_NE_15_MINS
                       AMPLI_GAIN_MIN_NE_15_MINS
                       LOW_FREQ_OFF_MAX_NE_15_MINS
                       LOW_FREQ_OFF_MIN_NE_15_MINS
                       RX_SIG_POW_MAX_NE_15_MINS
                       RX_SIG_POW_MIN_NE_15_MINS
                       AMPLI_GAIN_TILT_MAX_NE_30_SEC
                       AMPLI_GAIN_TILT_MIN_NE_30_SEC
                       AMPLI_GAIN_MAX_NE_30_SEC
                       AMPLI_GAIN_MIN_NE_30_SEC
                       LOW_FREQ_OFF_MAX_NE_30_SEC
                       LOW_FREQ_OFF_MIN_NE_30_SEC
                       RX_SIG_POW_MAX_NE_30_SEC
                       RX_SIG_POW_MIN_NE_30_SEC
                       DGD_MIN_NE_30_SEC
                       DGD_MAX_NE_30_SEC
                       LASER_BIAS_PC_MAX_NE_30_SEC
                       LASER_BIAS_MAX_NE_30_SEC
                       RX_PWR_MAX_NE_30_SEC
                       TX_PWR_MAX_NE_30_SEC
                       PMD_MIN_NE_30_SEC
                       CD_MIN_NE_30_SEC
                       PN_MIN_NE_30_SEC
                       PCR_MIN_NE_30_SEC
                       PDL_MIN_NE_30_SEC
                       OSNR_MIN_NE_30_SEC
                       LASER_BIAS_PC_MAX_LANE10_NE_30_SEC
                       LASER_BIAS_PC_MAX_LANE9_NE_30_SEC
                       LASER_BIAS_PC_MAX_LANE8_NE_30_SEC
                       LASER_BIAS_PC_MAX_LANE7_NE_30_SEC
                       LASER_BIAS_PC_MAX_LANE6_NE_30_SEC
                       LASER_BIAS_PC_MAX_LANE5_NE_30_SEC
                       LASER_BIAS_PC_MAX_LANE4_NE_30_SEC
                       LASER_BIAS_PC_MAX_LANE3_NE_30_SEC
                       LASER_BIAS_PC_MAX_LANE2_NE_30_SEC
                       LASER_BIAS_PC_MAX_LANE1_NE_30_SEC
                       LASER_BIAS_PC_MIN_LANE10_NE_30_SEC
                       LASER_BIAS_PC_MIN_LANE9_NE_30_SEC
                       LASER_BIAS_PC_MIN_LANE8_NE_30_SEC
                       LASER_BIAS_PC_MIN_LANE7_NE_30_SEC
                       LASER_BIAS_PC_MIN_LANE6_NE_30_SEC
                       LASER_BIAS_PC_MIN_LANE5_NE_30_SEC
                       LASER_BIAS_PC_MIN_LANE4_NE_30_SEC
                       LASER_BIAS_PC_MIN_LANE3_NE_30_SEC
                       LASER_BIAS_PC_MIN_LANE2_NE_30_SEC
                       LASER_BIAS_PC_MIN_LANE1_NE_30_SEC
                       LASER_BIAS_MAX_LANE10_NE_30_SEC
                       LASER_BIAS_MAX_LANE9_NE_30_SEC
                       LASER_BIAS_MAX_LANE8_NE_30_SEC
                       LASER_BIAS_MAX_LANE7_NE_30_SEC
                       LASER_BIAS_MAX_LANE6_NE_30_SEC
                       LASER_BIAS_MAX_LANE5_NE_30_SEC
                       LASER_BIAS_MAX_LANE4_NE_30_SEC
                       LASER_BIAS_MAX_LANE3_NE_30_SEC
                       LASER_BIAS_MAX_LANE2_NE_30_SEC
                       LASER_BIAS_MAX_LANE1_NE_30_SEC
                       LASER_BIAS_MIN_LANE10_NE_30_SEC
                       LASER_BIAS_MIN_LANE9_NE_30_SEC
                       LASER_BIAS_MIN_LANE8_NE_30_SEC
                       LASER_BIAS_MIN_LANE7_NE_30_SEC
                       LASER_BIAS_MIN_LANE6_NE_30_SEC
                       LASER_BIAS_MIN_LANE5_NE_30_SEC
                       LASER_BIAS_MIN_LANE4_NE_30_SEC
                       LASER_BIAS_MIN_LANE3_NE_30_SEC
                       LASER_BIAS_MIN_LANE2_NE_30_SEC
                       LASER_BIAS_MIN_LANE1_NE_30_SEC
                       RX_PWR_MAX_LANE10_NE_30_SEC
                       RX_PWR_MAX_LANE9_NE_30_SEC
                       RX_PWR_MAX_LANE8_NE_30_SEC
                       RX_PWR_MAX_LANE7_NE_30_SEC
                       RX_PWR_MAX_LANE6_NE_30_SEC
                       RX_PWR_MAX_LANE5_NE_30_SEC
                       RX_PWR_MAX_LANE4_NE_30_SEC
                       RX_PWR_MAX_LANE3_NE_30_SEC
                       RX_PWR_MAX_LANE2_NE_30_SEC
                       RX_PWR_MAX_LANE1_NE_30_SEC
                       RX_PWR_MIN_LANE10_NE_30_SEC
                       RX_PWR_MIN_LANE9_NE_30_SEC
                       RX_PWR_MIN_LANE8_NE_30_SEC
                       RX_PWR_MIN_LANE7_NE_30_SEC
                       RX_PWR_MIN_LANE6_NE_30_SEC
                       RX_PWR_MIN_LANE5_NE_30_SEC
                       RX_PWR_MIN_LANE4_NE_30_SEC
                       RX_PWR_MIN_LANE3_NE_30_SEC
                       RX_PWR_MIN_LANE2_NE_30_SEC
                       RX_PWR_MIN_LANE1_NE_30_SEC
                       TX_PWR_MAX_LANE10_NE_30_SEC
                       TX_PWR_MAX_LANE9_NE_30_SEC
                       TX_PWR_MAX_LANE8_NE_30_SEC
                       TX_PWR_MAX_LANE7_NE_30_SEC
                       TX_PWR_MAX_LANE6_NE_30_SEC
                       TX_PWR_MAX_LANE5_NE_30_SEC
                       TX_PWR_MAX_LANE4_NE_30_SEC
                       TX_PWR_MAX_LANE3_NE_30_SEC
                       TX_PWR_MAX_LANE2_NE_30_SEC
                       TX_PWR_MAX_LANE1_NE_30_SEC
                       TX_PWR_MIN_LANE10_NE_30_SEC
                       TX_PWR_MIN_LANE9_NE_30_SEC
                       TX_PWR_MIN_LANE8_NE_30_SEC
                       TX_PWR_MIN_LANE7_NE_30_SEC
                       TX_PWR_MIN_LANE6_NE_30_SEC
                       TX_PWR_MIN_LANE5_NE_30_SEC
                       TX_PWR_MIN_LANE4_NE_30_SEC
                       TX_PWR_MIN_LANE3_NE_30_SEC
                       TX_PWR_MIN_LANE2_NE_30_SEC
                       TX_PWR_MIN_LANE1_NE_30_SEC
                       LASER_BIAS_PC_MIN_NE_30_SEC
                       LASER_BIAS_MIN_NE_30_SEC
                       RX_PWR_MIN_NE_30_SEC
                       TX_PWR_MIN_NE_30_SEC
                       PMD_MAX_NE_30_SEC
                       CD_MAX_NE_30_SEC
                       PN_MAX_NE_30_SEC
                       PCR_MAX_NE_30_SEC
                       PDL_MAX_NE_30_SEC
                       OSNR_MAX_NE_30_SEC
                       DGD_MIN_NE_1_DAY
                       DGD_MIN_NE_15_MINS
                       DGD_MAX_NE_1_DAY
                       DGD_MAX_NE_15_MINS
                       LASER_BIAS_PC_MAX_NE_1_DAY
                       LASER_BIAS_PC_MAX_NE_15_MINS
                       LASER_BIAS_MAX_NE_1_DAY
                       LASER_BIAS_MAX_NE_15_MINS
                       RX_PWR_MAX_NE_1_DAY
                       RX_PWR_MAX_NE_15_MINS
                       TX_PWR_MAX_NE_1_DAY
                       TX_PWR_MAX_NE_15_MINS
                       PMD_MIN_NE_1_DAY
                       PMD_MIN_NE_15_MINS
                       CD_MIN_NE_1_DAY
                       CD_MIN_NE_15_MINS
                       PN_MIN_NE_1_DAY
                       PN_MIN_NE_15_MINS
                       PCR_MIN_NE_1_DAY
                       PCR_MIN_NE_15_MINS
                       SOPMD_MIN_NE_1_DAY
                       SOPMD_MIN_NE_15_MINS
                       PDL_MIN_NE_1_DAY
                       PDL_MIN_NE_15_MINS
                       OSNR_MIN_NE_1_DAY
                       OSNR_MIN_NE_15_MINS
                       LASER_BIAS_PC_MAX_LANE10_NE_1_DAY
                       LASER_BIAS_PC_MAX_LANE10_NE_15_MINS
                       LASER_BIAS_PC_MAX_LANE9_NE_1_DAY
                       LASER_BIAS_PC_MAX_LANE9_NE_15_MINS
                       LASER_BIAS_PC_MAX_LANE8_NE_1_DAY
                       LASER_BIAS_PC_MAX_LANE8_NE_15_MINS
                       LASER_BIAS_PC_MAX_LANE7_NE_1_DAY
                       LASER_BIAS_PC_MAX_LANE7_NE_15_MINS
                       LASER_BIAS_PC_MAX_LANE6_NE_1_DAY
                       LASER_BIAS_PC_MAX_LANE6_NE_15_MINS
                       LASER_BIAS_PC_MAX_LANE5_NE_1_DAY
                       LASER_BIAS_PC_MAX_LANE5_NE_15_MINS
                       LASER_BIAS_PC_MAX_LANE4_NE_1_DAY
                       LASER_BIAS_PC_MAX_LANE4_NE_15_MINS
                       LASER_BIAS_PC_MAX_LANE3_NE_1_DAY
                       LASER_BIAS_PC_MAX_LANE3_NE_15_MINS
                       LASER_BIAS_PC_MAX_LANE2_NE_1_DAY
                       LASER_BIAS_PC_MAX_LANE2_NE_15_MINS
                       LASER_BIAS_PC_MAX_LANE1_NE_1_DAY
                       LASER_BIAS_PC_MAX_LANE1_NE_15_MINS
                       LASER_BIAS_PC_MIN_LANE10_NE_1_DAY
                       LASER_BIAS_PC_MIN_LANE10_NE_15_MINS
                       LASER_BIAS_PC_MIN_LANE9_NE_1_DAY
                       LASER_BIAS_PC_MIN_LANE9_NE_15_MINS
                       LASER_BIAS_PC_MIN_LANE8_NE_1_DAY
                       LASER_BIAS_PC_MIN_LANE8_NE_15_MINS
                       LASER_BIAS_PC_MIN_LANE7_NE_1_DAY
                       LASER_BIAS_PC_MIN_LANE7_NE_15_MINS
                       LASER_BIAS_PC_MIN_LANE6_NE_1_DAY
                       LASER_BIAS_PC_MIN_LANE6_NE_15_MINS
                       LASER_BIAS_PC_MIN_LANE5_NE_1_DAY
                       LASER_BIAS_PC_MIN_LANE5_NE_15_MINS
                       LASER_BIAS_PC_MIN_LANE4_NE_1_DAY
                       LASER_BIAS_PC_MIN_LANE4_NE_15_MINS
                       LASER_BIAS_PC_MIN_LANE3_NE_1_DAY
                       LASER_BIAS_PC_MIN_LANE3_NE_15_MINS
                       LASER_BIAS_PC_MIN_LANE2_NE_1_DAY
                       LASER_BIAS_PC_MIN_LANE2_NE_15_MINS
                       LASER_BIAS_PC_MIN_LANE1_NE_1_DAY
                       LASER_BIAS_PC_MIN_LANE1_NE_15_MINS
                       LASER_BIAS_MAX_LANE10_NE_1_DAY
                       LASER_BIAS_MAX_LANE10_NE_15_MINS
                       LASER_BIAS_MAX_LANE9_NE_1_DAY
                       LASER_BIAS_MAX_LANE9_NE_15_MINS
                       LASER_BIAS_MAX_LANE8_NE_1_DAY
                       LASER_BIAS_MAX_LANE8_NE_15_MINS
                       LASER_BIAS_MAX_LANE7_NE_1_DAY
                       LASER_BIAS_MAX_LANE7_NE_15_MINS
                       LASER_BIAS_MAX_LANE6_NE_1_DAY
                       LASER_BIAS_MAX_LANE6_NE_15_MINS
                       LASER_BIAS_MAX_LANE5_NE_1_DAY
                       LASER_BIAS_MAX_LANE5_NE_15_MINS
                       LASER_BIAS_MAX_LANE4_NE_1_DAY
                       LASER_BIAS_MAX_LANE4_NE_15_MINS
                       LASER_BIAS_MAX_LANE3_NE_1_DAY
                       LASER_BIAS_MAX_LANE3_NE_15_MINS
                       LASER_BIAS_MAX_LANE2_NE_1_DAY
                       LASER_BIAS_MAX_LANE2_NE_15_MINS
                       LASER_BIAS_MAX_LANE1_NE_1_DAY
                       LASER_BIAS_MAX_LANE1_NE_15_MINS
                       LASER_BIAS_MIN_LANE10_NE_1_DAY
                       LASER_BIAS_MIN_LANE10_NE_15_MINS
                       LASER_BIAS_MIN_LANE9_NE_1_DAY
                       LASER_BIAS_MIN_LANE9_NE_15_MINS
                       LASER_BIAS_MIN_LANE8_NE_1_DAY
                       LASER_BIAS_MIN_LANE8_NE_15_MINS
                       LASER_BIAS_MIN_LANE7_NE_1_DAY
                       LASER_BIAS_MIN_LANE7_NE_15_MINS
                       LASER_BIAS_MIN_LANE6_NE_1_DAY
                       LASER_BIAS_MIN_LANE6_NE_15_MINS
                       LASER_BIAS_MIN_LANE5_NE_1_DAY
                       LASER_BIAS_MIN_LANE5_NE_15_MINS
                       LASER_BIAS_MIN_LANE4_NE_1_DAY
                       LASER_BIAS_MIN_LANE4_NE_15_MINS
                       LASER_BIAS_MIN_LANE3_NE_1_DAY
                       LASER_BIAS_MIN_LANE3_NE_15_MINS
                       LASER_BIAS_MIN_LANE2_NE_1_DAY
                       LASER_BIAS_MIN_LANE2_NE_15_MINS
                       LASER_BIAS_MIN_LANE1_NE_1_DAY
                       LASER_BIAS_MIN_LANE1_NE_15_MINS
                       RX_PWR_MAX_LANE10_NE_1_DAY
                       RX_PWR_MAX_LANE10_NE_15_MINS
                       RX_PWR_MAX_LANE9_NE_1_DAY
                       RX_PWR_MAX_LANE9_NE_15_MINS
                       RX_PWR_MAX_LANE8_NE_1_DAY
                       RX_PWR_MAX_LANE8_NE_15_MINS
                       RX_PWR_MAX_LANE7_NE_1_DAY
                       RX_PWR_MAX_LANE7_NE_15_MINS
                       RX_PWR_MAX_LANE6_NE_1_DAY
                       RX_PWR_MAX_LANE6_NE_15_MINS
                       RX_PWR_MAX_LANE5_NE_1_DAY
                       RX_PWR_MAX_LANE5_NE_15_MINS
                       RX_PWR_MAX_LANE4_NE_1_DAY
                       RX_PWR_MAX_LANE4_NE_15_MINS
                       RX_PWR_MAX_LANE3_NE_1_DAY
                       RX_PWR_MAX_LANE3_NE_15_MINS
                       RX_PWR_MAX_LANE2_NE_1_DAY
                       RX_PWR_MAX_LANE2_NE_15_MINS
                       RX_PWR_MAX_LANE1_NE_1_DAY
                       RX_PWR_MAX_LANE1_NE_15_MINS
                       RX_PWR_MIN_LANE10_NE_1_DAY
                       RX_PWR_MIN_LANE10_NE_15_MINS
                       RX_PWR_MIN_LANE9_NE_1_DAY
                       RX_PWR_MIN_LANE9_NE_15_MINS
                       RX_PWR_MIN_LANE8_NE_1_DAY
                       RX_PWR_MIN_LANE8_NE_15_MINS
                       RX_PWR_MIN_LANE7_NE_1_DAY
                       RX_PWR_MIN_LANE7_NE_15_MINS
                       RX_PWR_MIN_LANE6_NE_1_DAY
                       RX_PWR_MIN_LANE6_NE_15_MINS
                       RX_PWR_MIN_LANE5_NE_1_DAY
                       RX_PWR_MIN_LANE5_NE_15_MINS
                       RX_PWR_MIN_LANE4_NE_1_DAY
                       RX_PWR_MIN_LANE4_NE_15_MINS
                       RX_PWR_MIN_LANE3_NE_1_DAY
                       RX_PWR_MIN_LANE3_NE_15_MINS
                       RX_PWR_MIN_LANE2_NE_1_DAY
                       RX_PWR_MIN_LANE2_NE_15_MINS
                       RX_PWR_MIN_LANE1_NE_1_DAY
                       RX_PWR_MIN_LANE1_NE_15_MINS
                       TX_PWR_MAX_LANE10_NE_1_DAY
                       TX_PWR_MAX_LANE10_NE_15_MINS
                       TX_PWR_MAX_LANE9_NE_1_DAY
                       TX_PWR_MAX_LANE9_NE_15_MINS
                       TX_PWR_MAX_LANE8_NE_1_DAY
                       TX_PWR_MAX_LANE8_NE_15_MINS
                       TX_PWR_MAX_LANE7_NE_1_DAY
                       TX_PWR_MAX_LANE7_NE_15_MINS
                       TX_PWR_MAX_LANE6_NE_1_DAY
                       TX_PWR_MAX_LANE6_NE_15_MINS
                       TX_PWR_MAX_LANE5_NE_1_DAY
                       TX_PWR_MAX_LANE5_NE_15_MINS
                       TX_PWR_MAX_LANE4_NE_1_DAY
                       TX_PWR_MAX_LANE4_NE_15_MINS
                       TX_PWR_MAX_LANE3_NE_1_DAY
                       TX_PWR_MAX_LANE3_NE_15_MINS
                       TX_PWR_MAX_LANE2_NE_1_DAY
                       TX_PWR_MAX_LANE2_NE_15_MINS
                       TX_PWR_MAX_LANE1_NE_1_DAY
                       TX_PWR_MAX_LANE1_NE_15_MINS
                       TX_PWR_MIN_LANE10_NE_1_DAY
                       TX_PWR_MIN_LANE10_NE_15_MINS
                       TX_PWR_MIN_LANE9_NE_1_DAY
                       TX_PWR_MIN_LANE9_NE_15_MINS
                       TX_PWR_MIN_LANE8_NE_1_DAY
                       TX_PWR_MIN_LANE8_NE_15_MINS
                       TX_PWR_MIN_LANE7_NE_1_DAY
                       TX_PWR_MIN_LANE7_NE_15_MINS
                       TX_PWR_MIN_LANE6_NE_1_DAY
                       TX_PWR_MIN_LANE6_NE_15_MINS
                       TX_PWR_MIN_LANE5_NE_1_DAY
                       TX_PWR_MIN_LANE5_NE_15_MINS
                       TX_PWR_MIN_LANE4_NE_1_DAY
                       TX_PWR_MIN_LANE4_NE_15_MINS
                       TX_PWR_MIN_LANE3_NE_1_DAY
                       TX_PWR_MIN_LANE3_NE_15_MINS
                       TX_PWR_MIN_LANE2_NE_1_DAY
                       TX_PWR_MIN_LANE2_NE_15_MINS
                       TX_PWR_MIN_LANE1_NE_1_DAY
                       TX_PWR_MIN_LANE1_NE_15_MINS
                       LASER_BIAS_PC_MIN_NE_1_DAY
                       LASER_BIAS_PC_MIN_NE_15_MINS
                       LASER_BIAS_MIN_NE_1_DAY
                       LASER_BIAS_MIN_NE_15_MINS
                       RX_PWR_MIN_NE_1_DAY
                       RX_PWR_MIN_NE_15_MINS
                       TX_PWR_MIN_NE_1_DAY
                       TX_PWR_MIN_NE_15_MINS
                       PMD_MAX_NE_1_DAY
                       PMD_MAX_NE_15_MINS
                       CD_MAX_NE_1_DAY
                       CD_MAX_NE_15_MINS
                       PN_MAX_NE_1_DAY
                       PN_MAX_NE_15_MINS
                       PCR_MAX_NE_1_DAY
                       PCR_MAX_NE_15_MINS
                       SOPMD_MAX_NE_1_DAY
                       SOPMD_MAX_NE_15_MINS
                       PDL_MAX_NE_1_DAY
                       PDL_MAX_NE_15_MINS
                       OSNR_MAX_NE_1_DAY
                       OSNR_MAX_NE_15_MINS
                       OPTICAL_FEC_UNCWORD
                       OPTICAL_FECMISMATCH
                       OPTICAL_AS_MT
                       OPTICAL_PROV_IN_PROG
                       OPTICAL_LO_OSNR
                       OPTICAL_OUT_OF_RNG_CD
                       OPTICAL_HI_DGD
                       OPTICAL_TX_POWER_PROV_MISMATCH
                       OPTICAL_WVL_OUT_OF_LOCK
                       OPTICAL_UNQUALIFIED_PPM
                       OPTICAL_HI_LASERBIAS
                       OPTICAL_LO_TXPOWER
                       OPTICAL_HI_TXPOWER
                       OPTICAL_LO_RXPOWER
                       OPTICAL_HI_RXPOWER
                       OPTICAL_PROV_MISMATCH
                       OPTICAL_MEA
                       OPTICAL_IMPROPRMVL
                       FEC_POST_FEC_BER_MAX_NE_30_SEC
                       FEC_POST_FEC_BER_MIN_NE_30_SEC
                       FEC_PRE_FEC_BER_MAX_NE_30_SEC
                       FEC_PRE_FEC_BER_MIN_NE_30_SEC
                       FEC_Q_MARGIN_INST_MIN_NE_30_SEC
                       FEC_Q_MARGIN_INST_MAX_NE_30_SEC
                       FEC_Q_MARGIN_MIN_NE_30_SEC
                       FEC_Q_MARGIN_MAX_NE_30_SEC
                       FEC_Q_MIN_NE_30_SEC
                       FEC_Q_MAX_NE_30_SEC
                       FEC_POST_FEC_BER_MAX_NE_15_MINS
                       FEC_POST_FEC_BER_MIN_NE_15_MINS
                       FEC_PRE_FEC_BER_MAX_NE_15_MINS
                       FEC_PRE_FEC_BER_MIN_NE_15_MINS
                       FEC_Q_MARGIN_INST_MIN_NE_15_MINS
                       FEC_Q_MARGIN_INST_MAX_NE_15_MINS
                       FEC_Q_MARGIN_MIN_NE_15_MINS
                       FEC_Q_MARGIN_MAX_NE_15_MINS
                       FEC_Q_MIN_NE_15_MINS
                       FEC_Q_MAX_NE_15_MINS
                       FEC_POST_FEC_BER_MAX_NE_1_DAY
                       FEC_POST_FEC_BER_MIN_NE_1_DAY
                       FEC_PRE_FEC_BER_MAX_NE_1_DAY
                       FEC_PRE_FEC_BER_MIN_NE_1_DAY
                       FEC_Q_MARGIN_INST_MIN_NE_1_DAY
                       FEC_Q_MARGIN_INST_MAX_NE_1_DAY
                       FEC_Q_MARGIN_MIN_NE_1_DAY
                       FEC_Q_MARGIN_MAX_NE_1_DAY
                       FEC_Q_MIN_NE_1_DAY
                       FEC_Q_MAX_NE_1_DAY
                       FEC_EC_WORD_NE_30_SEC
                       FEC_EC_WORD_NE_1_DAY
                       FEC_EC_WORD_NE_15_MINS
                       FEC_UNC_WORDS_NE_30_SEC
                       FEC_BIT_EC_NE_30_SEC
                       FEC_UNC_WORDS_NE_15_MINS
                       FEC_UNC_WORDS_NE_1_DAY
                       FEC_BIT_EC_NE_1_DAY
                       FEC_BIT_EC_NE_15_MINS
                       OTNSEC_OUT_BLOCKS_UN_PROTECTED_NE_1_DAY
                       OTNSEC_OUT_BLOCKS_PROTECTED_NE_1_DAY
                       OTNSEC_OUT_BLOCKS_ZEROED_NE_1_DAY
                       OTNSEC_OUT_BLOCKS_SEQUENCE_ERRORS_NE_1_DAY
                       OTNSEC_OUT_BLOCKS_UN_ENCRYPTED_NE_1_DAY
                       OTNSEC_OUT_BLOCKS_ENC_NE_1_DAY
                       OTNSEC_OUT_BLOCKS_NE_1_DAY
                       OTNSEC_IN_BLOCKS_ZEROED_NE_1_DAY
                       OTNSEC_IN_BLOCKS_AUTH_ERRORS_NE_1_DAY
                       OTNSEC_IN_BLOCKS_REPLAY_ERRORS_NE_1_DAY
                       OTNSEC_IN_BLOCKS_SEQUENCE_ERRORS_NE_1_DAY
                       OTNSEC_IN_BLOCKS_UN_PROTECTED_NE_1_DAY
                       OTNSEC_IN_BLOCKS_PROTECTED_NE_1_DAY
                       OTNSEC_IN_BLOCKS_UN_ENCRYPTED_NE_1_DAY
                       OTNSEC_IN_BLOCKS_ENC_NE_1_DAY
                       OTNSEC_IN_BLOCKS_NE_1_DAY
                       OTNSEC_OUT_BLOCKS_UN_PROTECTED_NE_15_MINS
                       OTNSEC_OUT_BLOCKS_PROTECTED_NE_15_MINS
                       OTNSEC_OUT_BLOCKS_ZEROED_NE_15_MINS
                       OTNSEC_OUT_BLOCKS_SEQUENCE_ERRORS_NE_15_MINS
                       OTNSEC_OUT_BLOCKS_UN_ENCRYPTED_NE_15_MINS
                       OTNSEC_OUT_BLOCKS_ENC_NE_15_MINS
                       OTNSEC_OUT_BLOCKS_NE_15_MINS
                       OTNSEC_IN_BLOCKS_ZEROED_NE_15_MINS
                       OTNSEC_IN_BLOCKS_AUTH_ERRORS_NE_15_MINS
                       OTNSEC_IN_BLOCKS_REPLAY_ERRORS_NE_15_MINS
                       OTNSEC_IN_BLOCKS_SEQUENCE_ERRORS_NE_15_MINS
                       OTNSEC_IN_BLOCKS_UN_PROTECTED_NE_15_MINS
                       OTNSEC_IN_BLOCKS_PROTECTED_NE_15_MINS
                       OTNSEC_IN_BLOCKS_UN_ENCRYPTED_NE_15_MINS
                       OTNSEC_IN_BLOCKS_ENC_NE_15_MINS
                       OTNSEC_IN_BLOCKS_NE_15_MINS
                       OTNSEC_OUT_BLOCKS_UN_PROTECTED_NE_30_SEC
                       OTNSEC_OUT_BLOCKS_PROTECTED_NE_30_SEC
                       OTNSEC_OUT_BLOCKS_ZEROED_NE_30_SEC
                       OTNSEC_OUT_BLOCKS_SEQUENCE_ERRORS_NE_30_SEC
                       OTNSEC_OUT_BLOCKS_UN_ENCRYPTED_NE_30_SEC
                       OTNSEC_OUT_BLOCKS_ENC_NE_30_SEC
                       OTNSEC_OUT_BLOCKS_NE_30_SEC
                       OTNSEC_IN_BLOCKS_ZEROED_NE_30_SEC
                       OTNSEC_IN_BLOCKS_AUTH_ERRORS_NE_30_SEC
                       OTNSEC_IN_BLOCKS_REPLAY_ERRORS_NE_30_SEC
                       OTNSEC_IN_BLOCKS_SEQUENCE_ERRORS_NE_30_SEC
                       OTNSEC_IN_BLOCKS_UN_PROTECTED_NE_30_SEC
                       OTNSEC_IN_BLOCKS_PROTECTED_NE_30_SEC
                       OTNSEC_IN_BLOCKS_UN_ENCRYPTED_NE_30_SEC
                       OTNSEC_IN_BLOCKS_ENC_NE_30_SEC
                       OTNSEC_IN_BLOCKS_NE_30_SEC
                       PRBS_LOST_COUNT_NE_30_SEC
                       PRBS_FOUND_COUNT_NE_30_SEC
                       PRBS_EBC_NE_30_SEC
                       PRBS_LOST_COUNT_NE_1_DAY
                       PRBS_FOUND_COUNT_NE_1_DAY
                       PRBS_EBC_NE_1_DAY
                       PRBS_LOST_COUNT_NE_15_MINS
                       PRBS_FOUND_COUNT_NE_15_MINS
                       PRBS_EBC_NE_15_MINS
                       UAS_TCM6_FE_30_SEC
                       UAS_TCM6_NE_30_SEC
                       FC_TCM6_FE_30_SEC
                       FC_TCM6_NE_30_SEC
                       SESR_TCM6_FE_30_SEC
                       SESR_TCM6_NE_30_SEC
                       ESR_TCM6_FE_30_SEC
                       ESR_TCM6_NE_30_SEC
                       SES_TCM6_FE_30_SEC
                       SES_TCM6_NE_30_SEC
                       ES_TCM6_FE_30_SEC
                       ES_TCM6_NE_30_SEC
                       BBER_TCM6_FE_30_SEC
                       BBER_TCM6_NE_30_SEC
                       BBE_TCM6_FE_30_SEC
                       BBE_TCM6_NE_30_SEC
                       UAS_TCM5_FE_30_SEC
                       UAS_TCM5_NE_30_SEC
                       FC_TCM5_FE_30_SEC
                       FC_TCM5_NE_30_SEC
                       SESR_TCM5_FE_30_SEC
                       SESR_TCM5_NE_30_SEC
                       ESR_TCM5_FE_30_SEC
                       ESR_TCM5_NE_30_SEC
                       SES_TCM5_FE_30_SEC
                       SES_TCM5_NE_30_SEC
                       ES_TCM5_FE_30_SEC
                       ES_TCM5_NE_30_SEC
                       BBER_TCM5_FE_30_SEC
                       BBER_TCM5_NE_30_SEC
                       BBE_TCM5_FE_30_SEC
                       BBE_TCM5_NE_30_SEC
                       UAS_TCM4_FE_30_SEC
                       UAS_TCM4_NE_30_SEC
                       FC_TCM4_FE_30_SEC
                       FC_TCM4_NE_30_SEC
                       SESR_TCM4_FE_30_SEC
                       SESR_TCM4_NE_30_SEC
                       ESR_TCM4_FE_30_SEC
                       ESR_TCM4_NE_30_SEC
                       SES_TCM4_FE_30_SEC
                       SES_TCM4_NE_30_SEC
                       ES_TCM4_FE_30_SEC
                       ES_TCM4_NE_30_SEC
                       BBER_TCM4_FE_30_SEC
                       BBER_TCM4_NE_30_SEC
                       BBE_TCM4_FE_30_SEC
                       BBE_TCM4_NE_30_SEC
                       UAS_TCM3_FE_30_SEC
                       UAS_TCM3_NE_30_SEC
                       FC_TCM3_FE_30_SEC
                       FC_TCM3_NE_30_SEC
                       SESR_TCM3_FE_30_SEC
                       SESR_TCM3_NE_30_SEC
                       ESR_TCM3_FE_30_SEC
                       ESR_TCM3_NE_30_SEC
                       SES_TCM3_FE_30_SEC
                       SES_TCM3_NE_30_SEC
                       ES_TCM3_FE_30_SEC
                       ES_TCM3_NE_30_SEC
                       BBER_TCM3_FE_30_SEC
                       BBER_TCM3_NE_30_SEC
                       BBE_TCM3_FE_30_SEC
                       BBE_TCM3_NE_30_SEC
                       UAS_TCM2_FE_30_SEC
                       UAS_TCM2_NE_30_SEC
                       FC_TCM2_FE_30_SEC
                       FC_TCM2_NE_30_SEC
                       SESR_TCM2_FE_30_SEC
                       SESR_TCM2_NE_30_SEC
                       ESR_TCM2_FE_30_SEC
                       ESR_TCM2_NE_30_SEC
                       SES_TCM2_FE_30_SEC
                       SES_TCM2_NE_30_SEC
                       ES_TCM2_FE_30_SEC
                       ES_TCM2_NE_30_SEC
                       BBER_TCM2_FE_30_SEC
                       BBER_TCM2_NE_30_SEC
                       BBE_TCM2_FE_30_SEC
                       BBE_TCM2_NE_30_SEC
                       UAS_TCM1_FE_30_SEC
                       UAS_TCM1_NE_30_SEC
                       FC_TCM1_FE_30_SEC
                       FC_TCM1_NE_30_SEC
                       SESR_TCM1_FE_30_SEC
                       SESR_TCM1_NE_30_SEC
                       ESR_TCM1_FE_30_SEC
                       ESR_TCM1_NE_30_SEC
                       SES_TCM1_FE_30_SEC
                       SES_TCM1_NE_30_SEC
                       ES_TCM1_FE_30_SEC
                       ES_TCM1_NE_30_SEC
                       BBER_TCM1_FE_30_SEC
                       BBER_TCM1_NE_30_SEC
                       BBE_TCM1_FE_30_SEC
                       BBE_TCM1_NE_30_SEC
                       UAS_TCM6_FE_1_DAY
                       UAS_TCM6_NE_1_DAY
                       UAS_TCM6_FE_15_MINS
                       UAS_TCM6_NE_15_MINS
                       UAS_TCM5_FE_1_DAY
                       UAS_TCM5_NE_1_DAY
                       UAS_TCM5_FE_15_MINS
                       UAS_TCM5_NE_15_MINS
                       UAS_TCM4_FE_1_DAY
                       UAS_TCM4_NE_1_DAY
                       UAS_TCM4_FE_15_MINS
                       UAS_TCM4_NE_15_MINS
                       UAS_TCM3_FE_1_DAY
                       UAS_TCM3_NE_1_DAY
                       UAS_TCM3_FE_15_MINS
                       UAS_TCM3_NE_15_MINS
                       UAS_TCM2_FE_1_DAY
                       UAS_TCM2_NE_1_DAY
                       UAS_TCM2_FE_15_MINS
                       UAS_TCM2_NE_15_MINS
                       UAS_TCM1_FE_1_DAY
                       UAS_TCM1_NE_1_DAY
                       UAS_TCM1_FE_15_MINS
                       UAS_TCM1_NE_15_MINS
                       FC_TCM6_FE_1_DAY
                       FC_TCM6_NE_1_DAY
                       FC_TCM6_FE_15_MINS
                       FC_TCM6_NE_15_MINS
                       FC_TCM5_FE_1_DAY
                       FC_TCM5_NE_1_DAY
                       FC_TCM5_FE_15_MINS
                       FC_TCM5_NE_15_MINS
                       FC_TCM4_FE_1_DAY
                       FC_TCM4_NE_1_DAY
                       FC_TCM4_FE_15_MINS
                       FC_TCM4_NE_15_MINS
                       FC_TCM3_FE_1_DAY
                       FC_TCM3_NE_1_DAY
                       FC_TCM3_FE_15_MINS
                       FC_TCM3_NE_15_MINS
                       FC_TCM2_FE_1_DAY
                       FC_TCM2_NE_1_DAY
                       FC_TCM2_FE_15_MINS
                       FC_TCM2_NE_15_MINS
                       FC_TCM1_FE_1_DAY
                       FC_TCM1_NE_1_DAY
                       FC_TCM1_FE_15_MINS
                       FC_TCM1_NE_15_MINS
                       SESR_TCM6_FE_1_DAY
                       SESR_TCM6_NE_1_DAY
                       SESR_TCM6_FE_15_MINS
                       SESR_TCM6_NE_15_MINS
                       SESR_TCM5_FE_1_DAY
                       SESR_TCM5_NE_1_DAY
                       SESR_TCM5_FE_15_MINS
                       SESR_TCM5_NE_15_MINS
                       SESR_TCM4_FE_1_DAY
                       SESR_TCM4_NE_1_DAY
                       SESR_TCM4_FE_15_MINS
                       SESR_TCM4_NE_15_MINS
                       SESR_TCM3_FE_1_DAY
                       SESR_TCM3_NE_1_DAY
                       SESR_TCM3_FE_15_MINS
                       SESR_TCM3_NE_15_MINS
                       SESR_TCM2_FE_1_DAY
                       SESR_TCM2_NE_1_DAY
                       SESR_TCM2_FE_15_MINS
                       SESR_TCM2_NE_15_MINS
                       SESR_TCM1_FE_1_DAY
                       SESR_TCM1_NE_1_DAY
                       SESR_TCM1_FE_15_MINS
                       SESR_TCM1_NE_15_MINS
                       ESR_TCM6_FE_1_DAY
                       ESR_TCM6_NE_1_DAY
                       ESR_TCM6_FE_15_MINS
                       ESR_TCM6_NE_15_MINS
                       ESR_TCM5_FE_1_DAY
                       ESR_TCM5_NE_1_DAY
                       ESR_TCM5_FE_15_MINS
                       ESR_TCM5_NE_15_MINS
                       ESR_TCM4_FE_1_DAY
                       ESR_TCM4_NE_1_DAY
                       ESR_TCM4_FE_15_MINS
                       ESR_TCM4_NE_15_MINS
                       ESR_TCM3_FE_1_DAY
                       ESR_TCM3_NE_1_DAY
                       ESR_TCM3_FE_15_MINS
                       ESR_TCM3_NE_15_MINS
                       ESR_TCM2_FE_1_DAY
                       ESR_TCM2_NE_1_DAY
                       ESR_TCM2_FE_15_MINS
                       ESR_TCM2_NE_15_MINS
                       ESR_TCM1_FE_1_DAY
                       ESR_TCM1_NE_1_DAY
                       ESR_TCM1_FE_15_MINS
                       ESR_TCM1_NE_15_MINS
                       SES_TCM6_FE_1_DAY
                       SES_TCM6_NE_1_DAY
                       SES_TCM6_FE_15_MINS
                       SES_TCM6_NE_15_MINS
                       SES_TCM5_FE_1_DAY
                       SES_TCM5_NE_1_DAY
                       SES_TCM5_FE_15_MINS
                       SES_TCM5_NE_15_MINS
                       SES_TCM4_FE_1_DAY
                       SES_TCM4_NE_1_DAY
                       SES_TCM4_FE_15_MINS
                       SES_TCM4_NE_15_MINS
                       SES_TCM3_FE_1_DAY
                       SES_TCM3_NE_1_DAY
                       SES_TCM3_FE_15_MINS
                       SES_TCM3_NE_15_MINS
                       SES_TCM2_FE_1_DAY
                       SES_TCM2_NE_1_DAY
                       SES_TCM2_FE_15_MINS
                       SES_TCM2_NE_15_MINS
                       SES_TCM1_FE_1_DAY
                       SES_TCM1_NE_1_DAY
                       SES_TCM1_FE_15_MINS
                       SES_TCM1_NE_15_MINS
                       ES_TCM6_FE_1_DAY
                       ES_TCM6_NE_1_DAY
                       ES_TCM6_FE_15_MINS
                       ES_TCM6_NE_15_MINS
                       ES_TCM5_FE_1_DAY
                       ES_TCM5_NE_1_DAY
                       ES_TCM5_FE_15_MINS
                       ES_TCM5_NE_15_MINS
                       ES_TCM4_FE_1_DAY
                       ES_TCM4_NE_1_DAY
                       ES_TCM4_FE_15_MINS
                       ES_TCM4_NE_15_MINS
                       ES_TCM3_FE_1_DAY
                       ES_TCM3_NE_1_DAY
                       ES_TCM3_FE_15_MINS
                       ES_TCM3_NE_15_MINS
                       ES_TCM2_FE_1_DAY
                       ES_TCM2_NE_1_DAY
                       ES_TCM2_FE_15_MINS
                       ES_TCM2_NE_15_MINS
                       ES_TCM1_FE_1_DAY
                       ES_TCM1_NE_1_DAY
                       ES_TCM1_FE_15_MINS
                       ES_TCM1_NE_15_MINS
                       BBER_TCM6_FE_1_DAY
                       BBER_TCM6_NE_1_DAY
                       BBER_TCM6_FE_15_MINS
                       BBER_TCM6_NE_15_MINS
                       BBER_TCM5_FE_1_DAY
                       BBER_TCM5_NE_1_DAY
                       BBER_TCM5_FE_15_MINS
                       BBER_TCM5_NE_15_MINS
                       BBER_TCM4_FE_1_DAY
                       BBER_TCM4_NE_1_DAY
                       BBER_TCM4_FE_15_MINS
                       BBER_TCM4_NE_15_MINS
                       BBER_TCM3_FE_1_DAY
                       BBER_TCM3_NE_1_DAY
                       BBER_TCM3_FE_15_MINS
                       BBER_TCM3_NE_15_MINS
                       BBER_TCM2_FE_1_DAY
                       BBER_TCM2_NE_1_DAY
                       BBER_TCM2_FE_15_MINS
                       BBER_TCM2_NE_15_MINS
                       BBER_TCM1_FE_1_DAY
                       BBER_TCM1_NE_1_DAY
                       BBER_TCM1_FE_15_MINS
                       BBER_TCM1_NE_15_MINS
                       BBE_TCM6_FE_1_DAY
                       BBE_TCM6_NE_1_DAY
                       BBE_TCM6_FE_15_MINS
                       BBE_TCM6_NE_15_MINS
                       BBE_TCM5_FE_1_DAY
                       BBE_TCM5_NE_1_DAY
                       BBE_TCM5_FE_15_MINS
                       BBE_TCM5_NE_15_MINS
                       BBE_TCM4_FE_1_DAY
                       BBE_TCM4_NE_1_DAY
                       BBE_TCM4_FE_15_MINS
                       BBE_TCM4_NE_15_MINS
                       BBE_TCM3_FE_1_DAY
                       BBE_TCM3_NE_1_DAY
                       BBE_TCM3_FE_15_MINS
                       BBE_TCM3_NE_15_MINS
                       BBE_TCM2_FE_1_DAY
                       BBE_TCM2_NE_1_DAY
                       BBE_TCM2_FE_15_MINS
                       BBE_TCM2_NE_15_MINS
                       BBE_TCM1_FE_1_DAY
                       BBE_TCM1_NE_1_DAY
                       BBE_TCM1_FE_15_MINS
                       BBE_TCM1_NE_15_MINS
                       BBER_PM_FE_30_SEC
                       SESR_PM_FE_30_SEC
                       ESR_PM_FE_30_SEC
                       FC_PM_FE_30_SEC
                       BBE_PM_FE_30_SEC
                       UAS_PM_FE_30_SEC
                       SES_PM_FE_30_SEC
                       ES_PM_FE_30_SEC
                       BBER_PM_NE_30_SEC
                       SESR_PM_NE_30_SEC
                       ESR_PM_NE_30_SEC
                       FC_PM_NE_30_SEC
                       BBE_PM_NE_30_SEC
                       UAS_PM_NE_30_SEC
                       SES_PM_NE_30_SEC
                       ES_PM_NE_30_SEC
                       BBER_PM_FE_1_DAY
                       SESR_PM_FE_1_DAY
                       ESR_PM_FE_1_DAY
                       FC_PM_FE_1_DAY
                       BBE_PM_FE_1_DAY
                       UAS_PM_FE_1_DAY
                       SES_PM_FE_1_DAY
                       ES_PM_FE_1_DAY
                       BBER_PM_NE_1_DAY
                       SESR_PM_NE_1_DAY
                       ESR_PM_NE_1_DAY
                       FC_PM_NE_1_DAY
                       BBE_PM_NE_1_DAY
                       UAS_PM_NE_1_DAY
                       SES_PM_NE_1_DAY
                       ES_PM_NE_1_DAY
                       BBER_PM_FE_15_MINS
                       SESR_PM_FE_15_MINS
                       ESR_PM_FE_15_MINS
                       FC_PM_FE_15_MINS
                       BBE_PM_FE_15_MINS
                       UAS_PM_FE_15_MINS
                       SES_PM_FE_15_MINS
                       ES_PM_FE_15_MINS
                       BBER_PM_NE_15_MINS
                       SESR_PM_NE_15_MINS
                       ESR_PM_NE_15_MINS
                       FC_PM_NE_15_MINS
                       BBE_PM_NE_15_MINS
                       UAS_PM_NE_15_MINS
                       SES_PM_NE_15_MINS
                       ES_PM_NE_15_MINS
                       BBER_SM_FE_30_SEC
                       SESR_SM_FE_30_SEC
                       ESR_SM_FE_30_SEC
                       FC_SM_FE_30_SEC
                       BBE_SM_FE_30_SEC
                       UAS_SM_FE_30_SEC
                       SES_SM_FE_30_SEC
                       ES_SM_FE_30_SEC
                       BBER_SM_NE_30_SEC
                       SESR_SM_NE_30_SEC
                       ESR_SM_NE_30_SEC
                       FC_SM_NE_30_SEC
                       BBE_SM_NE_30_SEC
                       UAS_SM_NE_30_SEC
                       SES_SM_NE_30_SEC
                       ES_SM_NE_30_SEC
                       BBER_SM_FE_1_DAY
                       SESR_SM_FE_1_DAY
                       ESR_SM_FE_1_DAY
                       FC_SM_FE_1_DAY
                       BBE_SM_FE_1_DAY
                       UAS_SM_FE_1_DAY
                       SES_SM_FE_1_DAY
                       ES_SM_FE_1_DAY
                       BBER_SM_NE_1_DAY
                       SESR_SM_NE_1_DAY
                       ESR_SM_NE_1_DAY
                       FC_SM_NE_1_DAY
                       BBE_SM_NE_1_DAY
                       UAS_SM_NE_1_DAY
                       SES_SM_NE_1_DAY
                       ES_SM_NE_1_DAY
                       BBER_SM_FE_15_MINS
                       SESR_SM_FE_15_MINS
                       ESR_SM_FE_15_MINS
                       FC_SM_FE_15_MINS
                       BBE_SM_FE_15_MINS
                       UAS_SM_FE_15_MINS
                       SES_SM_FE_15_MINS
                       ES_SM_FE_15_MINS
                       BBER_SM_NE_15_MINS
                       SESR_SM_NE_15_MINS
                       ESR_SM_NE_15_MINS
                       FC_SM_NE_15_MINS
                       BBE_SM_NE_15_MINS
                       UAS_SM_NE_15_MINS
                       SES_SM_NE_15_MINS
                       ES_SM_NE_15_MINS
                       G709_FEC_UNCWORD
                       G709_ADDTNL_PARENT_DUMMY
                       G709_CRYPTO_INDEX_MISMATCH
                       G709_CRYPTO_KEY_EXPIRED
                       G709_SF_BER_PM
                       G709_SD_BER_PM
                       G709_SF_BER_TCM6
                       G709_SD_BER_TCM6
                       G709_TCM6_TIM
                       G709_TCM6_BDI
                       G709_TCM6_BIAE
                       G709_TCM6_IAE
                       G709_TCM6_LCK
                       G709_TCM6_OCI
                       G709_TCM6_LTC
                       G709_TCM6_AIS
                       G709_SF_BER_TCM5
                       G709_SD_BER_TCM5
                       G709_TCM5_TIM
                       G709_TCM5_BDI
                       G709_TCM5_BIAE
                       G709_TCM5_IAE
                       G709_TCM5_LCK
                       G709_TCM5_OCI
                       G709_TCM5_LTC
                       G709_TCM5_AIS
                       G709_SF_BER_TCM4
                       G709_SD_BER_TCM4
                       G709_TCM4_TIM
                       G709_TCM4_BDI
                       G709_TCM4_BIAE
                       G709_TCM4_IAE
                       G709_TCM4_LCK
                       G709_TCM4_OCI
                       G709_TCM4_LTC
                       G709_TCM4_AIS
                       G709_SF_BER_TCM3
                       G709_SD_BER_TCM3
                       G709_TCM3_TIM
                       G709_TCM3_BDI
                       G709_TCM3_BIAE
                       G709_TCM3_IAE
                       G709_TCM3_LCK
                       G709_TCM3_OCI
                       G709_TCM3_LTC
                       G709_TCM3_AIS
                       G709_SF_BER_TCM2
                       G709_SD_BER_TCM2
                       G709_TCM2_TIM
                       G709_TCM2_BDI
                       G709_TCM2_BIAE
                       G709_TCM2_IAE
                       G709_TCM2_LCK
                       G709_TCM2_OCI
                       G709_TCM2_LTC
                       G709_TCM2_AIS
                       G709_SF_BER_TCM1
                       G709_SD_BER_TCM1
                       G709_TCM1_TIM
                       G709_TCM1_BDI
                       G709_TCM1_BIAE
                       G709_TCM1_IAE
                       G709_TCM1_LCK
                       G709_TCM1_OCI
                       G709_TCM1_LTC
                       G709_TCM1_AIS
                       G709_PM_AS_MT
                       G709_OPU_CSF
                       G709_PM_BIAE
                       G709_PM_IAE
                       G709_OPU_PTIM
                       G709_PM_TIM
                       G709_PM_BDI
                       G709_PM_LCK
                       G709_PM_OCI
                       G709_PM_AIS
                       G709_INV_MUX_DUMMY
                       G709_FLEXO_RDI
                       G709_FLEXO_LOM
                       G709_FLEXO_LOF
                       G709_FLEXO_MM
                       G709_FLEXO_GIDM
                       G709_AS_MT
                       G709_FECMISMATCH
                       G709_SF_BER_SM
                       G709_SD_BER_SM
                       G709_TIM
                       G709_BDI
                       G709_BIAE
                       G709_IAE
                       G709_LOM
                       G709_LOF
                       G709_AIS
                       G709_LOS
                       FIBRE_CHANNEL_NOS
                       FIBRE_CHANNEL_SIGLOSS
                       FIBRE_CHANNEL_RF
                       FIBRE_CHANNEL_LF
                       FIBRE_CHANNEL_PCS_ERROR
                       FIBRE_CHANNEL_HI_BER
                       FIBRE_CHANNEL_SYNCLOSS
                       CPRI_SDI
                       CPRI_RAI
                       CPRI_LOF
                       CPRI_LOS
                       OTS_AS_MT
                       OTS_APC_RUNNING
                       OTS_SWITCH_TO_PROTECT
                       OTS_APC_CONFIG_MISMATCH
                       OTS_APC_DISABLED
                       OTS_AUTO_POW_RED
                       OTS_AUTO_LASER_SHUT
                       OTS_AMPLI_GAIN_HIGH
                       OTS_AMPLI_GAIN_LOW
                       OTS_RX_LOC
                       OTS_RX_LOS_P
                       OTS_RX_POWER_FAIL_LOW
                       OTS_TX_POWER_FAIL_LOW
                      ";
                  }
                  leaf sas {
                    type enumeration {
                      enum "UNKNOWN" {
                        value 0;
                        description
                          "Unkown severity";
                      }
                      enum "NONREPORTED" {
                        value 1;
                        description
                          "Non reported severity";
                      }
                      enum "NONFAULTED" {
                        value 2;
                        description
                          "Non faulted severity";
                      }
                      enum "MINOR" {
                        value 3;
                        description
                          "Minor severity";
                      }
                      enum "MAJOR" {
                        value 4;
                        description
                          "Major severity";
                      }
                      enum "CRITICAL" {
                        value 5;
                        description
                          "Critical severity";
                      }
                    }
                    mandatory true;
                    description
                      "Service affecting fault severity";
                  }
                  leaf nsas {
                    type enumeration {
                      enum "UNKNOWN" {
                        value 0;
                        description
                          "Unkown severity";
                      }
                      enum "NONREPORTED" {
                        value 1;
                        description
                          "Non reported severity";
                      }
                      enum "NONFAULTED" {
                        value 2;
                        description
                          "Non faulted severity";
                      }
                      enum "MINOR" {
                        value 3;
                        description
                          "Minor severity";
                      }
                      enum "MAJOR" {
                        value 4;
                        description
                          "Major severity";
                      }
                      enum "CRITICAL" {
                        value 5;
                        description
                          "Critical severity";
                      }
                    }
                    mandatory true;
                    description
                      "Not service affecting fault severity";
                  }
                }
              }
            }
          }
        }
        leaf description {
          type string {
            length "1..128" {
              description
                "Fault profile description";
            }
          }
          description
            "Fault profile description";
        }
        container apply {
          description
            "Apply fault profile";
          list rack {
            key "rack-number";
            description
              "rack numnber";
            leaf rack-number {
              type uint32 {
                range "0..1" {
                  description
                    "rack number";
                }
              }
              description
                "rack number";
            }
            container slots {
              description
                "physical rack slot";
              list slot {
                key "slot";
                description
                  "physical rack slot";
                leaf slot {
                  type string {
                    pattern "(LC[0-9]+)|ALL";
                  }
                  description
                    "physical rack slot";
                }
                container propagate {
                  presence "Indicates a propagate node is configured.";
                  description
                    "Apply fault profile on child entities of card";
                }
              }
            }
            container slot-ports {
              description
                "physical rack slot and port";
              list slot-port {
                key "slot port";
                description
                  "physical rack slot and port";
                leaf slot {
                  type string {
                    pattern "(LC[0-9]+)";
                  }
                  description
                    "slot number";
                }
                leaf port {
                  type uint32 {
                    range "0..32" {
                      description
                        "physical port";
                    }
                  }
                  description
                    "physical port";
                }
                container propagate {
                  presence "Indicates a propagate node is configured.";
                  description
                    "Apply fault profile on child entities";
                }
              }
            }
          }
        }
      }
    }
  }
}
