module Cisco-IOS-XR-ip-static-ipv6-oper {
  namespace "http://cisco.com/ns/yang/Cisco-IOS-XR-ip-static-ipv6-oper";
  prefix ip-static-ipv6-oper;

  import Cisco-IOS-XR-types {
    prefix xr;
  }
  import cisco-semver {
    prefix semver;
  }
  include Cisco-IOS-XR-ip-static-ipv6-oper-sub1 {
    revision-date 2026-04-13;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ip-static-ipv6 package operational data.
     
     This module contains definitions
     for the following management objects:
       ipv6-local: Local Routing Information
       ipv6-static: Static Routing Information
       ipv6-connected: connected Routing Information
     
     Copyright (c) 2013-2026 by Cisco Systems, Inc.
     All rights reserved.";

  revision 2026-04-13 {
    description
      "Updated prefix-length formatting";
    semver:module-version "3.0.0";
  }
  revision 2025-04-28 {
    description
      "Added support for cross-AFI next-hops
       2023-10-20
          Fixed support for ipv6-sr-policy-detail
       2023-06-21
          Added new elements to display nodeDB and Protect events
       2022-10-31
          Added support for static srv6 sid and locator
       2021-10-29
          Added leaf node for ip address algorithm";
    semver:module-version "2.0.0";
  }
  revision 2020-11-20 {
    description
      "Added leaf node for Prefer RIB over LDP";
    semver:module-version "1.2.0";
  }
  revision 2019-12-12 {
    description
      "Added leaf node for FlexAlgo for srv6";
    semver:module-version "1.1.0";
  }
  revision 2019-06-01 {
    description
      "Added oper ipv6 support for fridb, colocation, sr-policy
       2019-05-13
          Added ipv4 support for bfd sessions, object track database and segment routing";
    semver:module-version "1.1.0";
  }
  revision 2019-04-05 {
    description
      "Establish semantic version baseline.";
    semver:module-version "1.0.0";
  }
  revision 2019-01-03 {
    description
      "Added oper ipv6 support";
  }
  revision 2015-11-09 {
    description
      "IOS XR 6.0 revision.";
  }

  typedef Ipv6friafi {
    type enumeration {
      enum "ipv4" {
        value 1;
        description
          "ipv4 addressfamily";
      }
      enum "ipv6" {
        value 2;
        description
          "ipv6 addressfamily";
      }
    }
    description
      "Ipv6friafi";
  }

  typedef Afiipv6 {
    type enumeration {
      enum "ipv4" {
        value 1;
        description
          "ipv4 addressfamily";
      }
      enum "ipv6" {
        value 2;
        description
          "ipv6 addressfamily";
      }
    }
    description
      "Afiipv6";
  }

  typedef Safiipv6 {
    type enumeration {
      enum "unicast" {
        value 1;
        description
          "unicat type";
      }
      enum "multicast" {
        value 2;
        description
          "multicast type";
      }
    }
    description
      "Safiipv6";
  }

  typedef Ipv6frisafi {
    type enumeration {
      enum "unicast" {
        value 1;
        description
          "unicast type";
      }
      enum "multicast" {
        value 2;
        description
          "multicast type";
      }
    }
    description
      "Ipv6frisafi";
  }

  grouping TOPO-VRF-TABLE {
    description
      "Common node of ipv6-static, ipv6-local,
       ipv6-connected";
    container topo-vrfs {
      description
        "vrf list for Topology";
      list topo-vrf {
        key "vrf-name";
        description
          "vrf name";
        leaf vrf-name {
          type xr:Cisco-ios-xr-string;
          description
            "The name of thei vrf";
        }
        list topo-table {
          key "table-name";
          description
            "Topology table name";
          leaf table-name {
            type xr:Cisco-ios-xr-string;
            description
              "The name of the atble";
          }
          list topo-afi {
            key "afi";
            description
              "Topology address family type";
            leaf afi {
              type Afiipv6;
              description
                "IPv6 AFI";
            }
            list topo-safi {
              key "safi";
              description
                "Topology SAFI type";
              container destinations {
                description
                  "route info";
                list destination {
                  description
                    "Destinatioin address and prefix length";
                  leaf prefix {
                    type xr:Cisco-ios-xr-string;
                    description
                      "IP Prefix";
                  }
                  leaf prefix-length {
                    type xr:Ipv6-prefix-length;
                    description
                      "IPv6 Prefix length";
                  }
                  uses IPV6-STATIC-ROUTE-BD;
                }
              }
              leaf safi {
                type Safiipv6;
                description
                  "IPv6 SAFI";
              }
            }
          }
        }
      }
    }
  }

  grouping IPV6-PROTECT-NODE-EVENTS-DB {
    description
      "Common node of ipv6-local, ipv6-connected";
    container ipv6-protect-node-events {
      description
        "Protect interface event info";
      list ipv6-protect-node-event {
        key "node";
        description
          "Protect interface event";
        leaf node {
          type xr:Node-id;
          description
            "Node ID";
        }
        list ipv6-protect-interface-event {
          key "name";
          description
            "Protect Interface to display";
          leaf name {
            type xr:Interface-name;
            description
              "Interface Name";
          }
          uses IPV6-STATIC-PROT-INTF-EVENT-BD;
        }
      }
    }
  }

  grouping NHVRF-TABLE {
    description
      "Common node of ipv6-static, ipv6-local,
       ipv6-connected";
    container nhvrfs {
      description
        "next-hop's vrf list";
      list nhvrf {
        key "vrf-name";
        description
          "vrf name";
        leaf vrf-name {
          type xr:Cisco-ios-xr-string;
          description
            "The name of thei vrf";
        }
        list nh-table {
          key "table-name";
          description
            "next-hop table name";
          leaf table-name {
            type xr:Cisco-ios-xr-string;
            description
              "The name of the atble";
          }
          list nhafi {
            key "afi";
            description
              "next-hop address family type";
            leaf afi {
              type Afiipv6;
              description
                "IPv6 AFI";
            }
            list nhsafi {
              key "safi";
              description
                "next-hop safi(unicat|multicast) type";
              container nh-addresses {
                description
                  "next-hop Database";
                list nh-address {
                  key "next-hop-addr";
                  description
                    "next hop address to display";
                  leaf next-hop-addr {
                    type xr:Cisco-ios-xr-string;
                    description
                      "next hop address";
                  }
                  uses IPV6-STATIC-NHDB-BD;
                }
              }
              leaf safi {
                type Safiipv6;
                description
                  "IPv6 SAFI";
              }
            }
          }
        }
      }
    }
  }

  grouping TABLE {
    description
      "Common node of ipv6-static, ipv6-local,
       ipv6-connected";
    container table-ids {
      description
        "list of Tables";
      list table-id {
        key "table-id";
        description
          "Table ID to display";
        leaf table-id {
          type xr:Hex-integer;
          description
            "Table ID";
        }
        uses IP-STATIC-TDB-BD;
      }
    }
  }

  grouping IPV6FRIDB {
    description
      "Common node of ipv6-local, ipv6-connected";
    container ipv6fridbvrfs {
      description
        "ipv6 forward database";
      list ipv6fridbvrf {
        key "vrf-name";
        description
          "vrf name";
        leaf vrf-name {
          type xr:Cisco-ios-xr-string;
          description
            "Forward DB vrf name";
        }
        list ipv6fridb-table {
          key "table-name";
          description
            "table name";
          leaf table-name {
            type xr:Cisco-ios-xr-string;
            description
              "The name of the forward DB table";
          }
          list ipv6fridbafi {
            key "afitype";
            description
              "address family type";
            leaf afitype {
              type Ipv6friafi;
              description
                "IPv6 AFI";
            }
            list ipv6fridbsafi {
              key "safitype";
              description
                "unicast|multicast";
              leaf safitype {
                type Ipv6frisafi;
                description
                  "IPv6 SAFI";
              }
              list ipv6fridb-interface {
                key "interface-name";
                description
                  "forward DB Interface to display";
                leaf interface-name {
                  type xr:Interface-name;
                  description
                    "forward DB Interface name";
                }
                uses IP-STATIC-FRIDB-BD;
              }
            }
          }
        }
      }
    }
  }

  grouping BFDVRF-TABLE {
    description
      "Common node of ipv6-static, ipv6-local,
       ipv6-connected";
    container bfdvrfs {
      description
        "BFD's vrf list";
      list bfdvrf {
        key "vrf-name";
        description
          "vrf name";
        leaf vrf-name {
          type xr:Cisco-ios-xr-string;
          description
            "The name of the vrf";
        }
        list bfd-table {
          key "table-name";
          description
            "BFD table name";
          leaf table-name {
            type xr:Cisco-ios-xr-string;
            description
              "The name of the table";
          }
          list bfdafi {
            key "afi";
            description
              "BFD address family type";
            leaf afi {
              type Afiipv6;
              description
                "IPv6 AFI";
            }
            list bfdsafi {
              key "safi";
              description
                "BFD safi(unicat|multicast) type";
              container bfd-addresses {
                description
                  "list of BFD sessions";
                list bfd-address {
                  key "bfd-next-hop-addr";
                  description
                    "BFD next-hop address to display";
                  leaf bfd-next-hop-addr {
                    type xr:Cisco-ios-xr-string;
                    description
                      "BFD next hop address";
                  }
                  uses IPV6-STATIC-NHDB-BFD-BD;
                }
              }
              leaf safi {
                type Safiipv6;
                description
                  "IPv6 SAFI";
              }
            }
          }
        }
      }
    }
  }

  grouping TABLE-EVENTS {
    description
      "Common node of ipv6-static, ipv6-local,
       ipv6-connected";
    container table-events-ids {
      description
        "list of Tables";
      list table-events-id {
        key "table-id";
        description
          "Table ID to display events info";
        leaf table-id {
          type xr:Hex-integer;
          description
            "Table ID";
        }
        uses EVT-HIST-INFO;
      }
    }
  }

  grouping IPV6-PROTECT-NODE-DB {
    description
      "Common node of ipv6-local, ipv6-connected";
    container ipv6-protect-nodes {
      description
        "ipv6 Protect Node Database";
      list ipv6-protect-node {
        key "node";
        description
          "Protect Node to display";
        leaf node {
          type xr:Node-id;
          description
            "Node ID";
        }
        uses IPV6-STATIC-PROT-NODE-BD;
      }
    }
  }

  grouping IPV6-IF-DB {
    description
      "Common node of ipv6-static, ipv6-local,
       ipv6-connected";
    container ipv6vrfs {
      description
        "ipv6 interface database";
      list ipv6vrf {
        key "vrf-name";
        description
          "vrf name";
        leaf vrf-name {
          type xr:Cisco-ios-xr-string;
          description
            "The name of the";
        }
        list ipv6-table {
          key "table-name";
          description
            "table name";
          leaf table-name {
            type xr:Cisco-ios-xr-string;
            description
              "The name of the";
          }
          list ipv6afi {
            key "afi";
            description
              "address family type";
            leaf afi {
              type Afiipv6;
              description
                "IPv6 AFI";
            }
            list ipv6safi {
              key "safi";
              description
                "unicast|multicast";
              leaf safi {
                type Safiipv6;
                description
                  "IPv6 SAFI";
              }
              list ipv6-interface {
                key "interface-name";
                description
                  "Interface to display";
                leaf interface-name {
                  type xr:Interface-name;
                  description
                    "Interface name";
                }
                uses IPV6-STATIC-IDB-BD;
              }
            }
          }
        }
      }
    }
  }

  container ipv6-local {
    config false;
    description
      "Local Routing Information";
    uses IPV6FRIDB;
    uses NHVRF-TABLE;
    uses TABLE-EVENTS;
    uses IPV6-PROTECT-NODE-EVENTS-DB;
    uses BFDVRF-TABLE;
    uses TOPO-VRF-TABLE;
    uses IPV6-IF-DB;
    uses TABLE;
    uses IPV6-PROTECT-NODE-DB;
  }
  container ipv6-static {
    config false;
    description
      "Static Routing Information";
    container ipv6-track-object-names {
      description
        "list of track objects";
      list ipv6-track-object-name {
        key "ot-name";
        description
          "Track object to display";
        leaf ot-name {
          type xr:Cisco-ios-xr-string;
          description
            "The name of the tacking object";
        }
        uses IPV6-STATIC-OTDB-BD;
      }
    }
    container srv6-locators {
      description
        "Display locator database";
      list srv6-locator {
        key "locator-name";
        description
          "Locator to display";
        leaf locator-name {
          type xr:Cisco-ios-xr-string;
          description
            "Locator name";
        }
        uses IP-STATIC-LOCDB-BD;
      }
    }
    container ipv6-exp-paths {
      description
        "list of explicit paths";
      list ipv6-exp-path {
        key "explicit-path";
        description
          "Explicit path to display";
        leaf explicit-path {
          type xr:Cisco-ios-xr-string;
          description
            "The name of the explicit path";
        }
        uses IPV6-STATIC-TEDB-BD;
      }
    }
    container ipv6-colocationvrf-names {
      description
        "list of colocation vrfs";
      list ipv6-colocationvrf-name {
        key "vrf";
        description
          "vrf name of table id to display colocation list";
        leaf vrf {
          type xr:Cisco-ios-xr-string;
          description
            "vrf name";
        }
        list ipv6-colocation-table {
          key "table-name";
          description
            "table name to display colocation list";
          leaf table-name {
            type xr:Cisco-ios-xr-string;
            description
              "table name";
          }
          list ipv6-colocation-afi {
            key "afi";
            description
              "Colocation address family type";
            leaf afi {
              type Afiipv6;
              description
                "IPv6 AFI";
            }
            list ipv6-colocation-safi {
              key "safi";
              description
                "Colocation safi(unicat|multicast) type";
              container ipv6-colo-table-ids {
                description
                  "tables to display colocation list";
                list ipv6-colo-table-id {
                  key "table-id";
                  description
                    "table to display colocation list";
                  leaf table-id {
                    type xr:Hex-integer;
                    description
                      "Table ID";
                  }
                  uses IP-STATIC-COLOCATION-BD;
                }
              }
              leaf safi {
                type Safiipv6;
                description
                  "IPv6 SAFI";
              }
            }
          }
        }
      }
    }
    container ipv6-sr-policy-details {
      description
        "ipv6 sr-policy interface database";
      list ipv6-sr-policy-detail {
        key "srpolicy";
        description
          "sr policy to display";
        leaf srpolicy {
          type xr:Cisco-ios-xr-string;
          description
            "sr policy name";
        }
        uses IPV6-STATIC-XTC-DB-BD;
      }
    }
    container ipv6-sids {
      description
        "Display srv6 sid database";
      list ipv6-sid {
        key "srv6-sid-addr";
        description
          "Srv6 Sid to display";
        leaf srv6-sid-addr {
          type xr:Cisco-ios-xr-string;
          description
            "Srv6 Sid Addr";
        }
        uses IP-STATIC-SIDDB-BD;
      }
    }
    uses NHVRF-TABLE;
    uses TABLE-EVENTS;
    uses BFDVRF-TABLE;
    uses TOPO-VRF-TABLE;
    uses IPV6-IF-DB;
    uses TABLE;
  }
  container ipv6-connected {
    config false;
    description
      "connected Routing Information";
    uses IPV6FRIDB;
    uses NHVRF-TABLE;
    uses TABLE-EVENTS;
    uses IPV6-PROTECT-NODE-EVENTS-DB;
    uses BFDVRF-TABLE;
    uses TOPO-VRF-TABLE;
    uses IPV6-IF-DB;
    uses TABLE;
    uses IPV6-PROTECT-NODE-DB;
  }
}
