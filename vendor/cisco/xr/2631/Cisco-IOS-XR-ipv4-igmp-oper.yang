module Cisco-IOS-XR-ipv4-igmp-oper {
  namespace "http://cisco.com/ns/yang/Cisco-IOS-XR-ipv4-igmp-oper";
  prefix ipv4-igmp-oper;

  import ietf-inet-types {
    prefix inet;
  }
  import Cisco-IOS-XR-types {
    prefix xr;
  }
  import cisco-semver {
    prefix semver;
  }
  include Cisco-IOS-XR-ipv4-igmp-oper-sub1 {
    revision-date 2022-09-21;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ipv4-igmp package operational data.
     
     This model is deprecated and is replaced by
     Cisco-IOS-XR-igmp-oper.yang which will provide the
     compatible functionalities.
     
     This module contains definitions
     for the following management objects:
       mld: MLD operational data
       igmp: IGMP operational data
     
     Copyright (c) 2013-2022 by Cisco Systems, Inc.
     All rights reserved.";

  revision 2022-09-21 {
    description
      "event-history ipv4_igmp.bag/ipv4_igmp_common_oper.sch show igmp missed-packet";
    semver:module-version "3.0.0";
  }
  revision 2021-05-17 {
    description
      "Added DVMRP packet counter tracking for malloc and free.";
    semver:module-version "2.1.0";
  }
  revision 2019-10-31 {
    description
      "Changes to IOS-XR IGMP oper";
    semver:module-version "2.1.0";
  }
  revision 2019-04-05 {
    description
      "Establish semantic version baseline.";
    semver:module-version "1.1.0";
  }
  revision 2018-01-31 {
    description
      "Fixed incorrect plural rendering.";
  }
  revision 2017-09-07 {
    description
      "Fixed type translation error.";
  }
  revision 2015-11-09 {
    description
      "IOS XR 6.0 revision.";
  }

  typedef Igmpssm-map {
    type enumeration {
      enum "static" {
        value 0;
        description
          "Static";
      }
      enum "dns" {
        value 1;
        description
          "Dns";
      }
      enum "all" {
        value 2;
        description
          "All";
      }
    }
    description
      "Igmpssm map";
  }

  grouping VRF-TABLE {
    description
      "Common node of active, standby";
    container vrfs {
      description
        "VRF Table";
      list vrf {
        key "vrf-name";
        description
          "VRF table Names";
        container summary {
          description
            "IGMP Summary Information";
          uses IGMP-EDM-SUMMARY-BAG;
        }
        container interface-state-ons {
          description
            "IGMP Interface state on";
          list interface-state-on {
            key "interface-name";
            description
              "IGMP Interface";
            leaf interface-name {
              type xr:Interface-name;
              description
                "Interface Name";
            }
            uses IGMP-EDM-IDB-BAG;
          }
        }
        container detail-groups {
          description
            "IGMP Detail Group Database";
          list detail-group {
            key "group-address interface-name source-address";
            description
              "IGMP Detail Group Entry Information";
            leaf group-address {
              type inet:ip-address-no-zone;
              description
                "Group Address";
            }
            leaf interface-name {
              type xr:Interface-name;
              description
                "Interface Name";
            }
            leaf source-address {
              type inet:ip-address-no-zone;
              description
                "Source/Host Address";
            }
            uses IGMP-EDM-GROUPS-DETAIL-BAG;
          }
        }
        container non-active-groups {
          description
            "IGMP Non-Active Groups Information";
          uses IGMP-EDM-NOT-ACTIVE-ALLGROUPS-BAG;
        }
        container ssm-maps {
          description
            "SSM Map Table";
          list ssm-map {
            key "ssm-map-type group-address";
            description
              "SSM Map information";
            leaf ssm-map-type {
              type Igmpssm-map;
              description
                "SSM Map Type";
            }
            leaf group-address {
              type inet:ip-address-no-zone;
              description
                "Group address";
            }
            uses IGMP-EDM-SSM-MAP-BAG;
          }
        }
        container explicit-groups {
          description
            "IGMP Explicit Group Database";
          list explicit-group {
            key "group-address interface-name source-address";
            description
              "IGMP Explicit Group Entry Information";
            leaf group-address {
              type inet:ip-address-no-zone;
              description
                "Group Address";
            }
            leaf interface-name {
              type xr:Interface-name;
              description
                "Interface Name";
            }
            leaf source-address {
              type inet:ip-address-no-zone;
              description
                "Source/Host Address";
            }
            uses IGMP-EDM-GROUPS-ET-BAG;
          }
        }
        container interface-table {
          description
            "IGMP Interface specific Table";
          uses INTERFACE;
        }
        container interface-unicast-qos-adjusts {
          description
            "IGMP Interface Unicast-Qos-Adjust";
          list interface-unicast-qos-adjust {
            key "interface-name";
            description
              "IGMP Interface";
            leaf interface-name {
              type xr:Interface-name;
              description
                "Interface Name";
            }
            uses IGMP-EDM-I2Q-INTF-STATS-BAG;
          }
        }
        container ranges {
          description
            "Range table";
          list range {
            key "group-address group-mask";
            description
              "Range information";
            leaf group-address {
              type inet:ip-address-no-zone;
              description
                "Group address";
            }
            leaf group-mask {
              type uint32;
              description
                "Group Mask";
            }
            uses IGMP-GROUP-RANGE;
          }
        }
        container ifrs-interfaces {
          description
            "IGMP Interface specific";
          list ifrs-interface {
            key "interface-name";
            description
              "IGMP IFRS Interface";
            leaf interface-name {
              type xr:Interface-name;
              description
                "IFRS Interface Name";
            }
            uses IGMP-EDM-IDB-IFRS-BAG;
          }
        }
        container traffic-counters {
          description
            "IGMP Message Traffic Counters";
          uses IGMP-EDM-TRAFFIC-BAG;
        }
        container groups {
          description
            "IGMP Group Database Table";
          list group {
            key "group-address interface-name";
            description
              "IGMP Group Entry Information";
            leaf group-address {
              type inet:ip-address-no-zone;
              description
                "Group Address";
            }
            leaf interface-name {
              type xr:Interface-name;
              description
                "Interface Name";
            }
            uses IGMP-EDM-GROUPS-BAG;
          }
        }
        container group-summary {
          description
            "IGMP Groups Summary";
          uses IGMP-EDM-GROUPS-SUMMARY-BAG;
        }
        container ifrs-interface-summary {
          description
            "IGMP IFRS Interface summary";
          uses IGMP-EDM-IDB-SUMM-BAG;
        }
        container global-interface-table {
          description
            "IGMP Global Interface ";
          uses INTERFACE;
        }
        container ssm-map-details {
          description
            "SSM Map Detail";
          list ssm-map-detail {
            key "ssm-map-type group-address";
            description
              "SSM Map Detail Table information";
            leaf ssm-map-type {
              type Igmpssm-map;
              description
                "SSM Map Type";
            }
            leaf group-address {
              type inet:ip-address-no-zone;
              description
                "Group address";
            }
            uses IGMP-EDM-SSM-MAP-DETAIL-BAG;
          }
        }
        container interface-state-offs {
          description
            "IGMP Interface state off";
          list interface-state-off {
            key "interface-name";
            description
              "IGMP Interface";
            leaf interface-name {
              type xr:Interface-name;
              description
                "Interface Name";
            }
            uses IGMP-EDM-IDB-BAG;
          }
        }
        leaf vrf-name {
          type xr:Cisco-ios-xr-string {
            length "1..32";
          }
          description
            "VRF name";
        }
      }
    }
  }

  grouping INTERFACE {
    description
      "Common node of interface-table,
       global-interface-table";
    list interface {
      key "interface-name";
      description
        "IGMP Interface";
      leaf interface-name {
        type xr:Interface-name;
        description
          "Interface Name";
      }
      uses IGMP-EDM-IDB-BAG;
    }
  }

  grouping PROCESS {
    description
      "Common node of active, standby";
    container process {
      description
        "Process";
      container amt-summary {
        description
          "MRIB RouteDB Expiry Information";
        uses AMT-SUMMARY-BAG;
      }
      container nsr {
        description
          "NSR Information";
        uses IGMP-EDM-NSR-BAG;
      }
      container amt-gateways {
        description
          "Table containing AMT Gateway DataBase
           information";
        list amt-gateway {
          key "gateway-address port";
          description
            "AMT Gateway DataBase information";
          leaf gateway-address {
            type inet:ipv4-address-no-zone;
            description
              "Gateway Address";
          }
          leaf port {
            type uint32;
            description
              "Port";
          }
          uses AMT-GW-BAG;
        }
      }
      container unicast-qos-adjust-stats {
        description
          "IGMP Unicast-Qos-Adjust Statistics";
        uses IGMP-EDM-I2Q-STATS-BAG;
      }
      container bvi-statistics {
        description
          "IGMP BVI Stats";
        uses IGMP-EDM-BVI-STATS-BAG;
      }
      container missed-packets-table {
        description
          "Missed packets information";
        container missed-packets-membership-table {
          description
            "Missed packets membership information";
          uses IGMP-MISSED-PACKETS-LIST-BAG;
        }
        container missed-packets-ssm-query-table {
          description
            "Missed packets ssm query information";
          uses IGMP-MISSED-PACKETS-LIST-BAG;
        }
        container missed-packets-general-query-table {
          description
            "Missed packets general query information";
          uses IGMP-MISSED-PACKETS-LIST-BAG;
        }
        container missed-packets-group-specific-table {
          description
            "Missed packets group specific information";
          uses IGMP-MISSED-PACKETS-LIST-BAG;
        }
      }
      container nsf {
        description
          "NSF Information";
        uses IGMP-EDM-NSF-BAG;
      }
    }
  }

  grouping ACTIVE {
    description
      "Common node of igmp, mld";
    container active {
      description
        "Active Process";
      uses VRF-TABLE;
      uses PROCESS;
    }
  }

  grouping STANDBY {
    description
      "Common node of igmp, mld";
    container standby {
      description
        "Standby Process";
      uses VRF-TABLE;
      uses PROCESS;
    }
  }

  container mld {
    config false;
    status deprecated;
    description
      "This model is deprecated and is replaced by
       Cisco-IOS-XR-igmp-oper.yang which will provide
       the compatible functionalities.  MLD operational
       data";
    uses STANDBY;
    uses ACTIVE;
  }
  container igmp {
    config false;
    status deprecated;
    description
      "This model is deprecated and is replaced by
       Cisco-IOS-XR-igmp-oper.yang which will provide
       the compatible functionalities.  IGMP operational
       data";
    uses STANDBY;
    uses ACTIVE;
  }
}
