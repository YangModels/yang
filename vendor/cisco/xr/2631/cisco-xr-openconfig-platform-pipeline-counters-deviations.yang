module cisco-xr-openconfig-platform-pipeline-counters-deviations {
  namespace "http://cisco.com/ns/yang/cisco-xr-openconfig-platform-pipeline-counters-deviations";
  prefix oc-ppc-devs;

  import openconfig-platform-pipeline-counters {
    prefix oc-ppc;
  }
  import openconfig-platform {
    prefix oc-platform;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a set of deviations for 
      
     openconfig-platform-pipeline-counters.yang

     on Cisco IOS-XR devices.

     Copyright (c) 2025-2026 by Cisco Systems, Inc., and/or its affiliates.
     All rights reserved.";

  revision "2026-02-18" {
    description
      "Added deviations for deprecated lookup-block drop counters.";
  }

  revision "2025-12-17" {
    description
      "Initial revision with ACL-related leaf node deviations.";
  }

  // Deviation for acl-memory-total-entries
  deviation "/oc-platform:components/oc-platform:component/oc-platform:integrated-circuit/oc-ppc:pipeline-counters/oc-ppc:packet/oc-ppc:lookup-block/oc-ppc:state/oc-ppc:acl-memory-total-entries" {
    deviate not-supported;
    description
      "ACL memory total entries counter is not supported on this platform.";
  }

  // Deviation for acl-memory-used-entries
  deviation "/oc-platform:components/oc-platform:component/oc-platform:integrated-circuit/oc-ppc:pipeline-counters/oc-ppc:packet/oc-ppc:lookup-block/oc-ppc:state/oc-ppc:acl-memory-used-entries" {
    deviate not-supported;
    description
      "ACL memory used entries counter is not supported on this platform.";
  }

  // Deviation for acl-memory-total-bytes
  deviation "/oc-platform:components/oc-platform:component/oc-platform:integrated-circuit/oc-ppc:pipeline-counters/oc-ppc:packet/oc-ppc:lookup-block/oc-ppc:state/oc-ppc:acl-memory-total-bytes" {
    deviate not-supported;
    description
      "ACL memory total bytes counter is not supported on this platform.";
  }

  // Deviation for acl-memory-used-bytes
  deviation "/oc-platform:components/oc-platform:component/oc-platform:integrated-circuit/oc-ppc:pipeline-counters/oc-ppc:packet/oc-ppc:lookup-block/oc-ppc:state/oc-ppc:acl-memory-used-bytes" {
    deviate not-supported;
    description
      "ACL memory used bytes counter is not supported on this platform.";
  }

  // Deviation for acl-drops
  deviation "/oc-platform:components/oc-platform:component/oc-platform:integrated-circuit/oc-ppc:pipeline-counters/oc-ppc:drop/oc-ppc:lookup-block/oc-ppc:state/oc-ppc:acl-drops" {
    deviate not-supported;
    description
      "ACL drops counter is not supported on this platform.";
  }

  // Deviation for no-route
  deviation "/oc-platform:components/oc-platform:component/oc-platform:integrated-circuit/oc-ppc:pipeline-counters/oc-ppc:drop/oc-ppc:lookup-block/oc-ppc:state/oc-ppc:no-route" {
    deviate not-supported;
    description
      "No-route drops counter is not supported on this platform.";
  }

  // Deviation for no-label
  deviation "/oc-platform:components/oc-platform:component/oc-platform:integrated-circuit/oc-ppc:pipeline-counters/oc-ppc:drop/oc-ppc:lookup-block/oc-ppc:state/oc-ppc:no-label" {
    deviate not-supported;
    description
      "No-label drops counter is not supported on this platform.";
  }

  // Deviation for no-nexthop
  deviation "/oc-platform:components/oc-platform:component/oc-platform:integrated-circuit/oc-ppc:pipeline-counters/oc-ppc:drop/oc-ppc:lookup-block/oc-ppc:state/oc-ppc:no-nexthop" {
    deviate not-supported;
    description
      "No-nexthop drops counter is not supported on this platform.";
  }

  // Deviation for invalid-packet
  deviation "/oc-platform:components/oc-platform:component/oc-platform:integrated-circuit/oc-ppc:pipeline-counters/oc-ppc:drop/oc-ppc:lookup-block/oc-ppc:state/oc-ppc:invalid-packet" {
    deviate not-supported;
    description
      "Invalid-packet drops counter is not supported on this platform.";
  }

  // Deviation for forwarding-policy
  deviation "/oc-platform:components/oc-platform:component/oc-platform:integrated-circuit/oc-ppc:pipeline-counters/oc-ppc:drop/oc-ppc:lookup-block/oc-ppc:state/oc-ppc:forwarding-policy" {
    deviate not-supported;
    description
      "Forwarding-policy drops counter is not supported on this platform.";
  }

  // Deviation for incorrect-software-state
  deviation "/oc-platform:components/oc-platform:component/oc-platform:integrated-circuit/oc-ppc:pipeline-counters/oc-ppc:drop/oc-ppc:lookup-block/oc-ppc:state/oc-ppc:incorrect-software-state" {
    deviate not-supported;
    description
      "Incorrect-software-state drops counter is not supported on this platform.";
  }

  // Deviation for rate-limit
  deviation "/oc-platform:components/oc-platform:component/oc-platform:integrated-circuit/oc-ppc:pipeline-counters/oc-ppc:drop/oc-ppc:lookup-block/oc-ppc:state/oc-ppc:rate-limit" {
    deviate not-supported;
    description
      "Rate-limit drops counter is not supported on this platform.";
  }

  // Deviation for fragment-total-drops
  deviation "/oc-platform:components/oc-platform:component/oc-platform:integrated-circuit/oc-ppc:pipeline-counters/oc-ppc:drop/oc-ppc:lookup-block/oc-ppc:state/oc-ppc:fragment-total-drops" {
    deviate not-supported;
    description
      "Fragment-total-drops counter is not supported on this platform.";
  }

  // Deviation for lookup-aggregate
  deviation "/oc-platform:components/oc-platform:component/oc-platform:integrated-circuit/oc-ppc:pipeline-counters/oc-ppc:drop/oc-ppc:lookup-block/oc-ppc:state/oc-ppc:lookup-aggregate" {
    deviate not-supported;
    description
      "Lookup-aggregate drops counter is not supported on this platform.";
  }

  // Deviation for oversubscription
  deviation "/oc-platform:components/oc-platform:component/oc-platform:integrated-circuit/oc-ppc:pipeline-counters/oc-ppc:drop/oc-ppc:lookup-block/oc-ppc:state/oc-ppc:oversubscription" {
    deviate not-supported;
    description
      "Oversubscription drops counter is not supported on this platform.";
  }
}
