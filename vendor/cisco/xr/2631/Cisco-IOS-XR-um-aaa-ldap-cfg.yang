module Cisco-IOS-XR-um-aaa-ldap-cfg {
  namespace "http://cisco.com/ns/yang/Cisco-IOS-XR-um-aaa-ldap-cfg";
  prefix um-aaa-ldap-cfg;

  import Cisco-IOS-XR-types {
    prefix xr;
  }
  import ietf-inet-types {
    prefix inet;
  }
  import Cisco-IOS-XR-um-aaa-cfg {
    prefix a1;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR aaa-ldap package configuration.
     
     This YANG module augments the
     modules with configuration data.
     
     Copyright (c) 2026 by Cisco Systems, Inc., and/or its affiliates.
     All rights reserved.";

  revision 2026-04-29 {
    description
      "Initial release";
    semver:module-version "1.0.0";
  }

  augment "/a1:aaa" {
    description
      "This augment extends aaa nodes configuration";
    container ldap-server {
      description
        "LDAP server definition";
      container hosts {
        description
          "Specify a LDAP server";
        list host {
          key "ordering-index address port";
          description
            "Specify a LDAP server";
          leaf ordering-index {
            type uint32;
            description
              "This is used to sort the servers in the
               order of precedence";
          }
          leaf address {
            type inet:ip-address-no-zone;
            description
              "Specify a LDAP server";
          }
          leaf port {
            type uint32 {
              range "1..65535" {
                description
                  "Port number";
              }
            }
            description
              "TCP port for LDAP server (default is 389)";
          }
          leaf connect-timeout {
            type uint32 {
              range "1..1000" {
                description
                  "Timeout value in seconds to wait for server to reply for connect";
              }
            }
            description
              "Time in seconds to wait for this LDAP server to reply for connect (overrides default)";
          }
          leaf bind-timeout {
            type uint32 {
              range "1..1000" {
                description
                  "Timeout value in seconds to wait for server to reply for bind";
              }
            }
            description
              "Time in seconds to wait for this LDAP server to reply for bind (overrides default)";
          }
          leaf search-timeout {
            type uint32 {
              range "1..1000" {
                description
                  "Timeout value in seconds to wait for server to reply for search ";
              }
            }
            description
              "Time in seconds to wait for this LDAP server to reply for search (overrides default)";
          }
          leaf bind-dn {
            type string {
              length "1..800" {
                description
                  "Bind DN for LDAP connection.";
              }
            }
            description
              "Bind DN (Distinguished Name)";
          }
          leaf vrf {
            type string {
              length "1..800" {
                description
                  "VRF name for LDAP connection.";
              }
            }
            description
              "vrf name";
          }
          container bind-password {
            description
              "per-server encryption key (overrides default)";
            leaf seven {
              type xr:Proprietary-password;
              description
                "Specifies that a key will follow";
            }
          }
        }
      }
      leaf source-interface {
        type xr:Interface-name;
        description
          "Specify interface for source address in LDAP packets";
      }
      container vrfs {
        description
          "VRF for this source interface configuration";
        list vrf {
          key "vrf-name";
          description
            "VRF for this source interface configuration";
          leaf vrf-name {
            type xr:Cisco-ios-xr-string {
              length "1..32" {
                description
                  "Name of the VRF";
              }
            }
            description
              "VRF for this source interface configuration";
          }
          leaf source-interface {
            type xr:Interface-name;
            mandatory true;
            description
              "Specify interface for source address in LDAP packets";
          }
        }
      }
    }
  }
}
