module Cisco-IOS-XR-um-netconf-yang-cfg {
  yang-version 1.1;
  namespace "http://cisco.com/ns/yang/Cisco-IOS-XR-um-netconf-yang-cfg";
  prefix um-netconf-yang-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions for Cisco IOS-XR
     NETCONF YANG configuration.
     
     Copyright (c) 2019-2026 by Cisco Systems, Inc., and/or its affiliates.
     All rights reserved.";

  revision 2026-03-19 {
    description
      "Update to align with latest IOS-XR YANG quality guidelines.
       2026-02-19
         Changed range of netconf-yang/agent/session/limit from 1..50 to 1..128";
    semver:module-version "4.0.0";
  }
  revision 2025-07-31 {
    description
      "Removed absolute-timeout leaf from session container
       2023-10-20
          Added netconf1.0 container at netconf-yang agent level
       2021-11-22
          Added submod-enter at netconf-yang agent level";
    semver:module-version "3.0.0";
  }
  revision 2020-03-06 {
    description
      "- Removed models/openconfig/disable as the config has been deprecated.
       - Added a new container to enable with-defaults support.";
    semver:module-version "2.0.0";
  }
  revision 2019-06-10 {
    description
      "Establish semantic version baseline.";
    semver:module-version "1.0.1";
  }
  revision 2019-03-30 {
    description
      "Initial version";
  }

  container netconf-yang {
    description
      "NETCONF YANG configuration";
    reference
      "RFC 6241 - NETCONF Configuration Protocol
       RFC 6242 - Using the NETCONF Protocol over Secure Shell (SSH)";
    container agent {
      presence "Enables the NETCONF YANG agent";
      description
        "NETCONF YANG agent configuration";
      leaf ssh {
        type empty;
        description
          "Enable NETCONF-YANG agent over SSH connection";
      }
      container with-defaults-support {
        description
          "With-defaults support";
        reference "RFC 6243 - With-defaults Capability for NETCONF";
        leaf enable {
          type empty;
          description
            "Enable with-defaults support";
        }
      }
      leaf rate-limit {
        type uint32 {
          range "4096..max";
        }
        units "bytes per second";
        description
          "Number of bytes to process per second";
      }
      container session {
        description
          "Session settings";
        leaf limit {
          type uint8 {
            range "1..128";
          }
          default "50";
          description
            "Maximum count of concurrent sessions";
        }
        leaf idle-timeout {
          type uint16 {
            range "1..1440";
          }
          units "minutes";
          description
            "Timeout for an inactive session";
        }
      }
      container netconf1.0 {
        presence "Enable NETCONF version 1.0 support";
        description
          "NETCONF 1.0 configuration";
        reference
          "RFC 4741 - NETCONF Configuration Protocol
           RFC 4742 - Using the NETCONF Configuration Protocol over Secure
                      Shell (SSH)";
        leaf only {
          type empty;
          description
            "Disable NETCONF version 1.1 support";
        }
        leaf streaming-disabled {
          type empty;
          description
            "Disable streaming RPC reply messages";
        }
      }
    }
  }
}
