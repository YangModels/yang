module Cisco-IOS-XR-lpts-pa-act {
  namespace "http://cisco.com/ns/yang/Cisco-IOS-XR-lpts-pa-act";
  prefix lpts-pa-act;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR action package configuration.
     
        Copyright (c) 2016-2020 by Cisco Systems, Inc.
            All rights reserved.";

  revision 2020-09-20 {
    description
      "Initial revision";
    semver:module-version "1.0.0";
  }

  rpc clear-lpts-internal-queue-pa-statistics {
    description
      "Clear lpts internal stats ";
  }
  rpc clear-lpts-client-times {
    description
      "Clear lpts client times ";
  }
}
