module Cisco-IOS-XR-um-hw-module-vrf-cfg {
  namespace "http://cisco.com/ns/yang/Cisco-IOS-XR-um-hw-module-vrf-cfg";
  prefix um-hw-module-vrf-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR hw-module-vrf package configuration.
     
     This YANG module augments the
     modules with configuration data.
     
     Copyright (c) 2020-2025 by Cisco Systems, Inc., and/or its affiliates.
     All rights reserved.";

  revision 2020-05-08 {
    description
      "Initial release";
    semver:module-version "1.0.0";
  }

  container hw-module {
    description
      "Configure h/w module";
    container vrf {
      description
        "Configure vrf profile";
      leaf scale {
        type enumeration {
          enum "default" {
            value 0;
            description
              "Default vrf scale";
          }
          enum "extended" {
            value 1;
            description
              "Extended vrf scale";
          }
        }
        description
          "Configure vrf scale";
      }
    }
  }
}
