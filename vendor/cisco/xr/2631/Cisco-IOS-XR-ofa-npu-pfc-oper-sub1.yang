submodule Cisco-IOS-XR-ofa-npu-pfc-oper-sub1 {
  belongs-to Cisco-IOS-XR-ofa-npu-pfc-oper {
    prefix Cisco-IOS-XR-ofa-npu-pfc-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR ofa-npu-pfc package operational data.
     
     Copyright (c) 2013-2025 by Cisco Systems, Inc.
     All rights reserved.";

  revision 2025-03-19 {
    description
      "Added PFC related feilds, max-non-pfc-voqs, default, hbm-buffers-percentage";
    semver:module-version "1.1.0";
  }
  revision 2021-10-10 {
    description
      "Added PFC related fields, ecn, ecn-max, tc-pause-threshold, tc-ecn-max, tc-prob-per, tc-pause-threshold-unit, tc-headroom-unit, tc-ecn-unit and tc-ecn-max-unit.";
  }
  revision 2021-08-19 {
    description
      "Create the initial priority-flow-control oper yang model.";
  }
  revision 2019-04-05 {
    description
      "Establish semantic version baseline.";
  }
  revision 2015-11-09 {
    description
      "IOS XR 6.0 revision.";
  }

  grouping OFA-PFC-TC-MAP {
    description
      "OFA PFC TC MAP";
    leaf hbm-pool-num {
      type uint8;
      description
        "Hbm Pool Num";
    }
    leaf cgm-tc-group {
      type uint8;
      description
        "Cgm TC Group";
    }
  }

  grouping OFA-PFC-TC-CFG {
    description
      "OFA PFC TC CFG";
    leaf in-use {
      type uint32;
      description
        "Flag to indicate if PFC is configured for the tc";
    }
    leaf tc-pause-threshold {
      type uint32;
      description
        "Pause-threshold configured";
    }
    leaf tc-headroom {
      type uint32;
      description
        "Headroom configured";
    }
    leaf tc-ecn {
      type uint32;
      description
        "ECN configured";
    }
    leaf tc-ecn-max {
      type uint32;
      description
        "ECN Max configured";
    }
    leaf tc-prob-per {
      type uint32;
      description
        "ECN Prob Per configured";
    }
    leaf tc-pause-threshold-unit {
      type string {
        length "0..6";
      }
      description
        "Pause-threshold Unit";
    }
    leaf tc-headroom-unit {
      type string {
        length "0..6";
      }
      description
        "Headroom Unit";
    }
    leaf tc-ecn-unit {
      type string {
        length "0..6";
      }
      description
        "Ecn Unit";
    }
    leaf tc-ecn-max-unit {
      type string {
        length "0..6";
      }
      description
        "Ecn Max Unit";
    }
    leaf tc-reload-state {
      type uint32;
      description
        "Reload State";
    }
    leaf rx-only {
      type uint32;
      description
        "rx_only mode";
    }
  }

  grouping OFA-PFC-CFG {
    description
      "OFA PFC CFG";
    leaf in-use {
      type uint32;
      description
        "Flag to indicate if PFC is configured for the
         line-card";
    }
    leaf pfc-mode {
      type string {
        length "0..31";
      }
      description
        "pfc mode configured";
    }
    leaf evict-lossy-tcs {
      type uint32;
      description
        "evict lossy tcs";
    }
    leaf max-evict-lossy-voq {
      type uint32;
      description
        "max evict lossy voq";
    }
    leaf dflt-max-evict-lossy-voq {
      type uint32;
      description
        "default max evict lossy voq";
    }
    leaf total-hbm-buffers {
      type uint32;
      description
        "total hbm buffers";
    }
    leaf evict-lossless-max-hbm-buffers-per {
      type uint32;
      description
        "evict lossless max hbm buffers per";
    }
    leaf evict-lossy-max-hbm-buffers-per {
      type uint32;
      description
        "evict lossy max hbm buffers per";
    }
    list tc-cfg {
      max-elements "8";
      description
        "Keeps a record of the PFC configuration for the
         line-card";
      uses OFA-PFC-TC-CFG;
    }
    list tc-map {
      max-elements "8";
      description
        "tc to hbm pool map and tc to ctcg mapping";
      uses OFA-PFC-TC-MAP;
    }
  }
}
