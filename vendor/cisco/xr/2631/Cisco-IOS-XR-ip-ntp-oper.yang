module Cisco-IOS-XR-ip-ntp-oper {
  namespace "http://cisco.com/ns/yang/Cisco-IOS-XR-ip-ntp-oper";
  prefix ip-ntp-oper;

  import Cisco-IOS-XR-types {
    prefix xr;
  }
  import cisco-semver {
    prefix semver;
  }
  include Cisco-IOS-XR-ip-ntp-oper-sub1 {
    revision-date 2022-09-22;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ip-ntp package operational data.
     
     This module contains definitions
     for the following management objects:
       ntp: NTP operational data
     
     Copyright (c) 2013-2022 by Cisco Systems, Inc.
     All rights reserved.";

  revision 2022-09-22 {
    description
      "Added NTP panic handling related.";
    semver:module-version "1.2.0";
  }
  revision 2021-08-23 {
    description
      "Strong NTP authentication needs addition of authentication type.";
    semver:module-version "1.1.0";
  }
  revision 2019-04-05 {
    description
      "Establish semantic version baseline.";
    semver:module-version "1.0.1";
  }
  revision 2015-11-09 {
    description
      "IOS XR 6.0 revision.";
  }

  container ntp {
    config false;
    description
      "NTP operational data";
    container nodes {
      description
        "Node-specific NTP operational data";
      list node {
        key "node";
        description
          "NTP operational data for a particular node";
        container associations-detail {
          description
            "NTP Associations Detail information";
          uses NTP-EDM-ASSOC-DETAIL-RESULT;
        }
        container status {
          description
            "Status of NTP peer(s)";
          uses NTP-EDM-STATUS-RESULT;
        }
        container associations {
          description
            "NTP Associations information";
          uses NTP-EDM-ASSOC-SUMMARY-RESULT;
        }
        leaf node {
          type xr:Node-id;
          description
            "The node identifier";
        }
      }
    }
  }
}
