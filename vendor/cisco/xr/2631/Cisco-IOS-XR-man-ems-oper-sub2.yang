submodule Cisco-IOS-XR-man-ems-oper-sub2 {
  belongs-to Cisco-IOS-XR-man-ems-oper {
    prefix Cisco-IOS-XR-man-ems-oper;
  }

  import cisco-semver {
    prefix semver;
  }
  include Cisco-IOS-XR-man-ems-oper-sub1 {
    revision-date 2026-07-08;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR man-ems package operational data.
     
     Copyright (c) 2013-2026 by Cisco Systems, Inc.
     All rights reserved.";

  revision 2026-07-08 {
    description
      "Added pre-authentication connection gating counters to gRPC server state";
    semver:module-version "2.1.0";
  }
  revision 2025-04-28 {
    description
      "Removed status container under grpc.
       2024-08-28
          Added yang support for show grpc services
       2024-07-16
          Added support to view tls versions
       2024-03-03
          Added SRTE session list
       2023-12-18
          Added 'key' statement to list node 'destination'.
       2023-11-28
          Added support to view max-concurrent-streams.
       2023-09-01
          Added support to view certificate used by gRPC server for TLS authentication.
       2023-07-27
          Added gNMI, P4RT, and gRIBI service ports to grpc state.
       2023-06-01
          Added support for certificate common name.
       2023-04-26
          Added support for EMSd-Go soft memory limit.
       2023-04-21
          Added server name, keepalive time, timeout, enforcement to grpc state
       2023-03-22
          Added nodes server-keepalive-timeout and server-keepalive-time.
       2023-02-05
          Added gRPC tunnel virtual IP and listen address.
       2022-12-07
          Added support for gRPC listen addresses
       2022-07-20
          Added support for gRPC TLS version 1.0 flag
       2022-04-26
          Added support for gRPC server name
       2021-10-22
          Added certificate bundle statistics
       2021-10-20
          Added counters for load bundle
       2021-09-13
          Added status string to reflect unavailable port state.";
    semver:module-version "2.0.0";
  }
  revision 2021-06-10 {
    description
      "Added gRPC tunnel.";
    semver:module-version "1.2.0";
  }
  revision 2021-03-22 {
    description
      "Added keep alive commands.";
    semver:module-version "1.1.0";
  }
  revision 2019-04-05 {
    description
      "Establish semantic version baseline.";
    semver:module-version "1.0.1";
  }
  revision 2019-02-22 {
    description
      "Fixed yang evaluator warnings.";
  }
  revision 2015-11-09 {
    description
      "IOS XR 6.0 revision.";
  }

  grouping GRPC-SRTE-COUNTERS {
    description
      "srte rpc counters";
    leaf num-of-requests {
      type uint64;
      description
        "Number of RPC requests sent";
    }
    leaf num-of-responses {
      type uint64;
      description
        "Number of responses received";
    }
    leaf num-of-errors {
      type uint64;
      description
        "Number of errors";
    }
  }

  grouping GRPC-SRTE-SERVICE-SESSIONS {
    description
      "SRTE service session";
    container counters {
      description
        "stats for this destination";
      uses GRPC-SRTE-COUNTERS;
    }
    leaf address-xr {
      type string;
      description
        "Destination address";
    }
    leaf status {
      type Grpc-tunnel-status;
      description
        "Session status";
    }
    leaf status-str {
      type string;
      description
        "Status string in case of error";
    }
    leaf source-interface {
      type string;
      description
        "Source interface";
    }
    leaf source-ip {
      type string;
      description
        "Source interface IP";
    }
    leaf source-vrf {
      type string;
      description
        "Source interface vrf";
    }
    leaf vrf {
      type string;
      description
        "Configured VRF";
    }
    leaf no-tls {
      type boolean;
      description
        "TLS turned off when set to true";
    }
    leaf last-connected-timestamp {
      type uint64;
      description
        "Timestamp when session got connected";
    }
    leaf last-attempted-timestamp {
      type uint64;
      description
        "Timestamp when connection attempt was done";
    }
  }
}
