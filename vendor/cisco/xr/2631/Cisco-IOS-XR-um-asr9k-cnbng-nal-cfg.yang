module Cisco-IOS-XR-um-asr9k-cnbng-nal-cfg {
  namespace "http://cisco.com/ns/yang/Cisco-IOS-XR-um-asr9k-cnbng-nal-cfg";
  prefix um-asr9k-cnbng-nal-cfg;

  import Cisco-IOS-XR-types {
    prefix xr;
  }
  import ietf-inet-types {
    prefix inet;
  }
  import ietf-yang-types {
    prefix yang;
  }
  import Cisco-IOS-XR-um-interface-cfg {
    prefix a1;
  }
  import Cisco-IOS-XR-um-location-cfg {
    prefix location;
  }
  import tailf-common {
    prefix tailf;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR asr9k-cnbng-nal package configuration.
     
     This YANG module augments the
     modules with configuration data.
     
     Copyright (c) 2021-2026 by Cisco Systems, Inc., and/or its affiliates.
     All rights reserved.";

  revision 2026-03-23 {
    description
      "Fixed prefix_len range for access-control-route to start from 0 instead of 1.
       2026-02-18
         Added IPv4 support for access-control-route under subscriber redundancy group config.
       2026-01-19
         Added up-instance-id config under cnbng config and subscriber redundancy group config.
       2025-09-22
         Moved ipsubscriber config under cnbng-nal container";
    semver:module-version "3.0.0";
  }
  revision 2025-07-09 {
    description
      "Added max warm subscriber create config for warm group srg switchover
       2025-07-08
          Added config support for tracking l2tp tunnel ns/nr
       2025-07-07
          Added frame-route-metric-as-distance config under cnbng-nal
       2024-10-23
          Added ipv6-enable config support for auto loopback
       2024-10-14
          Added access and state control next-hop config under srg group
       2024-03-12
          Added ipv6 option under up-server and cp-server
       2023-09-28
          Added sub-interface index ranges under cnbng-nal interface configuration
       2023-03-21
          Deleted the group config under the cnbng-nal config
       2022-12-16
          Added new configs for ipv6 nd
       2022-09-27
          Added missing config CLI's
       2022-07-11
          Added missing description statement to nodes";
    semver:module-version "2.0.0";
  }
  revision 2021-05-26 {
    description
      "Initial release";
    semver:module-version "1.0.0";
  }

  grouping IF-BODY {
    description
      "Grouping for interface";
    container pppoe {
      when "../a1:interface-name[starts-with(text(),'FastEthernet')] or ../a1:interface-name[starts-with(text(),'GigabitEthernet')] or ../a1:interface-name[starts-with(text(),'TenGigE')] or ../a1:interface-name[starts-with(text(),'TwentyFiveGigE')] or ../a1:interface-name[starts-with(text(),'FortyGigE')] or ../a1:interface-name[starts-with(text(),'FiftyGigE')] or ../a1:interface-name[starts-with(text(),'HundredGigE')] or ../a1:interface-name[starts-with(text(),'TwoHundredGigE')] or ../a1:interface-name[starts-with(text(),'FourHundredGigE')] or ../a1:interface-name[starts-with(text(),'EightHundredGigE')] or ../a1:interface-name[starts-with(text(),'CPRIoE')] or ../a1:interface-name[starts-with(text(),'Bundle-Ether')] or ../a1:interface-name[starts-with(text(),'PW-Ether')]" {
        tailf:dependency "../a1:interface-name";
      }
      description
        "PPP over Ethernet";
      container enable {
        presence "Indicates a enable node is configured.";
        description
          "Enable PPPoE on the interface";
        leaf bba-group {
          type xr:Cisco-ios-xr-string {
            length "1..800" {
              description
                "The bba-group to use";
            }
          }
          description
            "Specify the bba-group to use with the interface";
        }
      }
    }
    container lns {
      when "../a1:interface-name[starts-with(text(),'Bundle-Ether')]" {
        tailf:dependency "../a1:interface-name";
      }
      description
        "lns enable";
      container enable {
        presence "Indicates a enable node is configured.";
        description
          "Enable LNS on the interface";
      }
    }
    container cnbng-nal {
      presence "Indicates a cnbng-nal node is configured.";
      description
        "Configure CNBNG interface settings";
      container ipsubscriber {
        when "../../a1:interface-name[starts-with(text(),'GigabitEthernet')] or ../../a1:interface-name[starts-with(text(),'TenGigE')] or ../../a1:interface-name[starts-with(text(),'TwentyFiveGigE')] or ../../a1:interface-name[starts-with(text(),'FortyGigE')] or ../../a1:interface-name[starts-with(text(),'HundredGigE')] or ../../a1:interface-name[starts-with(text(),'TwoHundredGigE')] or ../../a1:interface-name[starts-with(text(),'FourHundredGigE')] or ../../a1:interface-name[starts-with(text(),'EightHundredGigE')] or ../../a1:interface-name[starts-with(text(),'Bundle-Ether')] or ../../a1:interface-name[starts-with(text(),'PW-Ether')]" {
          tailf:dependency "../../a1:interface-name";
        }
        presence "Indicates a ipsubscriber node is configured.";
        description
          "Configure IP Subscriber settings";
        container ipv4 {
          description
            "Enable IPv4 Subscriber";
          container l2-connected {
            presence "Indicates a l2-connected node is configured.";
            description
              "Enable L2-connected IP Subscriber";
            container initiator {
              description
                "Configure IP Subscriber initiator";
              container dhcp {
                presence "Indicates a dhcp node is configured.";
                description
                  "Configure DHCP as first-sign-of-life protocol for IPv4 subscriber";
              }
            }
          }
          container routed {
            presence "Indicates a routed node is configured.";
            description
              "Enable Routed IP Subscriber";
            container initiator {
              description
                "Configure IP Subscriber initiator";
              container dhcp {
                presence "Indicates a dhcp node is configured.";
                description
                  "Configure DHCP as first-sign-of-life protocol for IPv4 subscriber";
              }
            }
          }
        }
        container ipv6 {
          description
            "Enable IPv6 Subscriber";
          container l2-connected {
            presence "Indicates a l2-connected node is configured.";
            description
              "Enable L2-connected IP Subscriber";
            container initiator {
              description
                "Configure IP Subscriber initiator";
              container dhcp {
                presence "Indicates a dhcp node is configured.";
                description
                  "Configure DHCP as first-sign-of-life protocol for IPv6 subscriber";
              }
            }
          }
          container routed {
            presence "Indicates a routed node is configured.";
            description
              "Enable Routed IP Subscriber";
            container initiator {
              description
                "Configure IP Subscriber initiator";
              container dhcp {
                presence "Indicates a dhcp node is configured.";
                description
                  "Configure DHCP as first-sign-of-life protocol for IPv6 subscriber";
                leaf prefix-len {
                  type uint32 {
                    range "1..127" {
                      description
                        "Prefix length";
                    }
                  }
                  description
                    "Prefix length for routed IPv6 subscribers";
                }
                container src-ip-dual-lookup {
                  must "../prefix-len";
                  presence "Indicates a src-ip-dual-lookup node is configured.";
                  description
                    "Enable source ip dual lookup";
                }
              }
            }
          }
        }
      }
      container ipv6 {
        description
          "Configure IPv6 settings for interface";
        container nd {
          presence "Indicates a nd node is configured.";
          description
            "Configure IPv6 ND related settings";
          container managed-config-flag {
            presence "Indicates a managed-config-flag node is configured.";
            description
              "Hosts should use stateful protocol for address config";
          }
          container other-config-flag {
            presence "Indicates a other-config-flag node is configured.";
            description
              "Hosts should use stateful protocol for non-address config";
          }
          container start-ra-on-ipv6-enable {
            presence "Indicates a start-ra-on-ipv6-enable node is configured.";
            description
              "Start RA generation on ipv6-enable config irrespective ipv6 afi state";
          }
          container ra-unicast {
            presence "Indicates a ra-unicast node is configured.";
            description
              "IPv6 unicast RA enable configuration";
          }
          container suppress-ra {
            presence "Indicates a suppress-ra node is configured.";
            description
              "Suppress IPv6 Router Advertisements(RA)";
          }
          container nud-enable {
            presence "Indicates a nud-enable node is configured.";
            description
              "IPv6 Neighbor Unreachability Detection(NUD) configuration. Applies only to IPoe Sessions";
          }
          container suppress-cache-learning {
            presence "Indicates a suppress-cache-learning node is configured.";
            description
              "To suppress cache learning on the interface";
          }
          container hop-limit {
            description
              "IPv6 Neighbor Discovery(ND) Router Advertisement(RA) hoplimit";
            container unspecified {
              presence "Indicates a unspecified node is configured.";
              description
                "Unspecified IPv6 Neighbor Discovery(ND) Router Advertisement(RA) hop-limit value";
            }
          }
          container mtu {
            description
              "IPv6 Neighbor Discovery(ND) Router Advertisement(RA) mtu option configuration";
            container suppress {
              presence "Indicates a suppress node is configured.";
              description
                "Suppress mtu option in IPv6  Neighbor Discovery(ND) Router Advertisement(RA) header";
            }
          }
          container router-preference {
            description
              "IPv6 ND router-preference";
            container high {
              must "not(../medium or ../low)";
              presence "Indicates a high node is configured.";
              description
                "High default router preference";
            }
            container medium {
              must "not(../high or ../low)";
              presence "Indicates a medium node is configured.";
              description
                "Medium default router preference";
            }
            container low {
              must "not(../high or ../medium)";
              presence "Indicates a low node is configured.";
              description
                "Low default router preference";
            }
          }
          leaf ra-lifetime {
            type uint32 {
              range "0..9000" {
                description
                  "RA Lifetime (seconds)";
              }
            }
            description
              "Set IPv6 Router Advertisement(RA) Lifetime";
          }
          leaf ns-interval {
            type uint32 {
              range "1000..4294967295" {
                description
                  "Retransmission interval in milliseconds";
              }
            }
            description
              "Set advertised Neighbor Solicitation(NS) retransmission interval";
          }
          leaf reachable-time {
            type uint32 {
              range "0..3600000" {
                description
                  "Reachability time in milliseconds";
              }
            }
            description
              "Set advertised reachability time";
          }
          leaf ra-interval {
            type uint32 {
              range "4..1800" {
                description
                  "Maximum RA Interval (sec)";
              }
            }
            description
              "Set IPv6 Router Advertisement(RA) Interval";
          }
          leaf minimum-ra-interval {
            type uint32 {
              range "3..1800" {
                description
                  "Minimum RA Interval (sec). Must be less than 0.75 * maximum interval";
              }
            }
            must "../ra-interval";
            description
              "Minimum RA Interval (sec). Must be less than 0.75 * maximum interval";
          }
          leaf ra-initial {
            type uint32 {
              range "0..32" {
                description
                  "Initial number of Router Advertisements(RA)";
              }
            }
            description
              "Set IPv6 Initial Router Advertisement(RA) Count and Interval";
          }
          leaf initial-router-advertisement {
            type uint32 {
              range "4..1800" {
                description
                  "Initial Router Advertisement(RA) Interval (sec)";
              }
            }
            must "../ra-initial";
            description
              "Initial Router Advertisement(RA) Interval (sec)";
          }
          container slaac {
            presence "Indicates a slaac node is configured.";
            description
              "Enable slaac prefix for subscriber";
          }
        }
      }
    }
  }

  grouping LOCATION-BODY {
    description
      "Grouping for location";
    container cnbng-nal {
      presence "Indicates a cnbng-nal node is configured.";
      description
        "Network Adaption Layer configuration";
      container enable-test-server {
        presence "Indicates a enable-test-server node is configured.";
        description
          "Enable test server for cnBNG NAL";
      }
      leaf max-create-in-progress {
        type uint32 {
          range "0..4294967295" {
            description
              "Value";
          }
        }
        description
          "Set max create in progress allowed";
      }
      leaf max-update-in-progress {
        type uint32 {
          range "0..4294967295" {
            description
              "Value";
          }
        }
        description
          "Set max update in progress allowed";
      }
      leaf max-delete-in-progress {
        type uint32 {
          range "0..4294967295" {
            description
              "Value";
          }
        }
        description
          "Set max delete in progress allowed";
      }
      leaf delete-batch-size {
        type uint32 {
          range "0..4294967295" {
            description
              "Value";
          }
        }
        description
          "Set batch size of bulk delete";
      }
      leaf delete-batch-timer {
        type uint32 {
          range "0..4294967295" {
            description
              "Value in ms";
          }
        }
        description
          "Set batch timer of bulk delete (ms)";
      }
      leaf max-warm-create-in-progress {
        type uint32 {
          range "50..200" {
            description
              "Create request range";
          }
        }
        description
          "Set max warm type subscriber create in progress allowed (dev only)";
      }
      leaf description {
        type string {
          length "1..256" {
            description
              "Config User-description";
          }
        }
        description
          "Description of the cnBNG NAL local-plane";
      }
      leaf hostidentifier {
        type xr:Cisco-ios-xr-string {
          length "1..64" {
            description
              "NAL Host-name";
          }
          pattern "[a-zA-Z][-_.a-z0-9A-Z]*";
        }
        description
          "NAL Host Identifier";
      }
      container route-summary {
        description
          "NAL Route-summary tag value";
        leaf tag {
          type uint32 {
            range "1..4294967295" {
              description
                "Tag value";
            }
          }
          description
            "Set a tag value for the route";
        }
      }
      container up-server {
        description
          "NAL control-plane up-server connection configs";
        leaf ipv4 {
          type inet:ipv4-address-no-zone;
          must "not(../interface or ../ipv6)";
          description
            "IP address type of UP's server";
        }
        leaf ipv6 {
          type inet:ipv6-address-no-zone;
          must "not(../interface or ../ipv4)";
          description
            "IP address type of UP's server";
        }
        leaf interface {
          type xr:Interface-name {
            pattern "Loopback.*";
          }
          must "not(../ipv4 or ../ipv6)";
          description
            "IPv4 address of UP's server";
        }
        leaf gtp-port {
          type uint32 {
            range "15002..15051" {
              description
                "UP-server source GTP port-number";
            }
          }
          must "(../ipv4 or ../ipv6 or ../interface)";
          description
            "user-plane's GTP port-number";
        }
        leaf pfcp-port {
          type uint32 {
            range "15002..15051" {
              description
                "UP-server source PFCP port-number";
            }
          }
          must "(../ipv4 or ../ipv6 or ../interface)";
          description
            "user-plane's PFCP port-number";
        }
        leaf vrf {
          type union {
            type string {
              pattern "default" {
                description
                  "UP-server default VRF";
              }
            }
            type xr:Cisco-ios-xr-string {
              length "1..32" {
                description
                  "UP server's VRF Name";
              }
            }
          }
          must "(../ipv4 or ../ipv6 or ../interface)";
          description
            "UP server's VRF Name";
        }
      }
      container cp-server {
        description
          "NAL control-plane server connection configs";
        container primary {
          description
            "NAL's control-plane primary-server configs";
          leaf ipv4 {
            type inet:ipv4-address-no-zone;
            must "not(../ipv6)";
            description
              "IP address type of CP's primary-server";
          }
          leaf ipv6 {
            type inet:ipv6-address-no-zone;
            must "not(../ipv4)";
            description
              "IP address type of CP's primary-server";
          }
        }
      }
      container disconnect-history {
        description
          "Disconnect history related config items";
        container file-logging-enable {
          presence "Indicates a file-logging-enable node is configured.";
          description
            "Enable file logging";
        }
      }
      container secondary-address-update {
        description
          "Secondary address update during route provision";
        container enable {
          presence "Indicates a enable node is configured.";
          description
            "Enable secondary address update";
        }
      }
      container cp-association {
        description
          "CP association";
        leaf retry-count {
          type uint32 {
            range "5..20" {
              description
                "Retry count";
            }
          }
          description
            "Retry count";
        }
      }
      container spa-req-resp-history {
        description
          "SPA request response history related config items";
        container file-logging-enable {
          presence "Indicates a file-logging-enable node is configured.";
          description
            "Enable file logging";
        }
      }
      container ipoe {
        description
          "ipoe related config";
        leaf fsol-flow-control {
          type uint32 {
            range "50..400" {
              description
                "cps";
            }
          }
          description
            "ipoe fsol flow control";
        }
      }
      container pppoe {
        description
          "pppoe related config";
        leaf fsol-flow-control {
          type uint32 {
            range "50..400" {
              description
                "cps";
            }
          }
          description
            "pppoe fsol flow control";
        }
      }
      container up-cp-notification {
        description
          "up cp notification related config";
        leaf flow-control {
          type uint32 {
            range "20..400" {
              description
                "limit";
            }
          }
          description
            "up cp notification flow control";
        }
        leaf global-flow-control {
          type uint32 {
            range "100..1200" {
              description
                "global limit";
            }
          }
          description
            "up cp notification global flow control";
        }
      }
      container trace {
        description
          "NAL trace level config";
        container level {
          description
            "Set a level for the trace";
          container critical {
            must
              "not(../high or ../default
               or ../low or ../verbose
               or ../all)";
            presence "Indicates a critical node is configured.";
            description
              "NAL trace level critical";
          }
          container high {
            must
              "not(../critical or ../default
               or ../low or ../verbose
               or ../all)";
            presence "Indicates a high node is configured.";
            description
              "NAL trace level high";
          }
          container default {
            must
              "not(../critical or ../high
               or ../low or ../verbose
               or ../all)";
            presence "Indicates a default node is configured.";
            description
              "NAL trace level default (medium)";
          }
          container low {
            must
              "not(../critical or ../high
               or ../default or ../verbose
               or ../all)";
            presence "Indicates a low node is configured.";
            description
              "NAL trace level low";
          }
          container verbose {
            must
              "not(../critical or ../high
               or ../default or ../low
               or ../all)";
            presence "Indicates a verbose node is configured.";
            description
              "NAL trace level verbose";
          }
          container all {
            must
              "not(../critical or ../high
               or ../default or ../low
               or ../verbose)";
            presence "Indicates a all node is configured.";
            description
              "NAL trace level all";
          }
        }
      }
      container disable-secondary-address-notification {
        presence "Indicates a disable-secondary-address-notification node is configured.";
        description
          "Disable secondary address notifiaction for the subscriber interfaces";
      }
      container up-cp-stats {
        description
          "up cp stats related config";
        leaf flow-control {
          type uint32 {
            range "20..500" {
              description
                "limit";
            }
          }
          description
            "up stats flow control";
        }
        leaf global-flow-control {
          type uint32 {
            range "150..1300" {
              description
                "global limit";
            }
          }
          description
            "up stats global flow control";
        }
      }
      container enable-tr459-mode {
        presence "Indicates a enable-tr459-mode node is configured.";
        description
          "Enable user-plane mode TR459";
      }
      container l2tp {
        description
          "l2tp config";
        container enable {
          presence "Indicates a enable node is configured.";
          description
            "Enable l2tp";
        }
        container map-tunnel-local-end-point-loopback {
          presence "Indicates a map-tunnel-local-end-point-loopback node is configured.";
          description
            "Map L2TP tunnel local end point to loopback interface";
        }
        container track-ns-nr {
          presence "Indicates tracking l2tp tunnel ns-nr is enabled.";
          description
            "Enable the tracking of l2tp ns-nr";
        }
      }
      leaf l2tp-tcp-mss-adjust {
        type uint32 {
          range "1280..1460" {
            description
              "Tcp mss adjust range";
          }
        }
        description
          "l2tp tcp-mss-adjust config";
      }
      container framed-route-metric-as-distance {
        presence "Indicates a framed-route-metric-as-distance node is configured.";
        description
          "Use framed-route metric as distance";
      }
      container auto-loopback {
        description
          "NAL Auto-Loopback configurations";
        container vrf {
          description
            "NAL Auto-loopback VRF info";
          list vrf {
            key "vrf-name";
            description
              "NAL Auto-Loopback vrf";
            leaf vrf-name {
              type union {
                type string {
                  pattern "default" {
                    description
                      "default VRF";
                  }
                }
                type xr:Cisco-ios-xr-string {
                  length "1..32" {
                    description
                      "VRF Name";
                  }
                }
              }
              description
                "NAL Auto-Loopback vrf name";
            }
            container interfaces {
              description
                "NAL Auto-Loopback interface";
              list interface {
                key "interface-name";
                description
                  "NAL Auto-Loopback interface";
                leaf interface-name {
                  type xr:Interface-name {
                    pattern "Loopback.*";
                  }
                  description
                    "NAL Auto-Loopback interface";
                }
                leaf primary-address {
                  type inet:ipv4-address-no-zone;
                  description
                    "NAL Auto-Loopback interface Primary Address";
                }
                container ipv6-enable {
                  presence "Indicates a ipv6-enable node is configured.";
                  description
                    "NAL Auto-Loopback interface ipv6 enable";
                }
              }
            }
            leaf description {
              type string {
                length "1..256" {
                  description
                    "Description of autoloopback interfaces";
                }
              }
              description
                "Description of loopbacks under VRF";
            }
          }
        }
      }
      container subscriber-redundancy {
        presence "Indicates a subscriber-redundancy node is configured.";
        description
          "Subscriber redundancy configuration";
        leaf damping-timer-val {
          type uint32 {
            range "60..600" {
              description
                "Timer value (in secs)";
            }
          }
          description
            "SRG damping timer interval";
        }
        leaf stats-request-rate {
          type uint32 {
            range "10..8000" {
              description
                "rate of stats request(Restricted to development)";
            }
          }
          description
            "rate of stats request on switchover(Restricted to development)";
        }
        leaf stats-request-rate-timeout {
          type uint32 {
            range "10..8000" {
              description
                "Timeout rate of stats request(Restricted to development)";
            }
          }
          description
            "rate of stats request on switchover(Restricted to development)";
        }
        leaf stats-request-svm-timeout {
          type uint32 {
            range "10..8000" {
              description
                "SVM timeout of stats request(Restricted to development)";
            }
          }
          description
            "rate of stats request on switchover(Restricted to development)";
        }
        container groups {
          description
            "SRG group configuration";
          list group {
            key "group-name";
            description
              "SRG group configuration";
            leaf group-name {
              type xr:Cisco-ios-xr-string {
                length "1..64" {
                  description
                    "SRG Group ID";
                }
              }
              description
                "SRG group configuration";
            }
            leaf virtual-mac {
              type yang:mac-address;
              description
                "Virtual MAC address for this SRG Group";
            }
            leaf core-tracking {
              type xr:Cisco-ios-xr-string {
                length "1..32" {
                  description
                    "Tracking Object Name";
                }
              }
              description
                "Core Tracking Object for this SRG Group";
            }
            leaf description {
              type string {
                length "1..256" {
                  description
                    "Description of srg group";
                }
              }
              description
                "Description of srg group";
            }
            leaf access-tracking {
              type xr:Cisco-ios-xr-string {
                length "1..32" {
                  description
                    "Tracking Object Name";
                }
              }
              description
                "Access Tracking Object for this SRG Group";
            }
            leaf damping-timer-val {
              type uint32 {
                range "60..600" {
                  description
                    "Damping timer value (in secs)";
                }
              }
              description
                "Damping timer value for this SRG Group";
            }
            container fast-switchover-disable {
              presence "Indicates a fast-switchover-disable node is configured.";
              description
                "Disable fast switchover for this SRG group";
            }
            container access-interface-list {
              presence "Indicates a access-interface-list node is configured.";
              description
                "Access interface list for this SRG Group";
              container interfaces {
                description
                  "Access interface";
                list interface {
                  key "interface-name";
                  description
                    "Access interface";
                  leaf interface-name {
                    type xr:Interface-name;
                    description
                      "Access interface";
                  }
                  leaf xr-interface-name {
                    type xr:Interface-name;
                    mandatory true;
                    description
                      "Access interface";
                  }
                }
              }
              container sub-intf-ranges {
                description
                  "Sub Interface Range";
                list sub-intf-range {
                  key "interface-name sub-intf-start-range sub-intf-end-range";
                  description
                    "Sub Interface Range";
                  leaf interface-name {
                    type xr:Interface-name;
                    description
                      "Access interface";
                  }
                  leaf sub-intf-start-range {
                    type uint32 {
                      range "0..2147483646" {
                        description
                          "Sub Interface Start Index";
                      }
                    }
                    description
                      "Sub Interface Range";
                  }
                  leaf sub-intf-end-range {
                    type uint32 {
                      range "0..2147483646" {
                        description
                          "Sub Interface End Index";
                      }
                    }
                    description
                      "Sub Interface End Index";
                  }
                  leaf xr-interface-name {
                    type xr:Interface-name;
                    mandatory true;
                    description
                      "Access interface";
                  }
                  leaf xr-sub-intf-start-range {
                    type uint32 {
                      range "0..2147483646" {
                        description
                          "Sub Interface Start Index";
                      }
                    }
                    mandatory true;
                    description
                      "Sub Interface Range";
                  }
                  leaf xr-sub-intf-end-range {
                    type uint32 {
                      range "0..2147483646" {
                        description
                          "Sub Interface End Index";
                      }
                    }
                    mandatory true;
                    description
                      "Sub Interface End Index";
                  }
                }
              }
            }
            leaf route-tag {
              type uint32 {
                range "1..4294967295" {
                  description
                    "Tag value to be applied for subnet routes";
                }
              }
              description
                "Route tag for subnets belonging to this group";
            }
            container access-control-route {
              description
                "Access control route for this group";
              container ipv6 {
                description
                  "IP Address";
                leaf ip_address {
                  type inet:ipv6-address-no-zone;
                  must "../prefix_len";
                  description
                    "IPv6 prefix";
                }
                leaf prefix_len {
                  type uint32 {
                    range "0..128" {
                      description
                        "Prefix length";
                    }
                  }
                  must "../ip_address";
                  description
                    "IPv6 prefix len";
                }
                leaf vrf {
                  type xr:Cisco-ios-xr-string {
                    length "1..32" {
                      description
                        "VRF Name";
                    }
                  }
                  must "../ip_address";
                  description
                    "Access control route vrf name";
                }
                leaf next-hop-vrf {
                  type xr:Cisco-ios-xr-string {
                    length "1..32" {
                      description
                        "VRF name";
                    }
                  }
                  must "../active-tag";
                  description
                    "Next-hop VRF";
                }
                leaf next-hop-address {
                  type inet:ipv6-address-no-zone;
                  must "../active-tag";
                  description
                    "Next-hop address";
                }
                leaf active-tag {
                  type uint32 {
                    range "1..4294967295" {
                      description
                        "Route tag value";
                    }
                  }
                  must "(../next-hop-vrf or ../next-hop-address) and ../standby-tag";
                  description
                    "Route Tag for Active SRG group";
                }
                leaf standby-tag {
                  type uint32 {
                    range "1..4294967295" {
                      description
                        "Route tag value";
                    }
                  }
                  must "../active-tag";
                  description
                    "Route Tag for Standby SRG group";
                }
              }
              container ipv4 {
                description
                  "IP Address";
                leaf ip_address {
                  type inet:ipv4-address-no-zone;
                  must "../prefix_len";
                  description
                    "IPv4 prefix";
                }
                leaf prefix_len {
                  type uint32 {
                    range "0..32" {
                      description
                        "Prefix length";
                    }
                  }
                  must "../ip_address";
                  description
                    "IPv4 prefix len";
                }
                leaf vrf {
                  type xr:Cisco-ios-xr-string {
                    length "1..32" {
                      description
                        "VRF Name";
                    }
                  }
                  must "../ip_address";
                  description
                    "Access control route vrf name";
                }
                leaf next-hop-vrf {
                  type xr:Cisco-ios-xr-string {
                    length "1..32" {
                      description
                        "VRF name";
                    }
                  }
                  must "../active-tag";
                  description
                    "Next-hop VRF";
                }
                leaf next-hop-address {
                  type inet:ipv4-address-no-zone;
                  must "../active-tag";
                  description
                    "Next-hop address";
                }
                leaf active-tag {
                  type uint32 {
                    range "1..4294967295" {
                      description
                        "Route tag value";
                    }
                  }
                  must "(../next-hop-vrf or ../next-hop-address) and ../standby-tag";
                  description
                    "Route Tag for Active SRG group";
                }
                leaf standby-tag {
                  type uint32 {
                    range "1..4294967295" {
                      description
                        "Route tag value";
                    }
                  }
                  must "../active-tag";
                  description
                    "Route Tag for Standby SRG group";
                }
              }
            }
            container state-control-next-hop-ip {
              description
                "State control next hop ip for this group";
              leaf ipv4 {
                type inet:ipv4-address-no-zone;
                description
                  "IPv4 address";
              }
              leaf ipv6 {
                type inet:ipv6-address-no-zone;
                description
                  "IPv6 address";
              }
            }
            leaf up-instance-id {
              type uint32 {
                range "1..15" {
                  description
                    "Instance ID value";
                }
              }
              description
                "Instance ID for this group";
            }
          }
        }
      }
      container up-instance-ids {
        description
          "CNBNG-nal UP Instance configuration";
        list up-instance-id {
          key "up-instance-id";
          description
            "CNBNG-nal UP Instance configuration";
          leaf up-instance-id {
            type uint32 {
              range "1..15" {
                description
                  "UP Instance ID";
              }
            }
            description
              "CNBNG-nal UP Instance configuration";
          }
          leaf description {
            type string {
              length "1..256" {
                description
                  "Description of up-instance-id";
              }
            }
            description
              "Description of up-instance-id";
          }
          leaf hostidentifier {
            type xr:Cisco-ios-xr-string {
              length "1..64" {
                description
                  "NAL Host-name";
              }
              pattern "[a-zA-Z][-_.a-z0-9A-Z]*";
            }
            description
              "NAL Host Identifier for selected UP instance";
          }
          container cp-association {
            description
              "CP association";
            leaf retry-count {
              type uint32 {
                range "5..20" {
                  description
                    "Retry count";
                }
              }
              description
                "Retry count";
            }
          }
          container cp-server {
            description
              "NAL control-plane server connection configs";
            container primary {
              description
                "NAL's control-plane primary-server configs";
              leaf ipv4 {
                type inet:ipv4-address-no-zone;
                must "not(../ipv6)";
                description
                  "IP address type of CP's primary-server";
              }
              leaf ipv6 {
                type inet:ipv6-address-no-zone;
                must "not(../ipv4)";
                description
                  "IP address type of CP's primary-server";
              }
            }
          }
          container up-server {
            description
              "NAL control-plane up-server connection configs";
            leaf ipv4 {
              type inet:ipv4-address-no-zone;
              must "not(../ipv6)";
              description
                "IP address type of UP's server";
            }
            leaf gtp-port {
              type uint32 {
                range "15002..15051" {
                  description
                    "UP-server source GTP port-number";
                }
              }
              must "(../ipv4 or ../ipv6 or ../interface)";
              description
                "user-plane's GTP port-number";
            }
            leaf pfcp-port {
              type uint32 {
                range "15002..15051" {
                  description
                    "UP-server source PFCP port-number";
                }
              }
              must "(../ipv4 or ../ipv6 or ../interface)";
              description
                "user-plane's PFCP port-number";
            }
            leaf vrf {
              type union {
                type string {
                  pattern "default" {
                    description
                      "default VRF";
                  }
                }
                type xr:Cisco-ios-xr-string {
                  length "1..32" {
                    description
                      "VRF Name";
                  }
                }
              }
              must "(../ipv4 or ../ipv6 or ../interface)";
              description
                "UP server's VRF Name";
            }
            leaf ipv6 {
              type inet:ipv6-address-no-zone;
              must "not(../ipv4)";
              description
                "IP address type of UP's server";
            }
            leaf interface {
              type xr:Interface-name {
                pattern "Loopback.*";
              }
              must "not(../ipv4 or ../ipv6)";
              description
                "Specify the source interface for the UP server connection";
            }
          }
          container up-cp-notification {
            description
              "up cp notification related config";
            leaf flow-control {
              type uint32 {
                range "20..400" {
                  description
                    "limit";
                }
              }
              description
                "up cp notification flow control";
            }
          }
          container up-cp-stats {
            description
              "up cp stats related config";
            leaf flow-control {
              type uint32 {
                range "20..500" {
                  description
                    "limit";
                }
              }
              description
                "up stats flow control";
            }
          }
        }
      }
    }
  }

  augment "/a1:interfaces/a1:interface" {
    description
      "This augment extends active nodes configuration";
    uses IF-BODY;
  }
  augment "/a1:interfaces/a1:interface-preconfigure" {
    description
      "This augment extends preconfigured nodes
       configuration";
    uses IF-BODY;
  }
  augment "/location:locations/location:location" {
    description
      "This augment extends active nodes configuration";
    uses LOCATION-BODY;
  }
  augment "/location:locations/location:preconfigured-location" {
    description
      "This augment extends preconfigured nodes
       configuration";
    uses LOCATION-BODY;
  }
}
