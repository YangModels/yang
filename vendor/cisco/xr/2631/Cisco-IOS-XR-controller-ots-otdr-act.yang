module Cisco-IOS-XR-controller-ots-otdr-act {
  namespace "http://cisco.com/ns/yang/Cisco-IOS-XR-controller-ots-otdr-act";
  prefix controller-ots-otdr-act;

  import Cisco-IOS-XR-types {
    prefix xr;
  }
  import cisco-semver {
    prefix semver;
  }

  organization
    "Cisco Systems, Inc.";
  contact
    "Cisco Systems, Inc.
     Customer Service
     Postal: 170 West Tasman Drive
     San Jose, CA 95134
     Tel: +1 800 553-NETS
     E-mail: cs-yang@cisco.com";
  description
    "This module contains a collection of YANG definitions
     for Cisco IOS-XR tone pattern for controller-ots module.
     Copyright (c) 2018-2026 by Cisco Systems, Inc., and/or its affiliates.
     All rights reserved.";

  revision 2026-07-15 {
    description
      "Updated OTDR capture-end values
       2026-02-06
         OTDR expert scan parameters support for ots controllers";
    semver:module-version "1.1.0";
  }
  revision 2025-07-01 {
    description
      "OTDR label support for ots controllers";
    semver:module-version "1.0.0";
  }
  revision 2024-08-22 {
    description
      "OTDR save baseline action support for ots controllers";
  }
  revision 2024-04-04 {
    description
      "OTDR action support for ots controllers in force mode";
  }
  revision 2022-12-22 {
    description
      "OTDR action support for ots controllers";
  }

  typedef Scan-type {
    type enumeration {
      enum "stop" {
        value 0;
        description
          "scan stop";
      }
      enum "start" {
        value 1;
        description
          "scan start";
      }
      enum "force-start" {
        value 2;
        description
          "scan force start";
      }
    }
    description
      "Scan type";
  }

  rpc ots-controller-otdr {
    description
      "ots controller OTDR generation";
    input {
      leaf controller {
        type xr:Interface-name;
        description
          "Controller name in R/S/I/P format";
      }
      leaf otdr-scan-rx {
        type Scan-type;
        description
          "OTDR SCAN at RX : Select otdr-scan-rx as start or stop";
      }
      leaf otdr-scan-tx {
        type Scan-type;
        description
          "OTDR SCAN at TX : select otdr-scan-tx as start or stop";
      }
      leaf label {
        type string {
          length "1..55";
        }
        description
          "OTDR Scan Label";
      }
      leaf capture-end {
        type uint32 {
          range "0..16000000";
        }
        units "cm";
        description
          "OTDR RX Capture End (Value in cm)";
      }
      leaf pulse-width {
        type uint32 {
          range "1..500000";
        }
        units "nanoseconds";
        description
          "OTDR RX Pulse Width (Value in nano seconds)";
      }
      leaf scan-duration {
        type uint32 {
          range "0..180";
        }
        units "seconds";
        description
          "OTDR RX Scan Duration (Value in seconds)";
      }
    }
  }
  rpc otdr-save-baseline-rx {
    description
      "ots controller OTDR save baseline";
    input {
      leaf controller {
        type xr:Interface-name;
        description
          "Controller name in R/S/I/P format";
      }
    }
  }
  rpc otdr-save-baseline-tx {
    description
      "ots controller OTDR save baseline";
    input {
      leaf controller {
        type xr:Interface-name;
        description
          "Controller name in R/S/I/P format";
      }
    }
  }
}
