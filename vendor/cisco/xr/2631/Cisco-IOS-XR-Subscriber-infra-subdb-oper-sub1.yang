submodule Cisco-IOS-XR-Subscriber-infra-subdb-oper-sub1 {
  belongs-to Cisco-IOS-XR-Subscriber-infra-subdb-oper {
    prefix Cisco-IOS-XR-Subscriber-infra-subdb-oper;
  }

  import ietf-yang-types {
    prefix yang;
  }
  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR Subscriber-infra-subdb package operational data.
     
     Copyright (c) 2013-2026 by Cisco Systems, Inc.
     All rights reserved.";

  revision 2026-02-03 {
    description
      "Increased service name length to 65 characters. Impacted path /oper/subdb/node/0/show/assoc";
    semver:module-version "2.3.0";
  }
  revision 2024-02-21 {
    description
      "Added new bag element for shmwin external pool allocation
       2023-06-06
          Added new bag for SIR flapped process information
       2021-11-29
          Added new statistics to SIR flap history.
       2021-09-17
          Adding new bag for retrieving subdb sirflap history .";
    semver:module-version "2.2.0";
  }
  revision 2021-02-22 {
    description
      "Adding yang support to retrive server connection time-stats.";
    semver:module-version "2.1.0";
  }
  revision 2020-04-02 {
    description
      "Added new bag for Subscriber database transition states and cfg object types.";
    semver:module-version "2.0.0";
  }
  revision 2019-04-05 {
    description
      "Establish semantic version baseline.";
    semver:module-version "1.0.1";
  }
  revision 2018-09-28 {
    description
      "Fixed Subscriber database Association.";
  }
  revision 2015-11-09 {
    description
      "IOS XR 6.0 revision.";
  }

  typedef Session-state {
    type enumeration {
      enum "init" {
        value 1;
        description
          "Initialisation";
      }
      enum "destroy" {
        value 2;
        description
          "Destroy";
      }
      enum "config-generate" {
        value 3;
        description
          "Config generate";
      }
      enum "feature-registration-wait" {
        value 4;
        description
          "Feature registration wait";
      }
      enum "config-apply" {
        value 5;
        description
          "Config apply";
      }
      enum "config-done" {
        value 6;
        description
          "Config done";
      }
      enum "config-removed" {
        value 7;
        description
          "Config removed";
      }
      enum "config-error" {
        value 8;
        description
          "Config error";
      }
      enum "error" {
        value 9;
        description
          "Error";
      }
      enum "sync" {
        value 11;
        description
          "Sync";
      }
    }
    description
      "Session states";
  }

  typedef Subdb-object-type-data {
    type enumeration {
      enum "user-profile" {
        value 1;
        description
          "User profile";
      }
      enum "service-profile" {
        value 2;
        description
          "Service profile";
      }
      enum "subscriber-service" {
        value 3;
        description
          "Subscriber service template";
      }
      enum "ppp" {
        value 4;
        description
          "PPP template";
      }
      enum "ip-subscriber" {
        value 5;
        description
          "IP subscriber template";
      }
    }
    description
      "Template types";
  }

  grouping SUBDB-SUBSCRIBER-OBJ {
    description
      "Subscriber database server information for a
       session";
    leaf session-state {
      type Session-state;
      description
        "Subscriber session state";
    }
    leaf activate-request-id {
      type uint32;
      description
        "Activate request identifier";
    }
    leaf transaction-id {
      type int32;
      description
        "Transaction identifier associated with a
         particular 'produce_done' or 'produce_all_done'
         request  default value is 0xffffffff which
         represents 'None'";
    }
    leaf produce-done-request-id {
      type uint32;
      description
        "Produce done request ID";
    }
    leaf destroy-req-received {
      type boolean;
      description
        "Flags indicating if a destroy request is
         received";
    }
    leaf destroy-request-id {
      type uint32;
      description
        "Destroy request ID";
    }
    leaf is-config-changed {
      type boolean;
      description
        "Is true if configuration change due to template
         change only and not due to a produce done
         request";
    }
    leaf is-creator-gone {
      type boolean;
      description
        "Is true if the creator of the connection is
         destroyed";
    }
    leaf is-delete-notify-done {
      type boolean;
      description
        "Is true if the deleted features have all been
         notified and all 'apply done' ack messages have
         been received";
    }
    leaf add-modify-done {
      type boolean;
      description
        "Is true if added/modified features have all been
         notified and all 'apply done' ack messages have
         been received";
    }
    leaf is-rollback-needed {
      type boolean;
      description
        "Is true if the subscriber should be rolled back
         to the configuration prior to this transaction
         when all the outstanding  backend programming
         interface requests are replied";
    }
    leaf is-rollback-in-progress {
      type boolean;
      description
        "Is true if subscriber's configuration is being
         rolled back";
    }
    leaf is-server-restart-apply {
      type boolean;
      description
        "Is true if the subscriber's configuration is
         being applied due to subscriber database server
         restart";
    }
    leaf is-rollback-performed {
      type boolean;
      description
        "Is true if rollback has previously been
         performed for this subscriber";
    }
    leaf repl-pending {
      type boolean;
      description
        "Flags indicating if there is pending replication";
    }
    leaf activate-timer-running {
      type boolean;
      description
        "Flags indicating if activate timer is running";
    }
    leaf apply-timer-running {
      type boolean;
      description
        "Flags indicating if apply timer is running";
    }
    leaf event-queue-size {
      type boolean;
      description
        "the current size of the event queue";
    }
    leaf restarts {
      type yang:hex-string;
      description
        "Restart vector to keep track of the restart
         state";
    }
    leaf template-interface-id {
      type uint32;
      description
        "Template Interface Identifier";
    }
  }

  grouping SUBDB-ASSOC-SESS {
    description
      "Subscriber database associated session";
    leaf template-type {
      type Subdb-object-type-data;
      description
        "Template type";
    }
    leaf template-name {
      type string {
        length "0..66";
      }
      description
        "Template name";
    }
    leaf varlist {
      type string {
        length "0..1000";
      }
      description
        "Varlist";
    }
  }

  grouping SUBDB-TEMPLATES {
    description
      "Subscriber database templates";
    list associated-template {
      description
        "Associated templates";
      uses SUBDB-ASSOC-SESS;
    }
  }

  grouping SUBDB-ASSOC-SESSION {
    description
      "Subscriber database associated session";
    container template {
      description
        "Subdb template";
      uses SUBDB-TEMPLATES;
    }
    leaf session-id {
      type uint32;
      description
        "Session ID";
    }
    leaf interface-name {
      type xr:Interface-name;
      description
        "Interface name";
    }
    leaf associations {
      type uint32;
      description
        "Association count which reflects number of
         entries in AssociatedTemplates";
    }
    leaf varlist-id {
      type uint32;
      description
        "Varlist Id";
    }
  }
}
