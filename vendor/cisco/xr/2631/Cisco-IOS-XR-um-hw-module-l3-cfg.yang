module Cisco-IOS-XR-um-hw-module-l3-cfg {
  namespace "http://cisco.com/ns/yang/Cisco-IOS-XR-um-hw-module-l3-cfg";
  prefix um-hw-module-l3-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR hw-module-l3 package configuration.
     
     This YANG module augments the
     modules with configuration data.
     
     Copyright (c) 2024-2025 by Cisco Systems, Inc., and/or its affiliates.
     All rights reserved.";

  revision 2025-03-21 {
    description
      "Added leaf for gre-lite-cfg";
    semver:module-version "1.1.0";
  }
  revision 2020-05-08 {
    description
      "Initial release";
    semver:module-version "1.0.0";
  }

  container hw-module {
    description
      "Configure h/w module";
    container l3 {
      description
        "Configure l3 ";
      container feature {
        description
          "Configure l3 features";
        leaf async-error-notify {
          type enumeration {
            enum "enable" {
              value 16;
              description
                "Enable async error notify feature";
            }
          }
          description
            "Configure async error notify feature";
        }
        leaf caching {
          type enumeration {
            enum "disable" {
              value 7;
              description
                "Disable fast convergence caching feature.";
            }
          }
          description
            "Configure fast convergence caching feature";
        }
        leaf ler {
          type enumeration {
            enum "disable" {
              value 3;
              description
                "Disable LER feature";
            }
          }
          description
            "Configure LER feature";
        }
        leaf lsr {
          type enumeration {
            enum "disable" {
              value 5;
              description
                "Disable LSR feature";
            }
          }
          description
            "Configure LSR feature";
        }
        leaf mpls-over-udp-decap {
          type enumeration {
            enum "enable" {
              value 1;
              description
                "Enable MPLS-over-UDP decap feature";
            }
          }
          description
            "Configure MPLS-over-UDP decap feature";
        }
        container pbr {
          description
            "Configure PBR feature";
          leaf sixpe {
            type enumeration {
              enum "enable" {
                value 1;
                description
                  "Enable BGP FS 6PE feature";
              }
            }
            description
              "Configure BGP FS 6pe";
          }
          leaf hash {
            type enumeration {
              enum "enable" {
                value 1;
                description
                  "Enable PBR hash feature";
              }
            }
            description
              "Configure PBR hash";
          }
          leaf stats {
            type enumeration {
              enum "disable" {
                value 1;
                description
                  "Disable PBR statistics";
              }
            }
            description
              "Configure PBR statistics";
          }
        }
        container per-prefix-egress-stats {
          presence "Indicates a per-prefix-egress-stats node is configured.";
          description
            "Configure per-prefix-egress stats feature";
          container enable {
            presence "Indicates a enable node is configured.";
            description
              "Enable per-prefix-egress-stats accounting for unicast labels";
          }
        }
        container per-prefix-async-egress-stats {
          presence "Indicates a per-prefix-async-egress-stats node is configured.";
          description
            "Configure per-async-prefix-egress stats feature";
          container enable {
            presence "Indicates a enable node is configured.";
            description
              "Enable per-prefix-egress-stats accounting for unicast labels";
          }
        }
        container gre-lite {
          presence "Indicates gre-lite mode is configured.";
          description
            "Configure GRE Lite mode";
          container enable {
            presence "Indicates a enable node is configured.";
            description
              "Enable GRE Lite mode";
          }
        }
        leaf sharedlspa {
          type enumeration {
            enum "enable" {
              value 10;
              description
                "Enable sharedlspa sharing";
            }
          }
          description
            "Configure shared_lspa feature";
        }
      }
    }
  }
}
