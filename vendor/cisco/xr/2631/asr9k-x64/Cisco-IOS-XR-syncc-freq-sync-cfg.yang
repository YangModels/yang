module Cisco-IOS-XR-syncc-freq-sync-cfg {
  namespace "http://cisco.com/ns/yang/Cisco-IOS-XR-syncc-freq-sync-cfg";
  prefix syncc-freq-sync-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR syncc-freq-sync package configuration.
     
     Copyright (c) 2013-2026 by Cisco Systems, Inc.
     All rights reserved.";

  revision 2026-06-22 {
    description
      "Schema added for Syncc freq sync configuration.";
    semver:module-version "1.0.0";
  }
  revision 2024-05-29 {
    description
      "Schema added for Syncc freq sync configuration.";
    semver:module-version "1.0.0";
  }
  revision 2019-04-05 {
    description
      "Establish semantic version baseline.";
  }
  revision 2015-11-09 {
    description
      "IOS XR 6.0 revision.";
  }
}
