module Cisco-IOS-XR-um-dot1x-cfg {
  namespace "http://cisco.com/ns/yang/Cisco-IOS-XR-um-dot1x-cfg";
  prefix um-dot1x-cfg;

  import Cisco-IOS-XR-types {
    prefix xr;
  }
  import ietf-yang-types {
    prefix yang;
  }
  import Cisco-IOS-XR-um-interface-cfg {
    prefix a1;
  }
  import Cisco-IOS-XR-um-aaa-cfg {
    prefix a2;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR dot1x package configuration.
     
     This YANG module augments the
     modules with configuration data.
     
     Copyright (c) 2022-2026 by Cisco Systems, Inc., and/or its affiliates.
     All rights reserved.";

  revision 2026-03-31 {
    description
      "Added key-exchange-groups leaf under eap method tls
       2026-03-30
         Added the inner-method container under ttls and updated
       AAA dot1x authentication server-group modeling.";
    semver:module-version "3.0.0";
  }
  revision 2025-08-15 {
    description
      "Added enable-tls13-legacy-kdf config under method tls
       2022-09-15
          Removed unwanted nodes under eapol destination-address
       2022-07-11
          Added missing description statement to nodes
       2022-06-01
          Adjusted controller augmentation hierarchy
       2022-03-22
          Added Retry time for MAC Authentication Bypass feature
       2021-11-22
          Added container mab under dot1x";
    semver:module-version "2.0.0";
  }
  revision 2021-03-19 {
    description
      "Initial release";
    semver:module-version "1.0.0";
  }

  grouping IF-BODY {
    description
      "Grouping for interface";
    container dot1x {
      description
        "Interface Config Commands for IEEE 802.1X";
      leaf profile {
        type xr:Cisco-ios-xr-string {
          length "1..800" {
            description
              "String";
          }
        }
        description
          "Credentials profile configuration";
      }
    }
    container eapol {
      description
        "EAPOL configuration commands";
      container destination-address {
        description
          "Destination address for EAPoL frames transmission";
        leaf mac-address {
          type yang:mac-address;
          description
            "configure this node";
        }
      }
      leaf eth-type {
        type enumeration {
          enum "876F" {
            value 34671;
            description
              "Value of Ethertype";
          }
        }
        description
          "EAPOL ethertype configuration";
      }
    }
  }

  grouping CONT-BODY {
    description
      "Grouping for controller";
    container dot1x {
      description
        "Interface Config Commands for IEEE 802.1X";
      leaf profile {
        type xr:Cisco-ios-xr-string {
          length "1..800" {
            description
              "String";
          }
        }
        description
          "Credentials profile configuration";
      }
    }
  }

  augment "/a1:interfaces/a1:interface" {
    description
      "This augment extends active nodes configuration";
    uses IF-BODY;
  }
  augment "/a1:interfaces/a1:interface-preconfigure" {
    description
      "This augment extends preconfigured nodes
       configuration";
    uses IF-BODY;
  }
  augment "/a1:controllers/a1:controller" {
    description
      "This augment extends active nodes configuration";
    uses CONT-BODY;
  }
  augment "/a1:controllers/a1:controller-preconfigure" {
    description
      "This augment extends preconfigured nodes
       configuration";
    uses CONT-BODY;
  }
  augment "/a2:aaa/a2:authentication" {
    description
      "This augment extends aaa authentication nodes
       configuration";
    container dot1x {
      description
        "Set authentication lists for Dot1x";
      list authentication-list {
        key "list-name";
        description
          "List name for AAA authentication";
        leaf list-name {
          type union {
            type string {
              pattern "default" {
                description
                  "Default list name for AAA authentication";
              }
            }
            type xr:Cisco-ios-xr-string {
              length "1..253" {
                description
                  "List name for AAA authentication";
              }
            }
          }
          description
            "List name for AAA authentication";
        }
        container groups {
          description
            "Use Server-group";
          container group-1 {
            description
              "First server-group";
            container radius {
              must "not(../server-group-name)";
              presence "Indicates a radius node is configured.";
              description
                "Use list of all RADIUS hosts";
            }
            leaf server-group-name {
              type xr:Cisco-ios-xr-string {
                length "1..253" {
                  description
                    "server-group name";
                }
              }
              must "not(../radius)";
              description
                "server-group name";
            }
          }
          container group-2 {
            description
              "Second server-group";
            container radius {
              must
                "not(../server-group-name) and
                 ../../group-1/server-group-name";
              presence "Indicates a radius node is configured.";
              description
                "Use list of all RADIUS hosts";
            }
            leaf server-group-name {
              type xr:Cisco-ios-xr-string {
                length "1..253" {
                  description
                    "server-group name";
                }
              }
              must
                "not(../radius) and
                 (../../group-1/radius or
                 ../../group-1/server-group-name)";
              description
                "server-group name";
            }
          }
          container group-3 {
            description
              "Third server-group";
            container radius {
              must
                "not(../server-group-name) and
                 ../../group-2/server-group-name and
                 not(../../group-1/radius)";
              presence "Indicates a radius node is configured.";
              description
                "Use list of all RADIUS hosts";
            }
            leaf server-group-name {
              type xr:Cisco-ios-xr-string {
                length "1..253" {
                  description
                    "server-group name";
                }
              }
              must
                "not(../radius) and
                 (../../group-2/radius or
                 ../../group-2/server-group-name)";
              description
                "server-group name";
            }
          }
          container group-4 {
            description
              "Fourth server-group";
            container radius {
              must
                "not(../server-group-name) and
                 ../../group-3/server-group-name and
                 not(../../group-1/radius or ../../group-2/radius)";
              presence "Indicates a radius node is configured.";
              description
                "Use list of all RADIUS hosts";
            }
            leaf server-group-name {
              type xr:Cisco-ios-xr-string {
                length "1..253" {
                  description
                    "server-group name";
                }
              }
              must
                "not(../radius) and
                 (../../group-3/radius or
                 ../../group-3/server-group-name)";
              description
                "server-group name";
            }
          }
        }
      }
    }
  }
  container dot1x {
    description
      "IEEE 802.1X Global Configuration Commands";
    container profiles {
      description
        "Configure 802.1X profiles";
      list profile {
        key "profile-name";
        description
          "Configure 802.1X profiles";
        leaf profile-name {
          type xr:Cisco-ios-xr-string {
            length "1..63" {
              description
                "Specify a profile name (max 63 charecters)";
            }
          }
          description
            "Configure 802.1X profiles";
        }
        container pae {
          description
            "Set 802.1x pae type";
          container authenticator {
            must "not(../supplicant or ../both)";
            presence "Indicates a authenticator node is configured.";
            description
              "Set PAE Type as Authenticator";
          }
          container supplicant {
            must "not(../authenticator or ../both)";
            presence "Indicates a supplicant node is configured.";
            description
              "Set PAE Type as Supplicant";
          }
          container both {
            must "not(../authenticator or ../supplicant)";
            presence "Indicates a both node is configured.";
            description
              "Set PAE Type as both Supplicant and Authenticator";
          }
        }
        container mab {
          presence "Indicates a mab node is configured.";
          description
            "Enable MAC Authentication Bypass";
        }
        container supplicant {
          description
            "Enter in Supplicant submode";
          container eap {
            description
              "Configure EAP Supplicant Parameters";
            leaf profile {
              type xr:Cisco-ios-xr-string {
                length "1..63" {
                  description
                    "EAP Profile Name";
                }
              }
              description
                "EAP Profile Configuration";
            }
          }
        }
        container authenticator {
          description
            "Enter in Authenticator submode";
          container eap {
            description
              "enable local EAP server";
            leaf profile {
              type xr:Cisco-ios-xr-string {
                length "1..63" {
                  description
                    "EAP Profile Name";
                }
              }
              description
                "EAP Profile Configuration";
            }
          }
          container timer {
            description
              "Set various timeouts";
            container reauth-time {
              description
                "In seconds, after which an automatic reauth should be initiated";
              container server {
                presence "Indicates a server node is configured.";
                description
                  "server given re-auth timer value, min expected value is 60 sec, default: 1hr";
              }
              leaf timer-value {
                type uint32 {
                  range "60..5184000" {
                    description
                      "In seconds, admin configured reauth timer value, min:60, max:5184000 (2 months)";
                  }
                }
                description
                  "In seconds, admin configured reauth timer value, min:60, max:5184000 (2 months)";
              }
            }
            leaf mab-retry-time {
              type uint32 {
                range "60..300" {
                  description
                    "In seconds, min:60(default), max:300 (5 minutes)";
                }
              }
              description
                "In seconds, interval after which an auth attempt will be initiated for auth failed or server unreachable MAB clients";
            }
          }
          container server {
            description
              "Remote AAA server event";
            container dead {
              description
                "AAA server unreachable";
              container action {
                description
                  "dot1x authenticator action";
                container auth-fail {
                  must "not(../auth-retry)";
                  presence "Indicates a auth-fail node is configured.";
                  description
                    "declare authentication failure on server unreachability";
                }
                container auth-retry {
                  must "not(../auth-fail)";
                  presence "Indicates a auth-retry node is configured.";
                  description
                    "no auth fail declared, retry authentication with supplicant, until server is reachable.";
                }
              }
            }
          }
          container host-mode {
            description
              "set the host mode for authentication";
            container multi-auth {
              must "not(../multi-host or ../single-host)";
              presence "Indicates a multi-auth node is configured.";
              description
                "multiple authentication mode";
            }
            container multi-host {
              must "not(../multi-auth or ../single-host)";
              presence "Indicates a multi-host node is configured.";
              description
                "multiple host mode";
            }
            container single-host {
              must "not(../multi-auth or ../multi-host)";
              presence "Indicates a single-host node is configured.";
              description
                "single host mode";
            }
          }
        }
      }
    }
  }
  container eap {
    description
      "EAP Global Configuration Commands";
    container profiles {
      description
        "Configure EAP profiles";
      list profile {
        key "profile-name";
        description
          "Configure EAP profiles";
        leaf profile-name {
          type xr:Cisco-ios-xr-string {
            length "1..63" {
              description
                "Specify a profile name (max 63 characters)";
            }
          }
          description
            "Configure EAP profiles";
        }
        leaf identity {
          type xr:Cisco-ios-xr-string {
            length "1..63" {
              description
                "Specify EAP Identity or Username for authentication";
            }
          }
          description
            "identity name";
        }
        container method {
          description
            "Add an allowed method";
          container tls {
            description
              "EAP-TLS method allowed";
            leaf pki-trustpoint {
              type xr:Cisco-ios-xr-string {
                length "1..63" {
                  description
                    "Specify the pki trustpoint name";
                }
              }
              description
                "Set pki trustpoint";
            }
            container enable-tls13-legacy-kdf {
              presence "Indicates a enable-tls13-legacy-kdf node is configured.";
              description
                "Enable legacy key derivation for MACsec EAP with TLS 1.3";
            }
            leaf key-exchange-groups {
              type xr:Cisco-ios-xr-string {
                length "1..1024" {
                  description
                    "Colon-separated list of TLS key exchange groups";
                }
              }
              description
                "Configure TLS key exchange groups (colon-separated list, e.g.
                 x448_mlkem768:X25519MLKEM768:x25519_mlkem512:mlkem512:p256_mlkem512:
                 mlkem768:p384_mlkem768:SecP256r1MLKEM768:mlkem1024:p521_mlkem1024:
                 SecP384r1MLKEM1024:x25519:secp256r1:x448:secp521r1:secp384r1:
                 ffdhe2048:ffdhe3072:ffdhe4096)";
            }
          }
          container ttls {
            description
              "EAP-TTLS method allowed";
            leaf pki-trustpoint {
              type xr:Cisco-ios-xr-string {
                length "1..63" {
                  description
                    "Specify the pki trustpoint name";
                }
              }
              description
                "Set pki trustpoint";
            }
            container inner-method {
              description
                "Add an allowed inner method";
              container attestation {
                description
                  "EAP-ATTESTATION method";
                container verifier {
                  description
                    "Set Verifier related attributes";
                  leaf rsakeylabel {
                    type xr:Cisco-ios-xr-string {
                      length "1..63" {
                        description
                          "Specify the rsakeylabel name of the verifier public key";
                      }
                    }
                    description
                      "Set RSA Key label name under which verifier's public key is imported";
                  }
                }
                container secure-topology {
                  presence "Indicates a secure-topology node is configured.";
                  description
                    "enables the secure topology use case";
                }
              }
            }
          }
        }
        container allow-eap-tls-v1-0 {
          presence "Indicates a allow-eap-tls-v1-0 node is configured.";
          description
            "Allow EAP TLS v1.0";
        }
      }
    }
  }
}
