module Cisco-IOS-XR-tty-management-cmd-oper {
  namespace "http://cisco.com/ns/yang/Cisco-IOS-XR-tty-management-cmd-oper";
  prefix tty-management-cmd-oper;

  import cisco-semver {
    prefix semver;
  }
  include Cisco-IOS-XR-tty-management-cmd-oper-sub1 {
    revision-date 2019-04-05;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR tty-management-cmd package operational data.
     
     This module contains definitions
     for the following management objects:
       show-users: Show users statistics
     
     Copyright (c) 2013-2019 by Cisco Systems, Inc.
     All rights reserved.";

  revision 2019-04-05 {
    description
      "Establish semantic version baseline.";
    semver:module-version "1.0.1";
  }
  revision 2019-02-25 {
    description
      "Fixed unconstrained data type issues";
  }
  revision 2017-09-07 {
    description
      "Fixed type translation error.";
  }
  revision 2015-11-09 {
    description
      "IOS XR 6.0 revision.";
  }

  container show-users {
    config false;
    description
      "Show users statistics";
    container sessions {
      description
        "Show users statistics";
      list session {
        key "session-id";
        description
          "Show users statistics";
        leaf session-id {
          type uint32 {
            range "0..4294967295";
          }
          description
            "Session Id";
        }
        uses SHOWUSERS-ENTRY;
      }
    }
  }
}
