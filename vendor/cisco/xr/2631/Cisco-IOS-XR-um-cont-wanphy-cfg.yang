module Cisco-IOS-XR-um-cont-wanphy-cfg {
  namespace "http://cisco.com/ns/yang/Cisco-IOS-XR-um-cont-wanphy-cfg";
  prefix um-cont-wanphy-cfg;

  import Cisco-IOS-XR-um-interface-cfg {
    prefix a1;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR cont-wanphy package configuration.
     
     This YANG module augments the
     modules with configuration data.
     
     Copyright (c) 2021-2025 by Cisco Systems, Inc., and/or its affiliates.
     All rights reserved.";

  revision 2022-07-11 {
    description
      "Added missing description statement to nodes";
    semver:module-version "1.1.0";
  }
  revision 2021-03-03 {
    description
      "Initial release";
    semver:module-version "1.0.0";
  }

  feature wanphy_cont {
    description
      "wanphy controller";
  }

  grouping CONT-BODY {
    description
      "Grouping for controller";
    container lanmode {
      description
        "Configure Lan Mode On/Off";
      container on {
        presence "Indicates a on node is configured.";
        description
          "Turn LanMode On";
      }
    }
    container wanmode {
      description
        "Configure Wan Mode On/Off";
      container on {
        presence "Indicates a on node is configured.";
        description
          "Turn WanMode On";
      }
    }
    container threshold {
      description
        "Configure WANPHY SF/SD BER threshold values";
      leaf sd-ber {
        type uint32 {
          range "3..9" {
            description
              "Bit error rate (10 to the minus n) (default 6)";
          }
        }
        description
          "Set Signal Degrade BER threshold";
      }
      leaf sf-ber {
        type uint32 {
          range "3..9" {
            description
              "Bit error rate (10 to the minus n) (default 3)";
          }
        }
        description
          "Set Signal Fail BER threshold";
      }
    }
    container mask-alarm {
      description
        "Disable WIS alarm being propagated to PCS";
      container plop {
        presence "Indicates a plop node is configured.";
        description
          "Mask PLOP";
      }
    }
    container report {
      description
        "Configure WANPHY SF/SD-BER alarm reporting";
      container sd-ber {
        presence "Indicates a sd-ber node is configured.";
        description
          "Set LBIP BER in excess of SD threshold reporting status";
      }
      container sf-ber {
        presence "Indicates a sf-ber node is configured.";
        description
          "Set LBIP BER in excess of SF threshold reporting status";
      }
      container los {
        description
          "Set Loss of Signal reporting status";
        container disable {
          presence "Indicates a disable node is configured.";
          description
            "Disable Reporting";
        }
      }
      container lof {
        description
          "Set Loss of Frame reporting status";
        container disable {
          presence "Indicates a disable node is configured.";
          description
            "Disable Reporting";
        }
      }
      container line-ais {
        presence "Indicates a line-ais node is configured.";
        description
          "Set Line Alarm Indication Signal reporting status";
      }
      container rdi {
        presence "Indicates a rdi node is configured.";
        description
          "Set Remote Defect Indicator reporting status";
      }
      container lop {
        description
          "Set Loss Of Pointer reporting status";
        container disable {
          presence "Indicates a disable node is configured.";
          description
            "Disable Reporting";
        }
      }
      container path-ais {
        presence "Indicates a path-ais node is configured.";
        description
          "Set Path Alarm Indication Signal reporting status";
      }
      container path-lcd {
        presence "Indicates a path-lcd node is configured.";
        description
          "Set Loss Of Code-Group Delineation reporting status";
      }
      container path-plm {
        presence "Indicates a path-plm node is configured.";
        description
          "Set Path Payload Label Mismatch reporting status";
      }
      container path-fe-plm {
        presence "Indicates a path-fe-plm node is configured.";
        description
          "Set Path Far End Label Mismatch reporting status";
      }
      container path-rdi {
        presence "Indicates a path-rdi node is configured.";
        description
          "Set Path Remote Defect Indication Signal reporting status";
      }
      container path-fe-ais {
        presence "Indicates a path-fe-ais node is configured.";
        description
          "Set Path Far End Alarm Indication Signal reporting status";
      }
    }
  }

  augment "/a1:controllers/a1:controller" {
    description
      "This augment extends active nodes configuration";
    uses CONT-BODY;
  }
  augment "/a1:controllers/a1:controller-preconfigure" {
    description
      "This augment extends preconfigured nodes
       configuration";
    uses CONT-BODY;
  }
  container wanphy {
    description
      "Configure Wanphy";
    container poll-timer {
      description
        "Make it 100 milliseconds";
      container timer-100ms {
        presence "Indicates a timer-100ms node is configured.";
        description
          "Configure 100 milliseconds";
      }
    }
  }
}
