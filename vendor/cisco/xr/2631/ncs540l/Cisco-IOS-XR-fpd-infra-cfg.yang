module Cisco-IOS-XR-fpd-infra-cfg {
  namespace "http://cisco.com/ns/yang/Cisco-IOS-XR-fpd-infra-cfg";
  prefix fpd-infra-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR fpd-infra package configuration.
     
     This model is deprecated and is replaced by
     Cisco-IOS-XR-um-fpd-cfg.yang which will provide the
     compatible functionalities.
     
     This module contains definitions
     for the following management objects:
       fpd: FPD Configuration
     
     Copyright (c) 2013-2022 by Cisco Systems, Inc.
     All rights reserved.";

  revision 2022-01-05 {
    description
      "Deprecated the native model, replaced by UM model in Exr.";
    semver:module-version "1.2.0";
  }
  revision 2020-07-06 {
    description
      "Added auto-upgrade config in display";
    semver:module-version "1.0.0";
  }
  revision 2020-05-21 {
    description
      "Separating eXR and LNT versions for module";
    semver:module-version "1.0.0";
  }
  revision 2019-04-05 {
    description
      "Establish semantic version baseline.";
    semver:module-version "1.0.0";
  }
  revision 2015-11-09 {
    description
      "IOS XR 6.0 revision.";
  }

  typedef Auto-reload {
    type enumeration {
      enum "disable" {
        value 0;
        description
          "fpd auto-reload disable";
      }
      enum "enable" {
        value 1;
        description
          "fpd auto-reload enable";
      }
    }
    description
      "Auto reload";
  }

  typedef Exclude {
    type enumeration {
      enum "pm" {
        value 1;
        description
          "fpd auto-upgrade exclude power module";
      }
    }
    description
      "Exclude";
  }

  typedef Auto-upgrade {
    type enumeration {
      enum "disable" {
        value 0;
        description
          "fpd auto-upgrade disable";
      }
      enum "enable" {
        value 1;
        description
          "fpd auto-upgrade enable";
      }
    }
    description
      "Auto upgrade";
  }

  container fpd {
    status deprecated;
    description
      "This model is deprecated and is replaced by
       Cisco-IOS-XR-um-fpd-cfg.yang which will provide
       the compatible functionalities.  FPD
       Configuration";
    leaf auto-reload {
      type Auto-reload;
      description
        "Enable or disable fpd auto-reload";
    }
    leaf exclude {
      type Exclude;
      description
        "Exclude entity for fpd auto-upgrade";
    }
    leaf auto-upgrade {
      type Auto-upgrade;
      description
        "Enable or disable fpd auto-upgrade";
    }
  }
}
