module Cisco-IOS-XR-controller-ots-psm-switchover-act {
  namespace "http://cisco.com/ns/yang/Cisco-IOS-XR-controller-ots-psm-switchover-act";
  prefix controller-ots-psm-switchover-act;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR PSM switchover for controller-ots module.
     
     Copyright (c) 2018-2026 by Cisco Systems, Inc.
     All rights reserved.";

  revision 2026-03-26 {
    description
      "Added explicit working/protected target for PSM switchover action";
    semver:module-version "1.0.0";
  }
  revision 2026-01-20 {
    description
      "PSM switchover action support for OTS controllers";
  }

  typedef psm-switchover-target {
    type enumeration {
      enum "manual-switch-to-working" {
        value 1;
        description
          "Manual switch to working path";
      }
      enum "manual-switch-to-protected" {
        value 2;
        description
          "Manual switch to protected path";
      }
    }
    description
      "PSM manual switchover target";
  }

  rpc ots-controller-psm-switchover {
    description
      "PSM controller switchover";
    input {
      leaf controller-name {
        type xr:Interface-name;
        mandatory true;
        description
          "OTS controller name in OtsR/S/I/P format";
      }
      leaf switchover-target {
        type psm-switchover-target;
        mandatory true;
        description
          "Requested switchover target path";
      }
    }
  }
}
