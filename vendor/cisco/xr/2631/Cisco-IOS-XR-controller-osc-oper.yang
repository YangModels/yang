module Cisco-IOS-XR-controller-osc-oper {
  namespace "http://cisco.com/ns/yang/Cisco-IOS-XR-controller-osc-oper";
  prefix controller-osc-oper;

  import Cisco-IOS-XR-types {
    prefix xr;
  }
  import cisco-semver {
    prefix semver;
  }
  include Cisco-IOS-XR-controller-osc-oper-sub1 {
    revision-date 2025-09-25;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR controller-osc package operational data.
     
     This module contains definitions
     for the following management objects:
       osc-oper: Osc operational data
     
     Copyright (c) 2013-2025 by Cisco Systems, Inc.
     All rights reserved.";

  revision 2025-09-25 {
    description
      "Change ampli gain fields from uint32 to int32";
    semver:module-version "1.0.0";
  }
  revision 2024-05-17 {
    description
      "Added LED state and Tx Power support for OSC Controllers";
  }
  revision 2023-07-17 {
    description
      "Added OSNR support for OSC controllers";
  }
  revision 2020-10-16 {
    description
      "New Oper Model Added for Osc Controller";
  }
  revision 2019-04-05 {
    description
      "Establish semantic version baseline.";
  }
  revision 2015-11-09 {
    description
      "IOS XR 6.0 revision.";
  }

  container osc-oper {
    config false;
    description
      "Osc operational data";
    container osc-ports {
      description
        "All Osc Port operational data";
      list osc-port {
        key "name";
        description
          "Osc operational data";
        container osc-info {
          description
            "Osc operational data";
          uses OSC-EDM-INFO;
        }
        leaf name {
          type xr:Interface-name;
          description
            "Port name";
        }
      }
    }
  }
}
