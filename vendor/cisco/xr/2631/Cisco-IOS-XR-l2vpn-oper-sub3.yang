submodule Cisco-IOS-XR-l2vpn-oper-sub3 {
  belongs-to Cisco-IOS-XR-l2vpn-oper {
    prefix Cisco-IOS-XR-l2vpn-oper;
  }

  import ietf-yang-types {
    prefix yang;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR l2vpn package operational data.
     
     Copyright (c) 2013-2026 by Cisco Systems, Inc.
     All rights reserved.";

  revision 2026-07-02 {
    description
      "- Removed xconnect-summary vpls-pw-max-exceeded-drop-cnt and bundle-ac-max-exceeded-drop-cnt
       2026-03-05
         - Add protect-dynamic-mac to bridge-domain security parameters
       2026-02-17
         - Removed PBB-related types and nodes.
       2025-12-22
         - Update L2FIB adjacency information
       2025-11-25
         - Add per-node l2fib-timers";
    semver:module-version "7.0.0";
  }
  revision 2025-08-26 {
    description
      "- Added l2fib-mac-learning-mac.attributes.is-sticky
       2025-06-07
          - Add tunnel-endpoint-id to EVPN Remote SHGs
       2025-06-07
          - Add encap key to l2fib-evpn-etree-remote
       2025-04-22
          - Added SRv6 locator app to l2vpn index
       2025-03-25
          - Added is-static field to PW local label
       2025-01-27
          - Added SRv6 value to psn-type enum
       2025-01-07
          - Changed policy_bw from 32-bit to 64-bit
       2025-01-03
          - Added EVPN IPMAC is-illegal
       2024-12-16
          - Add MSTI source-l2vpn and source-evpn and evpn-route-valid.
       2024-12-13
          - Changed required_bw and admited_bw from 32-bit to 64-bit
       2024-11-30
          - Remove instances-frr arrays
       2024-11-30
          - Add MSTI fast-path-frr-active
       2024-11-26
          - Added force-pw-up-state to xconnect/segment/pseudowire
       2024-09-03
          - Made several L2FIB opaque and string elements variable size: pw-id, irb-plat-data, platform-data
       2024-08-23
          - L2FIB support for EVPN VPWS L2FRR.
       2024-08-12
          - Added decoupled-mode to xconnect, status-up to l2fibx-con
       2024-08-08
          - Added protection-replay-complete bool to main-interface
       2024-07-31
          - Added pseudo-wire/remote-path-buffer
       2024-06-25
          - Added im-mtu-max-packet-size to the PWHE detail output
       2024-06-24
          - Added ARP/ND suppression flags to BVI info
       2024-05-03
          - Remove deprecated MOI ipv6-mapping-key
       2024-03-01
          - Add IPMAC Learning is-immutable, is-nd-override and is-nd-router
       2024-02-12
          - Add L2FIB support for Service-Groups (SGs)
       2024-01-25
          - Added evi-bd-count to summary
       2024-01-11
          - Add EVPN IPMAC is-immutable, is-nd-override and is-nd-router
       2023-11-10
          - Add support for pseudowires with XCID as PW ID
       2023-11-08
          - Added PD mac-address details
       2023-10-31
          - Add reroute-label to EVPN ports in l2vpn-forwarding
       2023-10-11
          - Add EVPN IPMAC is-best and is-latest
       2023-10-07
          - Add EVPN IPMAC bp-interface and xcid
       2023-10-02
          - Add replication-type to l2fib-evpn-incl-mcast-leaf-info
       2023-10-01
          - Added new internal service group app enum entry to l2vpn_id_mgr_app_bag_type
       2023-09-30
          - Add dynamic flow-label to EVPN Instance
       2023-06-17
          - Renamed master-context to primary-context - Renamed slave-context to secondary-context - Renamed master-time to primary-time
       2023-06-16
          - Added to stale-xid-modified to l2fib-mroute-summary.
       2023-06-01
          - Added modules-registered-for-issu-phase to nsr and proc-fsm information
       2023-05-09
          - Added no-child-vc and no-child-vc-up EVPN Down reasons - Increased the value of evpn-down-reason-max
       2023-04-28
          - Updated l2vpn-pw to hold vlan-aware-vc-up-count and vlan-aware-vc-down-count
       2023-04-26
          - Restructure EVPN path lists into an l2vpn-label-path-buffer container
       2023-03-27
          - Remove reference-count from mstp-port and main-interface-info
       2023-03-10
          - Remove iflist related items.
       2023-02-28
          - Remove pw-oam-refresh-transmit-time from l2vpn-globals
       2023-02-10
          - Add more states to l2fib-evpn-ip4mac and l2fib-evpn-ip6mac, remove arp-nd-delete-pending.
       2023-02-02
          - Change generic-interface-list to conform to new model.
       2023-02-01
          - Added EMOI ipv6-mapping-key and is-sh - Updated EMOI moi-type enum names
       2022-12-22
          - Added Promoted Backup EVPN DF Role.
       2022-12-09
          - Added pseudowire-headend under standby and node containers.
       2022-12-06
          - Added static L2 service vni mode.
       2022-11-29
          - Restructured remote-split-horizon-group-labels with an esi-id specific to encap-type.
       2022-11-19
          - Added LTEP NHOP support.
       2022-10-19
          - Deprecated logging NSR config
       2022-09-28
          - Added Global ID for PWHE IDBs.
       2022-09-14
          - Added evpn-esi-id for bridge port.
       2022-09-12
          - Added Attachment-Circuit to IP Tunnel cross-connect type.
       2022-09-07
          - Added ac-extra-id to attachment-circuit
       2022-09-07
          - Added IPv6 fields to VNI info - Added EVPN Peer ES down - Added internal-id to EVPN MOI context
       2022-09-01
          - Added internal-id to pseudowire-headend detail-interface
       2022-08-30
          - l2fib-summary: Added VXLAN nexthop information
       2022-08-09
          - Added L2VPN-VXLAN-TUNNEL grouping. - Added vxlan-tunnel container to L2VPN-SEGMENT grouping.
       2022-08-08
          - Added ESI ID for used in ESI filtering
       2022-07-06
          - Added new ID MGR App type for Auto RD per EVI
       2022-06-24
          - Update format of l2fib-message-summary
       2022-06-06
          - l2fib-evpn-incl-mcast-ole: Removed SRv6 SID format and added VNI ID to naming
       2022-05-30
          - Added a new leaf mac-limit-enabled to L2VPN-BRIDGE-SEC-PARAM.
       2022-05-26
          Refactored ES Service Carving Arrays
       2022-05-03
          - Added mac-limit-enabled - Removed duplicate fields
       2022-04-14
          - Add new APP type in IDMGR
       2022-03-21
          - Removed legacy and override ESI types
       2022-03-14
          - Added new members to main-interface-info protect-type
       2022-03-09
          - l2fib-mroute-port: Added hardware-information leaf.
       2022-03-08
          - Add EVPN unicast-label and multicast-label.
       2022-02-24
          - l2fib-mroute-port: Added pin-down-interface-name leaf.
       2022-02-09
          - Added l2fib-l3-sync-interfaces - Update keys of l2fib-mroute-port - Add l2fib-evpn-etree-remote - Update keys of l2fib-evpn-incl-mcast-ole - Add l2fib-mroute-ipv6-summary - Only expose valid keys and members of l2fib-mac-learning-mac, l2fib-mac-learning-mac-ipv4, and l2fib-mac-learning-mac-ipv6";
    semver:module-version "6.0.0";
  }
  revision 2021-09-07 {
    description
      "- Added SRv6 nhop
       2021-08-24
           Updated l2vpn forwarding adjacencies to expose both interface and address information.
       2021-08-13
           - Changed flag-extension to 32bit
       2021-07-20
           - Added support for MAC is-cfm flag";
    semver:module-version "5.0.0";
  }
  revision 2020-05-05 {
    description
      "changes related to treat SRv6 and SID as well-known when parsing XML for yang";
    semver:module-version "4.0.0";
  }
  revision 2020-04-28 {
    description
      "- AC Backup related changes
       2020-01-22
       - PWGROUP related changes
       2019-12-20
       - EVPN-VPWS related changes - SR-TE policy related changes";
    semver:module-version "3.0.0";
  }
  revision 2019-04-05 {
    description
      "Establish semantic version baseline.";
    semver:module-version "2.0.0";
  }
  revision 2019-03-30 {
    description
      "- Rename l2fib-mac-learning-mac* interface-handle to interface-name - Rename l2fib-pw-group tunnel-if-handle to tunnel-interface-name - Convert several array from leaf-list to list syntax. - Implement range datatypes for all L2FIB integers.";
  }
  revision 2018-08-01 {
    description
      "Removed empty groupings.";
  }
  revision 2017-09-07 {
    description
      "Fixed type translation error.";
  }
  revision 2017-06-26 {
    description
      "Change identifiers to be more readable.";
  }
  revision 2017-05-01 {
    description
      "Fixing backward compatibility error in module.";
  }
  revision 2015-11-09 {
    description
      "IOS XR 6.0 revision.";
  }

  typedef L2vpn-pwhe-intf {
    type enumeration {
      enum "pseudowire-ether" {
        value 0;
        description
          "PW Ether";
      }
      enum "pseudowire-iw" {
        value 1;
        description
          "PW IW";
      }
    }
    description
      "Interface type";
  }

  typedef Pwhe-port-im-state {
    type enumeration {
      enum "unknown" {
        value 0;
        description
          "Unknown";
      }
      enum "down" {
        value 1;
        description
          "Down";
      }
      enum "up" {
        value 2;
        description
          "Up";
      }
    }
    description
      "Pseudowire headend port states";
  }

  grouping L2VPN-PWHE-SUMMARY {
    description
      "Pseudowire headend summary";
    leaf interfaces {
      type uint32;
      description
        "Number of PW-HE interfaces";
    }
    leaf up-interfaces {
      type uint32;
      description
        "Number of interfaces up";
    }
    leaf down-interfaces {
      type uint32;
      description
        "Number of interfaces down";
    }
    leaf admin-down-interfaces {
      type uint32;
      description
        "Number of interfaces admin down";
    }
    leaf psuedowire-ether-interfaces {
      type uint32;
      description
        "Number of PW-Ether interfaces";
    }
    leaf up-psuedowire-ether-interfaces {
      type uint32;
      description
        "Number of PW-Ether interfaces up";
    }
    leaf down-pseudowire-ether-interfaces {
      type uint32;
      description
        "Number of PW-Ether interfaces down";
    }
    leaf admin-down-pseudowire-ether-interfaces {
      type uint32;
      description
        "Number of PW-Ether interfaces admin down";
    }
    leaf pseudowire-iw-interfaces {
      type uint32;
      description
        "Number of PW-IW interfaces";
    }
    leaf up-pseudowire-iw-interfaces {
      type uint32;
      description
        "Number of PW-IW interfaces up";
    }
    leaf down-pseudowire-iw-interfaces {
      type uint32;
      description
        "Number of PW-IW interfaces down";
    }
    leaf admin-down-pseudowire-iw-interfaces {
      type uint32;
      description
        "Number of PW-IW interfaces admin down";
    }
  }

  grouping L2VPN-PWHE-MAC-ADDR {
    description
      "MAC Address";
    leaf mac-address {
      type yang:mac-address;
      description
        "MAC Address";
    }
  }

  grouping L2VPN-L2-ADDR-PWHE-DETAIL {
    description
      "L2VPN L2 ADDR PWHE DETAIL";
    container mac-address {
      when "../interface-type = 'pseudowire-ether'" {
        description
          "../InterfaceType = 'PseudowireEther'";
      }
      description
        "MAC address";
      uses L2VPN-PWHE-MAC-ADDR;
    }
    leaf interface-type {
      type L2vpn-pwhe-intf;
      description
        "InterfaceType";
    }
  }

  grouping L2VPN-PWHE-DETAIL {
    description
      "Pseudowire headend detail";
    container l2-address {
      description
        "Layer2 Address";
      uses L2VPN-L2-ADDR-PWHE-DETAIL;
    }
    leaf interface-state {
      type Pwhe-port-im-state;
      description
        "Interface Status";
    }
    leaf admin-state {
      type Pwhe-port-im-state;
      description
        "Interface Admin Status";
    }
    leaf mtu {
      type uint32;
      description
        "MTU";
    }
    leaf im-mtu-max-packet-size {
      type uint32;
      description
        "Max Packet Size MTU from IM";
    }
    leaf bandwidth {
      type uint32;
      units "kbit/s";
      description
        "Bandwidth (Kbps)";
    }
    leaf label {
      type uint32;
      description
        "Label";
    }
    leaf l2-overhead {
      type uint32;
      description
        "L2 Overhead";
    }
    leaf vctype {
      type uint32;
      description
        "VC Type";
    }
    leaf control-word {
      type boolean;
      description
        "Control Word";
    }
    leaf internal-id {
      type uint32;
      description
        "Internal ID";
    }
  }

  grouping EVT-HIST-ENTRY {
    description
      "Event history Entry";
    leaf evt-timestamp {
      type string;
      description
        "The timestamp of the event";
    }
    leaf evt-name {
      type string;
      description
        "Event name";
    }
    leaf evt-type {
      type uint8;
      description
        "Event type";
    }
    leaf evt-many {
      type boolean;
      description
        "Multiple instance flag";
    }
    leaf evt-sticky {
      type boolean;
      description
        "Sticky flag";
    }
    list evt-data {
      description
        "Optional data";
      leaf entry {
        type uint32;
        description
          "Optional data";
      }
    }
  }

  grouping EVT-HIST-INFO {
    description
      "Per object event history";
    leaf evt-class-name {
      type string;
      description
        "Class name string";
    }
    leaf evt-granularity-ms {
      type uint32;
      units "millisecond";
      description
        "Granularity of timestamps, in milliseconds";
    }
    list evt-entry {
      description
        "Array of event entries";
      uses EVT-HIST-ENTRY;
    }
  }
}
