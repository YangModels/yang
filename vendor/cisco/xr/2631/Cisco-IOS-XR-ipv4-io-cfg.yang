module Cisco-IOS-XR-ipv4-io-cfg {
  namespace "http://cisco.com/ns/yang/Cisco-IOS-XR-ipv4-io-cfg";
  prefix ipv4-io-cfg;

  import ietf-inet-types {
    prefix inet;
  }
  import Cisco-IOS-XR-types {
    prefix xr;
  }
  import cisco-semver {
    prefix semver;
  }
  import Cisco-IOS-XR-ifmgr-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ipv4-io package configuration.
     
     This YANG module augments the
       Cisco-IOS-XR-ifmgr-cfg
     module with configuration data.
     
     Copyright (c) 2013-2021 by Cisco Systems, Inc.
     All rights reserved.";

  revision 2021-08-25 {
    description
      "Added new leaf for primary and secondary address.";
    semver:module-version "1.2.0";
  }
  revision 2020-02-18 {
    description
      "Added new leaf icmp-unreach-disable.";
    semver:module-version "1.1.0";
  }
  revision 2019-04-05 {
    description
      "Establish semantic version baseline.";
    semver:module-version "1.0.0";
  }
  revision 2018-01-11 {
    description
      "DHCP IPv4 client to support options in cli.";
  }
  revision 2017-05-01 {
    description
      "Fixing backward compatibility error in module.";
  }
  revision 2015-07-30 {
    description
      "Descriptions updated.";
  }
  revision 2015-01-07 {
    description
      "IOS XR 5.3.1 revision.";
  }

  typedef Ipv4-reachable {
    type enumeration {
      enum "any" {
        value 0;
        description
          "Source is reachable via any interface";
      }
      enum "received" {
        value 1;
        description
          "Source is reachable via interface on which
           packet was received";
      }
    }
    description
      "Ipv4 reachable";
  }

  typedef Ipv4-self-ping {
    type enumeration {
      enum "disabled" {
        value 0;
        description
          "Doesn't allow router to ping itself";
      }
      enum "enabled" {
        value 1;
        description
          "Allow router to ping itself";
      }
    }
    description
      "Ipv4 self ping";
  }

  typedef Ipv4-default-ping {
    type enumeration {
      enum "disabled" {
        value 0;
        description
          "Default route is not allowed to match when
           checking source address";
      }
      enum "enabled" {
        value 1;
        description
          "Allow default route to match when checking
           source address";
      }
    }
    description
      "Ipv4 default ping";
  }

  typedef Ipv4-interface-qppb {
    type enumeration {
      enum "ip-precedence" {
        value 1;
        description
          "Enable IP precedence based QPPB";
      }
      enum "qos-group" {
        value 2;
        description
          "Enable QoS-group based QPPB";
      }
      enum "both" {
        value 3;
        description
          "Enable both IP precedence and QoS-group based
           QPPB";
      }
    }
    description
      "Ipv4 interface qppb";
  }

  augment "/a1:interface-configurations/a1:interface-configuration" {
    description
      "This augment extends the configuration data of
       'Cisco-IOS-XR-ifmgr-cfg'";
    container ipv4-network {
      description
        "Interface IPv4 Network configuration data";
      container bgp-pa {
        description
          "Interface ipv4 bgp configuration";
        container input {
          description
            "Input";
          leaf source-accounting {
            type boolean;
            description
              "BGP PA configuration on source";
          }
          leaf destination-accounting {
            type boolean;
            description
              "BGP PA configuration on destination";
          }
        }
        container output {
          description
            "Output";
          leaf source-accounting {
            type boolean;
            description
              "BGP PA configuration on source";
          }
          leaf destination-accounting {
            type boolean;
            description
              "BGP PA configuration on destination";
          }
        }
      }
      container verify {
        description
          "Enable Verify handling for this interface";
        leaf reachable {
          type Ipv4-reachable;
          description
            "Source is reachable via any interface or
             interface on which packet was received";
        }
        leaf self-ping {
          type Ipv4-self-ping;
          description
            "Allow router to ping itself (opens
             vulnerability in verification)";
        }
        leaf default-ping {
          type Ipv4-default-ping;
          description
            "Allow default route to match when checking
             source address";
        }
      }
      container bgp {
        description
          "Interface ipv4 bgp configuration";
        container qppb {
          description
            "Interface ipv4 bgp policy propagation
             configuration";
          container input {
            description
              "Input";
            leaf source {
              type Ipv4-interface-qppb;
              description
                "QPPB configuration on source";
            }
            leaf destination {
              type Ipv4-interface-qppb;
              description
                "QPPB configuration on destination";
            }
          }
        }
        container flow-tag {
          description
            "Interface ipv4 bgp policy propagation flow tag
             configuration";
          container flow-tag-input {
            description
              "Input";
            leaf source {
              type boolean;
              description
                "FlowTag configuration on source";
            }
            leaf destination {
              type boolean;
              description
                "FlowTag configuration on destination";
            }
          }
        }
      }
      container addresses {
        description
          "Set the IP address of an interface";
        container secondaries {
          description
            "Specify a secondary address";
          list secondary {
            key "address";
            description
              "IP address and Mask";
            leaf address {
              type inet:ipv4-address-no-zone;
              description
                "Secondary IP address";
            }
            leaf netmask {
              type inet:ipv4-address-no-zone;
              mandatory true;
              description
                "Netmask";
            }
            leaf route-tag {
              type uint32 {
                range "1..4294967295";
              }
              description
                "RouteTag";
            }
            leaf algorithm {
              type uint32 {
                range "128..255";
              }
              description
                "Algorithm";
            }
          }
        }
        container primary {
          presence "Indicates a primary node is configured.";
          description
            "IP address and Mask";
          leaf address {
            type inet:ipv4-address-no-zone;
            mandatory true;
            description
              "IP address";
          }
          leaf netmask {
            type inet:ipv4-address-no-zone;
            mandatory true;
            description
              "Netmask";
          }
          leaf route-tag {
            type uint32 {
              range "1..4294967295";
            }
            description
              "RouteTag";
          }
          leaf algorithm {
            type uint32 {
              range "128..255";
            }
            description
              "Algorithm";
          }
        }
        leaf unnumbered {
          type xr:Interface-name;
          description
            "Enable IP processing without an explicit
             address";
        }
        leaf dhcp {
          type empty;
          description
            "IPv4 address and Mask negotiated via DHCP";
        }
      }
      container helper-addresses {
        description
          "The set of IP destination addresses for UDP
           broadcasts";
        list helper-address {
          key "address vrf-name";
          description
            "An IP destination addresses for UDP broadcasts";
          leaf address {
            type inet:ipv4-address-no-zone;
            description
              "IP destination address";
          }
          leaf vrf-name {
            type xr:Cisco-ios-xr-string {
              length "1..32";
            }
            description
              "VRF name";
          }
        }
      }
      leaf forwarding-enable {
        type empty;
        description
          "IPv4 forwarding to get enabled on an interface";
      }
      leaf icmp-unreach-disable {
        type empty;
        description
          "Disable ICMP unreachable for Nullx interface";
      }
      leaf icmp-mask-reply {
        type empty;
        description
          "The flag for enabling sending of ICMP mask
           reply messages";
      }
      leaf tcp-mss-adjust-enable {
        type empty;
        description
          "Enable TCP MSS Adjust on an interface";
      }
      leaf ttl-propagate-disable {
        type empty;
        description
          "Disable TTL propagate on an interface";
      }
      leaf point-to-point {
        type empty;
        description
          "Enable point-to-point handling for this
           interface.";
      }
      leaf mtu {
        type uint32 {
          range "68..65535";
        }
        description
          "The IP Maximum Transmission Unit";
      }
    }
  }
  augment "/a1:interface-configurations/a1:interface-configuration" {
    description
      "This augment extends the configuration data of
       'Cisco-IOS-XR-ifmgr-cfg'";
    container ipv4-network-forwarding {
      description
        "Interface IPv4 Network configuration data also
         used for forwarding";
      leaf directed-broadcast {
        type empty;
        description
          "Enable forwarding of directed broadcast";
      }
      leaf unreachables {
        type empty;
        description
          "Disable sending ICMP unreachables";
      }
      leaf redirects {
        type empty;
        description
          "Enable sending ICMP Redirect messages";
      }
    }
  }
}
