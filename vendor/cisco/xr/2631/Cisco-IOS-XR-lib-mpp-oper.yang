module Cisco-IOS-XR-lib-mpp-oper {
  namespace "http://cisco.com/ns/yang/Cisco-IOS-XR-lib-mpp-oper";
  prefix lib-mpp-oper;

  import cisco-semver {
    prefix semver;
  }
  include Cisco-IOS-XR-lib-mpp-oper-sub1 {
    revision-date 2019-04-05;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR lib-mpp package operational data.
     
     This module contains definitions
     for the following management objects:
       management-plane-protection: Management Plane Protection (MPP)
         operational data
     
     Copyright (c) 2013-2019 by Cisco Systems, Inc.
     All rights reserved.";

  revision 2019-04-05 {
    description
      "Establish semantic version baseline.";
    semver:module-version "1.0.1";
  }
  revision 2017-05-01 {
    description
      "Fixing backward compatibility error in module.";
  }
  revision 2015-01-07 {
    description
      "IOS XR 5.3.1 revision.";
  }

  grouping INTERFACE-TABLE {
    description
      "Common node of inband, outband";
    container interfaces {
      description
        "List of inband/outband interfaces";
      list interface {
        key "interface-name";
        description
          "MPP interface information";
        leaf interface-name {
          type string;
          description
            "Interface name, specify 'all' for all
             interfaces";
        }
        uses MPP-PROTO;
      }
    }
  }

  container management-plane-protection {
    config false;
    description
      "Management Plane Protection (MPP) operational
       data";
    container outband {
      description
        "Management Plane Protection (MPP) outband
         interface data";
      container vrf {
        description
          "Outband VRF information";
        uses VRF-INFO;
      }
      uses INTERFACE-TABLE;
    }
    container inband {
      description
        "Management Plane Protection (MPP) inband
         interface data";
      uses INTERFACE-TABLE;
    }
  }
}
