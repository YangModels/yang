submodule Cisco-IOS-XR-crypto-svault-oper-sub1 {
  belongs-to Cisco-IOS-XR-crypto-svault-oper {
    prefix Cisco-IOS-XR-crypto-svault-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR crypto-svault package operational data.
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  grouping SVAULT-EDM-STATUS-RESULT {
    description
      "Show Svault status result";
    leaf vault-enable {
      type boolean;
      description
        "VaultEnable";
    }
    leaf vault-redundancy {
      type boolean;
      description
        "VaultRedundancy";
    }
    leaf host {
      type string;
      description
        "Host";
    }
    leaf port {
      type string;
      description
        "Port";
    }
    leaf https-enable {
      type boolean;
      description
        "HttpsEnable";
    }
    leaf auth-support-list {
      type string;
      description
        "AuthSupportList";
    }
  }
}
