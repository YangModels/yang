module Cisco-IOS-XR-install-cfg {
  namespace "http://cisco.com/ns/yang/Cisco-IOS-XR-install-cfg";
  prefix install-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR install package configuration.
     
     This module contains definitions
     for the following management objects:
       install: Install configuration data
     
     Copyright (c) 2013-2025 by Cisco Systems, Inc.
     All rights reserved.";

  revision 2025-11-21 {
    description
      "Deprecated support for remote repositories (FTP, HTTP, and HTTPS URLs)";
    semver:module-version "1.1.0";
  }
  revision 2019-12-11 {
    description
      "Repository URL description updated.";
    semver:module-version "1.0.1";
  }
  revision 2019-04-05 {
    description
      "Establish semantic version baseline.";
    semver:module-version "1.0.0";
  }
  revision 2015-11-09 {
    description
      "IOS XR 6.0 revision.";
  }

  feature is-lnt {
    description
      "Enabled for LNT only";
  }

  container install {
    description
      "Install configuration data";
    container repositories {
      if-feature "is-lnt";
      description
        "Table of repositories";
      list repository {
        key "id";
        description
          "Repository configuration";
        leaf url {
          type string {
            length "1..900";
          }
          description
            "Repository URL - path to local repository or
             directory or ftp, http, or https path to
             remote repository, optionally containing the
             name of a VRF for the repository. Format one
             of: 
               ftp://<server>[;<vrf>]/<path_to_repo>
             (DEPRECATED IN 26.1.1)
               http://<server>[
             ;<vrf>]/<path_to_repo> (DEPRECATED IN 26.1
             .1)
               https://<server>[;<vrf>]/<path_to_repo>
             (DEPRECATED IN 26.1.1)
               file
             :///<path_to_repo>";
        }
        leaf description {
          type string {
            length "1..900";
          }
          description
            "Repository name or description";
        }
        leaf id {
          type string {
            length "1..80";
          }
          description
            "Repository identifier";
        }
      }
    }
    container fingerprints {
      presence "CLI submode compatibility.";
      description
        "Container for fingerprint config";
      leaf frequency {
        if-feature "is-lnt";
        type uint32 {
          range "1..12";
        }
        units "hour";
        description
          "Configured frequency of RPM fingerprint
           generation";
      }
    }
  }
}
