//*************  DO-NOT EDIT  **************
//*********** Auto-generated file ********** 

 module cisco-xr-openconfig-sampling-sflow-deviations {

  prefix  "oc-sflowdevs";

  namespace "http://cisco.com/ns/yang/cisco-xr-openconfig-sampling-sflow-deviations";

  import openconfig-sampling-sflow { prefix oc-sflow; }
  import openconfig-sampling { prefix oc-sampling; }

  organization "Cisco Systems, Inc.";

  contact
    "Cisco Systems, Inc.
     Customer Service

     Postal: 170 West Tasman Drive
     San Jose, CA 95134

     Tel: +1 800 553-NETS

     E-mail: cs-yang@cisco.com";

  description
    "This module contains a set of deviations for 

     openconfig-sampling-sflow.yang@2022-06-21 

     on Cisco IOS-XR devices.

     Copyright (c) 2023-2026 by Cisco Systems, Inc.
     All rights reserved.";

  revision "2026-05-11" {
    description
      "Remove deviations for packets-sampled and packets-sent state leaves";
  }
  revision "2023-01-18" {
    description
      "Initial revision applicable to IOS-XR 7.10.1";
  }

  deviation /oc-sampling:sampling/oc-sflow:sflow/oc-sflow:config/oc-sflow:egress-sampling-rate {
    deviate not-supported;
  }

  deviation /oc-sampling:sampling/oc-sflow:sflow/oc-sflow:state/oc-sflow:egress-sampling-rate {
    deviate not-supported;
  }

  deviation /oc-sampling:sampling/oc-sflow:sflow/oc-sflow:interfaces/oc-sflow:interface/oc-sflow:config/oc-sflow:polling-interval {
    deviate not-supported;
  }

  deviation /oc-sampling:sampling/oc-sflow:sflow/oc-sflow:interfaces/oc-sflow:interface/oc-sflow:state/oc-sflow:polling-interval {
    deviate not-supported;
  }

}
