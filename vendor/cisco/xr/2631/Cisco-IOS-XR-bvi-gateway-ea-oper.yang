module Cisco-IOS-XR-bvi-gateway-ea-oper {
  namespace "http://cisco.com/ns/yang/Cisco-IOS-XR-bvi-gateway-ea-oper";
  prefix bvi-gateway-ea-oper;

  import Cisco-IOS-XR-types {
    prefix xr;
  }
  import cisco-semver {
    prefix semver;
  }
  include Cisco-IOS-XR-bvi-gateway-ea-oper-sub1 {
    revision-date 2026-04-08;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR bvi-gateway-ea package operational data.
     
     This module contains definitions
     for the following management objects:
       bvi-gateway-ea: BVI-Gateway Execution Agent Operational Table
     
     Copyright (c) 2013-2026 by Cisco Systems, Inc.
     All rights reserved.";

  revision 2026-04-08 {
    description
      "Initial revision.";
    semver:module-version "1.0.0";
  }
  revision 2019-04-05 {
    description
      "Establish semantic version baseline.";
  }
  revision 2015-11-09 {
    description
      "IOS XR 6.0 revision.";
  }

  container bvi-gateway-ea {
    config false;
    description
      "BVI-Gateway Execution Agent Operational Table";
    container nodes {
      description
        "Table of BVI-Gateway EA data for a particular
         node";
      list node {
        key "node-id";
        description
          "BVI-Gateway EA operational data for a
           particular node";
        container bvi-gateway-interfaces {
          description
            "BVI-Gateway interface table";
          list bvi-gateway-interface {
            key "bvi-gateway-name";
            description
              "BVI-Gateway EA Interface Database Entry";
            leaf bvi-gateway-name {
              type xr:Interface-name;
              description
                "Interface Name";
            }
            uses L3DAG-EA-IDB;
          }
        }
        leaf node-id {
          type xr:Node-id;
          description
            "Location";
        }
      }
    }
  }
}
