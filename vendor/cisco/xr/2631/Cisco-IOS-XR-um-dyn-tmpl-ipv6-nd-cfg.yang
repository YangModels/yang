module Cisco-IOS-XR-um-dyn-tmpl-ipv6-nd-cfg {
  namespace "http://cisco.com/ns/yang/Cisco-IOS-XR-um-dyn-tmpl-ipv6-nd-cfg";
  prefix um-dyn-tmpl-ipv6-nd-cfg;

  import Cisco-IOS-XR-types {
    prefix xr;
  }
  import Cisco-IOS-XR-um-dynamic-template-cfg {
    prefix a1;
  }
  import Cisco-IOS-XR-um-dynamic-template-ipv6-cfg {
    prefix a2;
  }
  import ietf-inet-types {
    prefix inet;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR dyn-tmpl-ipv6-nd package configuration.
     
     This YANG module augments the
     modules with configuration data.
     
     Copyright (c) 2022-2025 by Cisco Systems, Inc., and/or its affiliates.
     All rights reserved.";

  revision 2023-02-27 {
    description
      "Added ra dns servers";
    semver:module-version "1.1.0";
  }
  revision 2020-12-14 {
    description
      "Initial release";
    semver:module-version "1.0.0";
  }

  grouping TEMPLATE-BODY {
    description
      "Grouping for template";
    container nd {
      description
        "ipv6 Neighbor Discovery subcommands";
      container ra-unicast {
        presence "Indicates a ra-unicast node is configured.";
        description
          "Send Unicast Solicited IPv6 Router Advertisements";
      }
      container router-preference {
        description
          "IPv6 ND router-preference";
        container high {
          must "not(../medium or ../low)";
          presence "Indicates a high node is configured.";
          description
            "High default router preference";
        }
        container medium {
          must "not(../high or ../low)";
          presence "Indicates a medium node is configured.";
          description
            "Medium default router preference";
        }
        container low {
          must "not(../high or ../medium)";
          presence "Indicates a low node is configured.";
          description
            "Low default router preference";
        }
      }
      leaf reachable-time {
        type uint32 {
          range "0..3600000" {
            description
              "Reachability time in milliseconds";
          }
        }
        description
          "Set advertised reachability time";
      }
      container dad {
        description
          "Set number of Duplicate Address Detection(DAD) transmits";
        leaf attempts {
          type uint32 {
            range "0..600" {
              description
                "Number of attempts";
            }
          }
          description
            "Set IPv6 Duplicate Address Detection(DAD) Transmits";
        }
      }
      container suppress-ra {
        presence "Indicates a suppress-ra node is configured.";
        description
          "Suppress IPv6 Router Advertisements(RA)";
      }
      container other-config-flag {
        presence "Indicates a other-config-flag node is configured.";
        description
          "Hosts should use stateful protocol for non-address config";
      }
      container managed-config-flag {
        presence "Indicates a managed-config-flag node is configured.";
        description
          "Hosts should use stateful protocol for address config";
      }
      leaf ns-interval {
        type uint32 {
          range "1000..4294967295" {
            description
              "Retransmission interval in milliseconds";
          }
        }
        description
          "Set advertised Neighbor Solicitation(NS) retransmission interval";
      }
      leaf ra-interval {
        type uint32 {
          range "4..1800" {
            description
              "Maximum RA Interval (sec)";
          }
        }
        description
          "Set IPv6 Router Advertisement(RA) Interval";
      }
      leaf minimum-ra-interval {
        type uint32 {
          range "3..1800" {
            description
              "Minimum RA Interval (sec). Must be less than 0.75 * maximum interval";
          }
        }
        must "../ra-interval";
        description
          "Minimum RA Interval (sec). Must be less than 0.75 * maximum interval";
      }
      leaf ra-lifetime {
        type uint32 {
          range "0..9000" {
            description
              "RA Lifetime (seconds)";
          }
        }
        description
          "Set IPv6 Router Advertisement(RA) Lifetime";
      }
      container hoplimit {
        description
          "IPv6 Neighbor Discovery(ND) Router Advertisement(RA) hoplimit";
        container unspecified {
          presence "Indicates a unspecified node is configured.";
          description
            "Unspecified IPv6 Neighbor Discovery(ND) Router Advertisement(RA) hop-limit value";
        }
      }
      container mtu {
        description
          "IPv6 Neighbor Discovery(ND) Router Advertisement(RA) mtu option configuration";
        container suppress {
          presence "Indicates a suppress node is configured.";
          description
            "Suppress mtu option in IPv6  Neighbor Discovery(ND) Router Advertisement(RA) header";
        }
      }
      container suppress-cache-learning {
        presence "Indicates a suppress-cache-learning node is configured.";
        description
          "IPv6 Neighbor Discovery(ND) configuration";
      }
      container nud-enable {
        presence "Indicates a nud-enable node is configured.";
        description
          "IPv6 Neighbor Unreachability Detection(NUD) configuration. Applies only to IPoe Sessions";
      }
      container start-ra-on-ipv6-enable {
        presence "Indicates a start-ra-on-ipv6-enable node is configured.";
        description
          "Start RA generation on ipv6-enable config irrespective ipv6 afi state";
      }
      leaf framed-prefix-pool {
        type xr:Cisco-ios-xr-string {
          length "1..64" {
            description
              "Name of framed address pool";
          }
        }
        description
          "IPv6 Neighbor Discovery(ND) pool configuration";
      }
      leaf ra-initial {
        type uint32 {
          range "0..32" {
            description
              "Initial number of Router Advertisements(RA) ";
          }
        }
        must "../initial-router-advertisement";
        description
          "Set IPv6 Initial Router Advertisement(RA) Count and Interval";
      }
      leaf initial-router-advertisement {
        type uint32 {
          range "4..1800" {
            description
              "Initial Router Advertisement(RA) Interval (sec).";
          }
        }
        must "../ra-initial";
        description
          "Initial Router Advertisement(RA) Interval (sec).";
      }
      container ra {
        description
          "IPv6 ND RA sub commands";
        container dns {
          description
            "IPv6 ND RA DNS";
          container servers {
            description
              "IPv6 ND RA DNS Server";
            list server {
              must "server-lifetime or zero-lifetime";
              key "address";
              description
                "IPv6 ND RA DNS Server";
              leaf address {
                type inet:ipv6-address-no-zone;
                description
                  "RA DNS Server IPv6 Address x:x::y";
              }
              leaf address-copy {
                type inet:ipv6-address-no-zone;
                mandatory true;
                description
                  "RA DNS Server IPv6 Address x:x::y";
              }
              leaf server-lifetime {
                type uint32 {
                  range "12..4294967295" {
                    description
                      "IPv6 RA DNS Server Lifetime Interval in Seconds,range should be between(3*(max ra interval)) <= dns lifetime <= 4294967295";
                  }
                }
                must "not(../zero-lifetime)";
                description
                  "IPv6 RA DNS Server Lifetime Interval in Seconds,range should be between(3*(max ra interval)) <= dns lifetime <= 4294967295";
              }
              container zero-lifetime {
                must "not(../server-lifetime)";
                presence "Indicates a zero-lifetime node is configured.";
                description
                  "Zero IPv6 RA DNS Server Lifetime";
              }
            }
          }
        }
      }
    }
  }

  augment "/a1:dynamic-template/a1:type/a1:ppp/a1:template/a2:ipv6" {
    description
      "This augment extends dynamic-template ppp nodes
       configuration";
    uses TEMPLATE-BODY;
  }
  augment "/a1:dynamic-template/a1:type/a1:ipsubscriber/a1:template/a2:ipv6" {
    description
      "This augment extends dynamic-template ipsubscriber nodes
       configuration";
    uses TEMPLATE-BODY;
  }
  augment "/a1:dynamic-template/a1:type/a1:service/a1:template/a2:ipv6" {
    description
      "This augment extends dynamic-template service nodes
       configuration";
    uses TEMPLATE-BODY;
  }
}
