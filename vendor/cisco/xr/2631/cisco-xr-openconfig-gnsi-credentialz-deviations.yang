module cisco-xr-openconfig-gnsi-credentialz-deviations {

  namespace "http://cisco.com/ns/yang/cisco-xr-openconfig-gnsi-credentialz-deviations";

  prefix  "oc-gnsi-credz-deviations";

  import openconfig-system { prefix oc-sys; }
  import openconfig-gnsi-credentialz { prefix oc-gnsi-credz; }

  organization "Cisco Systems, Inc.";

  contact
    "Cisco Systems, Inc.
     Customer Service

     Postal: 170 West Tasman Drive
     San Jose, CA 95134

     Tel: +1 800 553-NETS

     E-mail: cs-yang@cisco.com";

  description
    "This module contains a set of deviations for

    openconfig-gnsi-credentialz.yang

    on Cisco IOS-XR devices.

    Copyright (c) 2024 by Cisco Systems, Inc.
    All rights reserved.";

  revision "2024-08-29" {
    description
      "Initial deviations for gnsi credentialz";
  }

  deviation /oc-sys:system/oc-sys:aaa/oc-sys:authentication/oc-sys:admin-user/oc-sys:state/oc-gnsi-credz:password-version{
    deviate not-supported;
  }

  deviation /oc-sys:system/oc-sys:aaa/oc-sys:authentication/oc-sys:admin-user/oc-sys:state/oc-gnsi-credz:password-created-on{
    deviate not-supported;
  }

  deviation /oc-sys:system/oc-sys:aaa/oc-sys:authentication/oc-sys:admin-user/oc-sys:state/oc-gnsi-credz:authorized-principals-list-version{
    deviate not-supported;
  }

  deviation /oc-sys:system/oc-sys:aaa/oc-sys:authentication/oc-sys:admin-user/oc-sys:state/oc-gnsi-credz:authorized-principals-list-created-on{
    deviate not-supported;
  }

  deviation /oc-sys:system/oc-sys:aaa/oc-sys:authentication/oc-sys:admin-user/oc-sys:state/oc-gnsi-credz:authorized-keys-list-version{
    deviate not-supported;
  }

  deviation /oc-sys:system/oc-sys:aaa/oc-sys:authentication/oc-sys:admin-user/oc-sys:state/oc-gnsi-credz:authorized-keys-list-created-on{
    deviate not-supported;
  }
 }
