module Cisco-IOS-XR-ipv4-arp-cfg {
  namespace "http://cisco.com/ns/yang/Cisco-IOS-XR-ipv4-arp-cfg";
  prefix ipv4-arp-cfg;

  import ietf-inet-types {
    prefix inet;
  }
  import ietf-yang-types {
    prefix yang;
  }
  import Cisco-IOS-XR-types {
    prefix xr;
  }
  import cisco-semver {
    prefix semver;
  }
  import Cisco-IOS-XR-ifmgr-cfg {
    prefix a1;
  }
  import Cisco-IOS-XR-l2vpn-cfg {
    prefix a2;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ipv4-arp package configuration.
     
     This model is deprecated and is replaced by
     Cisco-IOS-XR-um-arp-cfg.yang which will provide the
     compatible functionalities.
     
     This module contains definitions
     for the following management objects:
       arp: ARP configuraiton
       iedge-cfg: IEDGE ARP configuration
       arpgmp: ARP configuration
       arp-redundancy: ARP configuraiton
     
     This YANG module augments the
       Cisco-IOS-XR-ifmgr-cfg,
       Cisco-IOS-XR-l2vpn-cfg
     modules with configuration data.
     
     Copyright (c) 2013-2025 by Cisco Systems, Inc.
     All rights reserved.";

  revision 2025-01-08 {
    description
      "Adding support for ARP Probe pacing";
    semver:module-version "1.1.0";
  }
  revision 2019-05-12 {
    description
      "Deprecated the native model, replaced by UM model.";
    semver:module-version "1.0.0";
  }
  revision 2019-04-05 {
    description
      "Establish semantic version baseline.";
  }
  revision 2017-05-01 {
    description
      "Fixing backward compatibility error in module.";
  }
  revision 2015-11-09 {
    description
      "IOS XR 6.0 revision.";
  }

  typedef Arp-entry {
    type enumeration {
      enum "static" {
        value 0;
        description
          "Static ARP entry type";
      }
      enum "alias" {
        value 1;
        description
          "Alias ARP entry type";
      }
    }
    description
      "Arp entry";
  }

  typedef Arp-encap {
    type enumeration {
      enum "arpa" {
        value 1;
        description
          "Encapsulation type ARPA";
      }
      enum "srp" {
        value 4;
        description
          "Encapsulation type SRP";
      }
      enum "srpa" {
        value 5;
        description
          "Encapsulation type SRPA";
      }
      enum "srpb" {
        value 6;
        description
          "Encapsulation type SRPB";
      }
    }
    description
      "Arp encap";
  }

  typedef Evpn-proxy {
    type enumeration {
      enum "full-suppression" {
        value 1;
        description
          "EVPN Proxy Full Suppression";
      }
      enum "partial-suppression" {
        value 2;
        description
          "EVPN Proxy Partial Suppression";
      }
    }
    description
      "Evpn proxy";
  }

  augment "/a1:interface-configurations/a1:interface-configuration" {
    description
      "This augment extends the configuration data of
       'Cisco-IOS-XR-ifmgr-cfg'";
    container dagrs {
      status deprecated;
      description
        "This model is deprecated and is replaced by
         Cisco-IOS-XR-um-arp-cfg.yang which will provide
         the compatible functionalities.  Direct-Attached
         Gateway Redundancy configuration";
      list dagr {
        key "ip-addr";
        description
          "The DAGR entry being configured";
        container sub {
          description
            "DAGR Submode configuration";
          container metric {
            description
              "Set Route Metric";
            leaf metric-norm {
              type uint32 {
                range "0..256";
              }
              default "100";
              description
                "Normal Route Metric";
            }
            leaf metric-prio {
              type uint32 {
                range "0..256";
              }
              default "90";
              description
                "Priority Route Metric";
            }
          }
          container timers {
            description
              "Set Query Timers";
            leaf query-time {
              type uint32 {
                range "1..10000";
              }
              default "1";
              description
                "Query Timeout";
            }
            leaf sby-time {
              type uint32 {
                range "1..10000";
              }
              default "20";
              description
                "Standby Query Timeout";
            }
          }
          container distance {
            description
              "Set Route Distance";
            leaf dist-norm {
              type uint32 {
                range "0..256";
              }
              default "150";
              description
                "Normal Route Distance";
            }
            leaf dist-prio {
              type uint32 {
                range "0..256";
              }
              default "5";
              description
                "Priority Route Distance";
            }
          }
          leaf priority-timeout {
            type uint32 {
              range "1..10000";
            }
            default "20";
            description
              "Priority Timeout value";
          }
        }
        leaf enter {
          type empty;
          description
            "DAGR Group Enter item";
        }
        leaf ip-addr {
          type inet:ipv4-address-no-zone;
          description
            "DAGR Peer IPv4 address";
        }
      }
    }
  }
  augment "/a1:interface-configurations/a1:interface-configuration" {
    description
      "This augment extends the configuration data of
       'Cisco-IOS-XR-ifmgr-cfg'";
    container ipv4arp {
      status deprecated;
      description
        "This model is deprecated and is replaced by
         Cisco-IOS-XR-um-arp-cfg.yang which will provide
         the compatible functionalities.  Configure
         Address Resolution Protocol";
      leaf probe-interval {
        type uint32 {
          range "30..300";
        }
        description
          "Probe interval on BFD down event";
      }
      leaf cache-limit {
        type uint32 {
          range "0..127999";
        }
        description
          "Limit ARP cache on the interface";
      }
      leaf learning-local {
        type empty;
        description
          "Enable the dynamic learning of ARP entries(for
           local subnet) on the interface";
      }
      leaf drop-adj-timeout {
        type uint32 {
          range "900..7200";
        }
        units "second";
        default "3600";
        description
          "Number of seconds for ARP drop adjacency
           timeout";
      }
      leaf learning-solicited {
        type empty;
        description
          "ARP learning solicited configuration";
      }
      leaf probe-retries {
        type uint32 {
          range "2..10";
        }
        description
          "Probe retries count on BFD down event";
      }
      leaf gratuitous-ignore {
        type empty;
        description
          "Ignore the receipt of Gratuitous ARP packets on
           the interface";
      }
      leaf proxy-arp {
        type empty;
        description
          "Proxy ARP configuration";
      }
      leaf purge-delay {
        type uint32 {
          range "1..65535";
        }
        description
          "Time to delay purging arp entries when the
           interface goes down";
      }
      leaf learning-disable {
        type empty;
        description
          "Disable the dynamic learning of ARP entries on
           the interface";
      }
      leaf local-proxy-arp {
        type empty;
        description
          "Local Proxy ARP configuration";
      }
      leaf evpn-proxy-arp {
        type Evpn-proxy;
        description
          "ARP EVPN Proxy configuration";
      }
      leaf timeout {
        type uint32 {
          range "30..2144448000";
        }
        units "second";
        description
          "Number of seconds for ARP cache timeout";
      }
    }
  }
  augment "/a1:interface-configurations/a1:interface-configuration/a2:host-tracking" {
    description
      "This augment extends the configuration data of
       'Cisco-IOS-XR-l2vpn-cfg'";
    container host-tracking-arp {
      status deprecated;
      description
        "This model is deprecated and is replaced by
         Cisco-IOS-XR-um-arp-cfg.yang which will provide
         the compatible functionalities.  Enable ARP host
         tracking on this interface";
      leaf bfd-detect-multiplier {
        type uint32 {
          range "2..50";
        }
        description
          "BFD Detect multiplier";
      }
      leaf bfd-min-interval {
        type uint32 {
          range "3..30000";
        }
        description
          "Hello interval in milli-seconds";
      }
      leaf bfd-fast-detect {
        type empty;
        description
          "Enable ARP BFD fast detect on this interface";
      }
      leaf bfd-source-ip-address {
        type inet:ipv4-address-no-zone;
        description
          "BFD Source IPv4 address";
      }
    }
  }
  container arp {
    status deprecated;
    description
      "This model is deprecated and is replaced by
       Cisco-IOS-XR-um-arp-cfg.yang which will provide
       the compatible functionalities.  ARP
       configuraiton";
    container probe-pace {
      presence "Indicates a probe-pace node is configured.";
      description
        "Configure Probe pacing for ARP";
      leaf rate {
        type uint32 {
          range "1..1000";
        }
        units "packet/s";
        description
          "Configure rate for the Probe pacing";
      }
      leaf enable {
        type empty;
        mandatory true;
        description
          "Enable Configure parameter for Probe Pacing";
      }
    }
    leaf max-entries {
      type uint32 {
        range "1..256000";
      }
      description
        "Configure maximum number of safe ARP entries per
         line card";
    }
    leaf inner-cos {
      type uint32 {
        range "0..7";
      }
      description
        "Configure inner cos values for arp packets";
    }
    leaf outer-cos {
      type uint32 {
        range "0..7";
      }
      description
        "Configure outer cos values for arp packets";
    }
    leaf police-interval {
      type uint32 {
        range "1..60";
      }
      units "second";
      description
        "Configure the policing interval in seconds to
         drop the ARP requests with the same MAC and, or
         same IP that comes.";
    }
  }
  container iedge-cfg {
    status deprecated;
    description
      "This model is deprecated and is replaced by
       Cisco-IOS-XR-um-arp-cfg.yang which will provide
       the compatible functionalities.  IEDGE ARP
       configuration";
    leaf subscriber-uncond-proxy {
      type empty;
      description
        "ARP Subscriber Enable Unconditional Proxy ARP";
    }
    leaf subscriber-scale-mode {
      type empty;
      description
        "ARP Subscriber Scale Mode Configuration";
    }
  }
  container arpgmp {
    status deprecated;
    description
      "This model is deprecated and is replaced by
       Cisco-IOS-XR-um-arp-cfg.yang which will provide
       the compatible functionalities.  ARP
       configuration";
    list vrf {
      key "vrf-name";
      description
        "Per VRF configuration, for the default VRF use
         'default'";
      container entries {
        description
          "ARP static and alias entry configuration";
        list entry {
          key "address";
          description
            "ARP static and alias entry configuration item";
          leaf address {
            type inet:ipv4-address-no-zone;
            description
              "IP Address";
          }
          leaf mac-address {
            type yang:mac-address;
            description
              "MAC Address";
          }
          leaf encapsulation {
            type Arp-encap;
            description
              "Encapsulation type";
          }
          leaf entry-type {
            type Arp-entry;
            description
              "Entry type";
          }
          leaf interface {
            type xr:Interface-name;
            description
              "Interface name";
          }
        }
      }
      leaf vrf-name {
        type xr:Cisco-ios-xr-string;
        description
          "VRF name";
      }
    }
  }
  container arp-redundancy {
    status deprecated;
    description
      "This model is deprecated and is replaced by
       Cisco-IOS-XR-um-arp-cfg.yang which will provide
       the compatible functionalities.  ARP
       configuraiton";
    container redundancy {
      presence "Indicates a redundancy node is configured.";
      description
        "Configure parameter for ARP Geo redundancy";
      container groups {
        description
          "Table of Group";
        list group {
          key "group-id";
          description
            "None";
          container peers {
            description
              "Table of Peer";
            list peer {
              key "prefix-string";
              description
                "None";
              leaf prefix-string {
                type inet:ip-address-no-zone;
                description
                  "Neighbor IPv4 address";
              }
            }
          }
          container interface-list {
            presence "Indicates a interface-list node is configured.";
            description
              "List of Interfaces for this Group";
            container interfaces {
              description
                "Table of Interface";
              list interface {
                key "interface-name";
                description
                  "Interface for this Group";
                leaf interface-name {
                  type xr:Interface-name;
                  description
                    "Interface name";
                }
                leaf interface-id {
                  type uint32 {
                    range "1..65535";
                  }
                  mandatory true;
                  description
                    "Interface Id for the interface";
                }
              }
            }
            leaf enable {
              type empty;
              mandatory true;
              description
                "Enable List of Interfaces for this Group.
                 Deletion of this object also causes deletion
                 of all associated objects under
                 InterfaceList.";
            }
          }
          leaf source-interface {
            type xr:Interface-name;
            description
              "Interface name";
          }
          leaf group-id {
            type uint32 {
              range "1..32";
            }
            description
              "Group ID";
          }
        }
      }
      leaf enable {
        type empty;
        mandatory true;
        description
          "Enable Configure parameter for ARP Geo
           redundancy. Deletion of this object also causes
           deletion of all associated objects under
           ArpRedundancy.";
      }
    }
  }
}
