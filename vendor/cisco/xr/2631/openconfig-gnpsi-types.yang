module openconfig-gnpsi-types {
  yang-version "1";
  namespace "http://openconfig.net/yang/gnpsi/types";
  prefix "oc-gnpsit";

  import openconfig-extensions {
    prefix oc-ext;
  }

  import openconfig-system-grpc {
    prefix oc-grpc;
  }

  organization
    "OpenConfig working group";
  contact
    "www.openconfig.net";

  description
    "This module adds gRPC server type relating to gNPSI running on
    a network device.";

  oc-ext:openconfig-version "0.1.0";
  oc-ext:catalog-organization "openconfig";
  oc-ext:origin "openconfig";

  revision 2024-05-29 {
    description
      "Initial revision.";
    reference "0.1.0";
  }

  identity GNPSI {
    base oc-grpc:GRPC_SERVICE;
    description
      "gNPSI: gRPC Network Packet Sampling Interface";
  }
}
