submodule Cisco-IOS-XR-osa-oper-sub1 {
  belongs-to Cisco-IOS-XR-osa-oper {
    prefix Cisco-IOS-XR-osa-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR osa package operational data.
     
     Copyright (c) 2013-2022 by Cisco Systems, Inc.
     All rights reserved.";

  revision 2022-03-16 {
    description
      "Enhancement to support hw-module working and protection path info.";
    semver:module-version "2.1.0";
  }
  revision 2020-06-01 {
    description
      "Enhancement to support LC startup config complete";
    semver:module-version "1.4.0";
  }
  revision 2019-10-11 {
    description
      "Enhancement in CLI for 50G trunk-rate";
    semver:module-version "1.2.0";
  }
  revision 2019-08-13 {
    description
      "Aligning modifications to 7.1.1.";
    semver:module-version "1.1.0";
  }
  revision 2019-04-05 {
    description
      "Establish semantic version baseline.";
    semver:module-version "1.0.0";
  }
  revision 2018-05-23 {
    description
      "Initial Revision.";
  }
  revision 2015-11-09 {
    description
      "IOS XR 6.0 revision.";
  }

  typedef Port-group-bitrate {
    type enumeration {
      enum "none" {
        value 0;
        description
          "Invalid Port Group BW";
      }
      enum "hundred-gig" {
        value 1;
        description
          "Hundred Gig";
      }
      enum "two-hundred-gig" {
        value 2;
        description
          "Two Hundred Gig";
      }
      enum "three-hundred-gig" {
        value 3;
        description
          "Three Hundred Gig";
      }
      enum "four-hundred-gig" {
        value 4;
        description
          "Four Hundred Gig";
      }
      enum "eight-hundred-gig" {
        value 5;
        description
          "Eight Hundred Gig";
      }
    }
    description
      "Port group bitrate";
  }

  typedef Capab {
    type enumeration {
      enum "txp" {
        value 0;
        description
          "Transponder";
      }
      enum "mxp" {
        value 1;
        description
          "Muxponder";
      }
    }
    description
      "Capab";
  }

  typedef Slice-client-bitrate {
    type enumeration {
      enum "none" {
        value 0;
        description
          "No Client Config";
      }
      enum "ten-gig-e" {
        value 1;
        description
          "Ten Gig Ether";
      }
      enum "hundred-gig-e" {
        value 2;
        description
          "Hundred Gig Ether";
      }
      enum "otu4" {
        value 3;
        description
          "Hundred Gig OTU4";
      }
      enum "otu2" {
        value 4;
        description
          "Ten Gig OTU2";
      }
      enum "otu2e" {
        value 5;
        description
          "Ten Gig OTU2e";
      }
      enum "otu3" {
        value 6;
        description
          "Forty Gig OTU3";
      }
      enum "forty-gig-e" {
        value 7;
        description
          "Forty Gig Ether";
      }
      enum "four-hundred-gig-e" {
        value 8;
        description
          "FourHundred Gig Ether";
      }
      enum "fibre-channel16g" {
        value 9;
        description
          "Fibre Channel 16G";
      }
      enum "fibre-channel32g" {
        value 10;
        description
          "Fibre Channel 32G";
      }
      enum "sonet" {
        value 11;
        description
          "SONET";
      }
      enum "sdh" {
        value 12;
        description
          "SDH";
      }
      enum "one-gig-e" {
        value 13;
        description
          "One Gig Ether";
      }
      enum "eight-hundred-gig-e" {
        value 14;
        description
          "EightHundred Gig Ether";
      }
      enum "mixed" {
        value 51;
        description
          "Mixed";
      }
    }
    description
      "Slice client bitrate";
  }

  typedef Slice-config-states {
    type enumeration {
      enum "slice-no-config" {
        value 0;
        description
          "Not Provisioned";
      }
      enum "slice-config-in-progress" {
        value 1;
        description
          "Provisioning In Progress";
      }
      enum "slice-config-complete" {
        value 2;
        description
          "Provisioned";
      }
      enum "slice-config-failure" {
        value 3;
        description
          "Provisioning Failed";
      }
      enum "slice-unconfig-in-progress" {
        value 4;
        description
          "Unprovisioning In Progress";
      }
    }
    description
      "Slice config states";
  }

  typedef Slice-trunk-bitrate {
    type enumeration {
      enum "none" {
        value 0;
        description
          "No Trunk Config";
      }
      enum "fifty-gig" {
        value 1;
        description
          "Fifty Gig";
      }
      enum "hundred-gig" {
        value 2;
        description
          "Hundred Gig";
      }
      enum "one-fifty-gig" {
        value 3;
        description
          "One Fifty Gig";
      }
      enum "two-hundred-gig" {
        value 4;
        description
          "Two Hundred Gig";
      }
      enum "two-fifty-gig" {
        value 5;
        description
          "Two Fifty Gig";
      }
      enum "three-hundred-gig" {
        value 6;
        description
          "Three Hundred Gig";
      }
      enum "three-fifty-gig" {
        value 7;
        description
          "Three Fifty Gig";
      }
      enum "four-hundred-gig" {
        value 8;
        description
          "Four Hundred Gig";
      }
      enum "four-fifty-gig" {
        value 9;
        description
          "Four Fifty Gig";
      }
      enum "five-hundred-gig" {
        value 10;
        description
          "Five Hundred Gig";
      }
      enum "five-fifty-gig" {
        value 11;
        description
          "Five Fifty Gig";
      }
      enum "six-hundred-gig" {
        value 12;
        description
          "Six Hundred Gig";
      }
      enum "seven-hundred-gig" {
        value 13;
        description
          "Seven Hundred Gig";
      }
      enum "eight-hundred-gig" {
        value 14;
        description
          "Eight Hundred Gig";
      }
      enum "nine-hundred-gig" {
        value 15;
        description
          "Nine Hundred Gig";
      }
      enum "ten-hundred-gig" {
        value 16;
        description
          "Ten Hundred Gig";
      }
      enum "eleven-hundred-gig" {
        value 17;
        description
          "Eleven Hundred Gig";
      }
      enum "twelve-hundred-gig" {
        value 18;
        description
          "Twelve Hundred Gig";
      }
    }
    description
      "Slice trunk bitrate";
  }

  grouping OSA-HWMOD-MXPONDER-OP {
    description
      "Hwmod Mxponder Information";
    list slice-info {
      description
        "slice info";
      uses HW-MODULE-SLICE-INFO-B;
    }
    list module-info {
      description
        "module info";
      uses HW-MODULE-SLICE-INFO-B;
    }
  }

  grouping OSA-HWMOD-XPONDER-PORT-GROUP-B {
    description
      "Port Group Restrictions Information";
    leaf port-group-id {
      type uint32;
      description
        "PortGroupId";
    }
    leaf port-group-bandwidth {
      type Port-group-bitrate;
      description
        "PortGroupBandwidth";
    }
    list client-port {
      description
        "client port";
      uses OSA-HWMOD-XPONDER-PORT-B;
    }
  }

  grouping CLIENT-RATE-CAPAB-INFO-B {
    description
      "CLIENT RATE CAPAB INFO B";
    leaf client-rate {
      type Slice-client-bitrate;
      description
        "ClientRate";
    }
    leaf capab-type {
      type Capab;
      description
        "CapabType";
    }
  }

  grouping OSA-HWMOD-XPONDER-CLIENT-INFO-B {
    description
      "Client Port Information";
    leaf client-port {
      type string {
        length "0..64";
      }
      description
        "ClientPort";
    }
    list client-rate-capab-info {
      description
        "client rate capab info";
      uses CLIENT-RATE-CAPAB-INFO-B;
    }
  }

  grouping OSA-HWMOD-XPONDER-GRAPH-CAPAB-INFO-B {
    description
      "Hardware capabilities Per Trunk Rate";
    leaf trunk-rate {
      type Slice-trunk-bitrate;
      description
        "TrunkRate";
    }
    list client-info {
      description
        "client info";
      uses OSA-HWMOD-XPONDER-CLIENT-INFO-B;
    }
  }

  grouping OSA-HWMOD-XPONDER-PORT-B {
    description
      "Port Number And Lane Information";
    leaf port-name {
      type string {
        length "0..64";
      }
      description
        "PortName";
    }
  }

  grouping OSA-HWMOD-XPONDER-SLICE-CAPAB-INFO-B {
    description
      "Supported HW Capabilities For A Given Slice";
    list trunk-port {
      description
        "trunk port";
      uses OSA-HWMOD-XPONDER-PORT-B;
    }
    list graph-capab-info {
      description
        "graph capab info";
      uses OSA-HWMOD-XPONDER-GRAPH-CAPAB-INFO-B;
    }
    list port-group-restriction {
      description
        "port group restriction";
      uses OSA-HWMOD-XPONDER-PORT-GROUP-B;
    }
  }

  grouping OSA-HWMOD-REGEN-OP {
    description
      "HWMOD Regen Information";
    list regen-slice-info {
      description
        "regen slice info";
      uses HW-MOD-REGEN-INFO-B;
    }
    list regen-module-info {
      description
        "regen module info";
      uses HW-MOD-REGEN-INFO-B;
    }
  }

  grouping HW-MODULE-SLICE-CLIENT-TRAFFIC-SPLIT-INFO-B {
    description
      "HW MODULE SLICE CLIENT TRAFFIC SPLIT INFO B";
    leaf trunk-name {
      type string {
        length "0..64";
      }
      description
        "TrunkName";
    }
    leaf percentage {
      type uint32;
      description
        "Percentage";
    }
  }

  grouping HW-MODULE-SLICE-CLIENT-PORT-INFO-B {
    description
      "HW MODULE SLICE CLIENT PORT INFO B";
    leaf client-name {
      type string {
        length "0..64";
      }
      description
        "ClientName";
    }
    leaf mapper-name {
      type string;
      description
        "MapperName";
    }
    leaf peer-name {
      type string;
      description
        "PeerName";
    }
    list trunk-port {
      description
        "trunk port";
      uses HW-MODULE-SLICE-CLIENT-TRAFFIC-SPLIT-INFO-B;
    }
  }

  grouping HW-MODULE-SLICE-INFO-B {
    description
      "Hwmod Slice Information";
    leaf client-rate {
      type Slice-client-bitrate;
      description
        "ClientRate";
    }
    leaf trunk-rate {
      type Slice-trunk-bitrate;
      description
        "TrunkRate";
    }
    leaf status {
      type Slice-config-states;
      description
        "Status";
    }
    leaf aps-working {
      type string {
        length "0..20";
      }
      description
        "ApsWorking";
    }
    leaf aps-protection {
      type string {
        length "0..20";
      }
      description
        "ApsProtection";
    }
    leaf-list slice-id-xr {
      type uint32;
      description
        "slice id xr";
    }
    leaf-list lldp-drop-status {
      type boolean;
      description
        "lldp drop status";
    }
    leaf-list mac-snoop-status {
      type boolean;
      description
        "mac snoop status";
    }
    leaf-list isprotection {
      type boolean;
      description
        "isprotection";
    }
    list client-port {
      description
        "client port";
      uses HW-MODULE-SLICE-CLIENT-PORT-INFO-B;
    }
  }

  grouping OSA-HWMOD-LC-STARTUP-CFG-B {
    description
      "LC Startup cfg complete";
    leaf lc-startup-complete {
      type boolean;
      description
        "LcStartupComplete";
    }
  }

  grouping HW-MODULE-EAST-PORT-ASSOCN-INFO-B {
    description
      "East Port Association Information";
    leaf west-port-name {
      type string {
        length "0..64";
      }
      description
        "WestPortName";
    }
  }

  grouping HW-MODULE-REGEN-EAST-PORT-INFO-B {
    description
      "East Port Information";
    container east-port-association {
      description
        "east port association";
      uses HW-MODULE-EAST-PORT-ASSOCN-INFO-B;
    }
    leaf east-port-name {
      type string {
        length "0..64";
      }
      description
        "EastPortName";
    }
  }

  grouping HW-MOD-REGEN-INFO-B {
    description
      "HWMOD Regen Module information";
    leaf trunk-rate {
      type Slice-trunk-bitrate;
      description
        "TrunkRate";
    }
    leaf status {
      type Slice-config-states;
      description
        "Status";
    }
    leaf-list slice-id-xr {
      type uint32;
      description
        "slice id xr";
    }
    list east-port {
      description
        "east port";
      uses HW-MODULE-REGEN-EAST-PORT-INFO-B;
    }
  }
}
