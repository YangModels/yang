module Cisco-IOS-XR-controller-sonet-cfg {
  namespace "http://cisco.com/ns/yang/Cisco-IOS-XR-controller-sonet-cfg";
  prefix controller-sonet-cfg;

  import Cisco-IOS-XR-types {
    prefix xr;
  }
  import cisco-semver {
    prefix semver;
  }
  import Cisco-IOS-XR-ifmgr-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR controller-sonet package configuration.
     
     This YANG module augments the
       Cisco-IOS-XR-ifmgr-cfg
     module with configuration data.
     
     Copyright (c) 2013-2022 by Cisco Systems, Inc.
     All rights reserved.";

  revision 2022-12-08 {
    description
      "Addition of leaf related to SFP TDM alarm propagation.";
    semver:module-version "1.0.0";
  }
  revision 2022-02-15 {
    description
      "64 byte mode added to SONETOverheadJ0Byte, maximum length of string accepted";
  }
  revision 2022-02-02 {
    description
      "Leaves prbs-framing, prbs-direction, prbs-err-inject and user-pattern made mandatory";
  }
  revision 2022-01-12 {
    description
      "Added cfg Schema for STM controller";
  }
  revision 2019-04-05 {
    description
      "Establish semantic version baseline.";
  }
  revision 2015-11-09 {
    description
      "IOS XR 6.0 revision.";
  }

  typedef Sonet-ma-clock-source {
    type enumeration {
      enum "internal" {
        value 0;
        description
          "Internal";
      }
      enum "line" {
        value 1;
        description
          "Line";
      }
    }
    description
      "Sonet ma clock source";
  }

  typedef Sonet-prbs-pattern {
    type enumeration {
      enum "pn31" {
        value 1;
        description
          "PRBS pattern pn31";
      }
      enum "pn23" {
        value 2;
        description
          "PRBS pattern pn23";
      }
      enum "pn15" {
        value 3;
        description
          "PRBS pattern pn15";
      }
      enum "pn11" {
        value 4;
        description
          "PRBS pattern pn11";
      }
      enum "pn9" {
        value 5;
        description
          "PRBS pattern pn9";
      }
      enum "pn7" {
        value 6;
        description
          "PRBS pattern pn7";
      }
      enum "pattern-user-defined" {
        value 7;
        description
          "user-defined prbs pattern(64-bit hex value)";
      }
    }
    description
      "Sonet prbs pattern";
  }

  typedef Mapping {
    type enumeration {
      enum "e1" {
        value 5;
        description
          "Mapping type E1";
      }
    }
    description
      "Mapping";
  }

  typedef Sonet-overhead-j1-byte {
    type enumeration {
      enum "16-byte" {
        value 2;
        description
          "16 Byte overhead";
      }
      enum "64-byte" {
        value 3;
        description
          "64 Byte Overhead";
      }
    }
    description
      "Sonet overhead j1 byte";
  }

  typedef Sonet-perf-mon {
    type enumeration {
      enum "enable" {
        value 0;
        description
          "Enable";
      }
      enum "disable" {
        value 1;
        description
          "Disable";
      }
    }
    description
      "Sonet perf mon";
  }

  typedef Tug3mode {
    type enumeration {
      enum "tug2" {
        value 4;
        description
          "Mode TUG2 (Tributary Unit Group TUG-2";
      }
    }
    description
      "Tug3mode";
  }

  typedef Augmodetug {
    type enumeration {
      enum "tug3" {
        value 3;
        description
          "Tributary Unit Group (TUG3)";
      }
    }
    description
      "Augmodetug";
  }

  typedef Mappingau4 {
    type enumeration {
      enum "au4" {
        value 1;
        description
          "aug map AU4";
      }
    }
    description
      "Mappingau4";
  }

  typedef Sonet-prbs-mode {
    type enumeration {
      enum "source" {
        value 1;
        description
          "PRBS source mode";
      }
      enum "sink" {
        value 2;
        description
          "PRBS sink mode";
      }
      enum "source-sink" {
        value 3;
        description
          "PRBS source-sink mode";
      }
    }
    description
      "Sonet prbs mode";
  }

  typedef Sonet-overhead-j0-byte {
    type enumeration {
      enum "1byte" {
        value 1;
        description
          "1 Byte overhead";
      }
      enum "16-byte" {
        value 2;
        description
          "16 Byte Overhead";
      }
      enum "64-byte" {
        value 3;
        description
          "64 Byte Overhead";
      }
    }
    description
      "Sonet overhead j0 byte";
  }

  typedef Sonet-prbs-framing {
    type enumeration {
      enum "none" {
        value 0;
        description
          "No framing config";
      }
      enum "frame-d" {
        value 1;
        description
          "PRBS framed";
      }
      enum "unframed" {
        value 2;
        description
          "PRBS unframed";
      }
    }
    description
      "Sonet prbs framing";
  }

  typedef Extended-sonet-loopback {
    type enumeration {
      enum "internal" {
        value 1;
        description
          "Internal loopback";
      }
      enum "line" {
        value 2;
        description
          "Line loopback";
      }
    }
    description
      "Extended sonet loopback";
  }

  typedef Payloadmode {
    type enumeration {
      enum "vc12" {
        value 5;
        description
          "Payload type VC12(Virtual Container)";
      }
    }
    description
      "Payloadmode";
  }

  typedef Sonet-prbs-direction {
    type enumeration {
      enum "none" {
        value 0;
        description
          "No direction config";
      }
      enum "line" {
        value 1;
        description
          "PRBS line";
      }
      enum "system" {
        value 2;
        description
          "PRBS system";
      }
    }
    description
      "Sonet prbs direction";
  }

  typedef Sonet-prbs-err-inject {
    type enumeration {
      enum "none" {
        value 0;
        description
          "No error-inject config";
      }
      enum "single" {
        value 1;
        description
          "PRBS single error injection";
      }
      enum "continuous" {
        value 2;
        description
          "PRBS continuous error injection";
      }
    }
    description
      "Sonet prbs err inject";
  }

  augment "/a1:interface-configurations/a1:interface-configuration" {
    description
      "This augment extends the configuration data of
       'Cisco-IOS-XR-ifmgr-cfg'";
    container sts {
      description
        "SONET path controller configuration";
      container sts-overhead {
        description
          "Specify Overhead value ";
        container sts-overhead-j1-expected {
          description
            "Specify J1 Expected value ";
          leaf overhead-byte {
            type Sonet-overhead-j1-byte;
            description
              "No of Overhead Byte";
          }
          leaf ascii-string {
            type string {
              length "1..62";
            }
            description
              "ASCII text (Max 15 characters for 16 Bytes
               and 62 for 64 Bytes)";
          }
        }
        container sts-overhead-j1-send {
          description
            "Specify J1 Send value ";
          leaf overhead-byte {
            type Sonet-overhead-j1-byte;
            description
              "No of Overhead Byte";
          }
          leaf ascii-string {
            type string {
              length "1..62";
            }
            description
              "ASCII text (Max 15 characters for 16 Bytes
               and 62 for 64 Bytes)";
          }
        }
      }
      leaf threshold-b3-ber {
        type uint32 {
          range "3..9";
        }
        default "6";
        description
          "Configure B3 BER Threshold Crossing Alert (TCA)
           reporting";
      }
      leaf sts-perf-mon {
        type Sonet-perf-mon;
        default "enable";
        description
          "Enable/Disable Performance Monitoring";
      }
    }
  }
  augment "/a1:interface-configurations/a1:interface-configuration" {
    description
      "This augment extends the configuration data of
       'Cisco-IOS-XR-ifmgr-cfg'";
    container vc {
      description
        "SDH path controller configuration";
      container vc-overhead {
        description
          "Specify Overhead value ";
        container vc-overhead-j1-expected {
          description
            "Specify J1 Expected value ";
          leaf overhead-byte {
            type Sonet-overhead-j1-byte;
            description
              "No of Overhead Byte";
          }
          leaf ascii-string {
            type string {
              length "1..62";
            }
            description
              "ASCII text (Max 15 characters for 16 Bytes
               and 62 for 64 Bytes)";
          }
        }
        container vc-overhead-j1-send {
          description
            "Specify J1 Send value ";
          leaf overhead-byte {
            type Sonet-overhead-j1-byte;
            description
              "No of Overhead Byte";
          }
          leaf ascii-string {
            type string {
              length "1..62";
            }
            description
              "ASCII text (Max 15 characters for 16 Bytes
               and 62 for 64 Bytes)";
          }
        }
      }
      leaf threshold-b3-ber {
        type uint32 {
          range "3..9";
        }
        default "6";
        description
          "Configure B3 BER Threshold Crossing Alert (TCA)
           reporting";
      }
      leaf sts-perf-mon {
        type Sonet-perf-mon;
        default "enable";
        description
          "Enable/Disable Performance Monitoring";
      }
    }
  }
  augment "/a1:interface-configurations/a1:interface-configuration" {
    description
      "This augment extends the configuration data of
       'Cisco-IOS-XR-ifmgr-cfg'";
    container stm {
      description
        "SDH port controller configuration";
      container stm-overhead {
        description
          "Specify Overhead value ";
        container stm-overhead-j0-expected {
          presence "Indicates a stm-overhead-j0-expected node is configured.";
          description
            "Specify J0 Expected value ";
          leaf overhead-byte {
            type Sonet-overhead-j0-byte;
            description
              "No of Overhead Byte";
          }
          leaf ascii-string {
            type string {
              length "1..62";
            }
            mandatory true;
            description
              "ASCII text (Max 15 characters for 16 Byte and
               62 characters for 64 Byte) pass NULL for 1
               Byte";
          }
          leaf byte-value {
            type uint32 {
              range "0..255";
            }
            mandatory true;
            description
              "expected j0 byte (pass 0 for 16Bytes and
               64Bytes)";
          }
        }
        container stm-overhead-j0-send {
          presence "Indicates a stm-overhead-j0-send node is configured.";
          description
            "Specify J0 Send value ";
          leaf overhead-byte {
            type Sonet-overhead-j0-byte;
            description
              "No of Overhead Byte";
          }
          leaf ascii-string {
            type string {
              length "1..62";
            }
            mandatory true;
            description
              "ASCII text (Max 15 characters for 16 Byte and
               62 characters for 64 Byte) pass NULL for 1
               Byte";
          }
          leaf byte-value {
            type uint32 {
              range "0..255";
            }
            mandatory true;
            description
              "transmit j0 byte (pass 0 for 16Byte)";
          }
        }
      }
      container prbs {
        presence "Indicates a prbs node is configured.";
        description
          "Configure Pseudo Random Binary Sequence";
        leaf prbs-mode {
          type Sonet-prbs-mode;
          mandatory true;
          description
            "PRBS Mode";
        }
        leaf prbs-pattern {
          type Sonet-prbs-pattern;
          mandatory true;
          description
            "PRBS Pattern";
        }
        leaf prbs-framing {
          type Sonet-prbs-framing;
          mandatory true;
          description
            "PRBS Framing";
        }
        leaf prbs-direction {
          type Sonet-prbs-direction;
          mandatory true;
          description
            "PRBS Direction";
        }
        leaf prbs-err-inject {
          type Sonet-prbs-err-inject;
          mandatory true;
          description
            "PRBS Error Injection";
        }
        leaf user-pattern {
          type xr:Hex-long-integer;
          mandatory true;
          description
            "PRBS user defined pattern(64-bit hex value)";
        }
      }
      container extended-loopbacks {
        description
          "Configure STM Extended loopback (diagnostics)";
        list extended-loopback {
          key "level";
          description
            "Configure extended loopback mode";
          leaf level {
            type uint32 {
              range "1..3";
            }
            description
              "Level";
          }
          leaf loopback {
            type Extended-sonet-loopback;
            mandatory true;
            description
              "Loopback";
          }
        }
      }
      leaf threshold-sd-ber {
        type uint32 {
          range "5..9";
        }
        default "6";
        description
          "Configure Signal Degrade BER threshold";
      }
      leaf threshold-b1-tca {
        type uint32 {
          range "3..9";
        }
        default "6";
        description
          "Configure B1 BER Threshold Crossing Alert (TCA)
           threshold";
      }
      leaf loopback {
        type string;
        description
          "STM port loopback mode:internal - Select local
           (terminal) loopback,line - Select network
           (facility) loopback";
      }
      leaf threshold-b2-tca {
        type uint32 {
          range "3..9";
        }
        default "6";
        description
          "Configure B2 BER Threshold Crossing Alert (TCA)
           threshold";
      }
      leaf threshold-sf-ber {
        type uint32 {
          range "3..5";
        }
        default "3";
        description
          "Configure Signal Fail BER threshold";
      }
      leaf clock-source {
        type Sonet-ma-clock-source;
        default "line";
        description
          "Configure SDH port Transmit clock source";
      }
      leaf perf-mon {
        type Sonet-perf-mon;
        default "enable";
        description
          "Enable/Disable Performance Monitoring";
      }
    }
  }
  augment "/a1:interface-configurations/a1:interface-configuration" {
    description
      "This augment extends the configuration data of
       'Cisco-IOS-XR-ifmgr-cfg'";
    container oc {
      description
        "SONET port controller configuration";
      container oc-overhead {
        description
          "Specify Overhead value ";
        container oc-overhead-j0-expected {
          presence "Indicates a oc-overhead-j0-expected node is configured.";
          description
            "Specify J0 Expected value ";
          leaf overhead-byte {
            type Sonet-overhead-j0-byte;
            description
              "No of Overhead Byte";
          }
          leaf ascii-string {
            type string {
              length "1..62";
            }
            mandatory true;
            description
              "ASCII text (Max 15 characters for 16 Byte and
               62 characters for 64 Byte) pass NULL for 1
               Byte";
          }
          leaf byte-value {
            type uint32 {
              range "0..255";
            }
            mandatory true;
            description
              "expected j0 byte (pass 0 for 16Bytes and
               64Bytes)";
          }
        }
        container oc-overhead-j0-send {
          presence "Indicates a oc-overhead-j0-send node is configured.";
          description
            "Specify J0 Send value ";
          leaf overhead-byte {
            type Sonet-overhead-j0-byte;
            description
              "No of Overhead Byte";
          }
          leaf ascii-string {
            type string {
              length "1..62";
            }
            mandatory true;
            description
              "ASCII text (Max 15 characters for 16 Byte and
               62 characters for 64 Byte) pass NULL for 1
               Byte";
          }
          leaf byte-value {
            type uint32 {
              range "0..255";
            }
            mandatory true;
            description
              "transmit j0 byte (pass 0 for 16Byte)";
          }
        }
      }
      container extended-loopbacks {
        description
          "Configure OC Extended loopback (diagnostics)";
        list extended-loopback {
          key "level";
          description
            "Configure extended loopback mode";
          leaf level {
            type uint32 {
              range "1..3";
            }
            description
              "Level";
          }
          leaf loopback {
            type Extended-sonet-loopback;
            mandatory true;
            description
              "Loopback";
          }
        }
      }
      container prbs {
        presence "Indicates a prbs node is configured.";
        description
          "Configure Pseudo Random Binary Sequence";
        leaf prbs-mode {
          type Sonet-prbs-mode;
          mandatory true;
          description
            "PRBS Mode";
        }
        leaf prbs-pattern {
          type Sonet-prbs-pattern;
          mandatory true;
          description
            "PRBS Pattern";
        }
        leaf prbs-framing {
          type Sonet-prbs-framing;
          mandatory true;
          description
            "PRBS Framing";
        }
        leaf prbs-direction {
          type Sonet-prbs-direction;
          mandatory true;
          description
            "PRBS Direction";
        }
        leaf prbs-err-inject {
          type Sonet-prbs-err-inject;
          mandatory true;
          description
            "PRBS Error Injection";
        }
        leaf user-pattern {
          type xr:Hex-long-integer;
          mandatory true;
          description
            "PRBS user defined pattern(64-bit hex value)";
        }
      }
      leaf propagate-tdm-alarm {
        type empty;
        description
          "Configure SFP TDM alarm propagation.";
      }
      leaf threshold-sd-ber {
        type uint32 {
          range "5..9";
        }
        default "6";
        description
          "Configure Signal Degrade BER threshold";
      }
      leaf threshold-b1-tca {
        type uint32 {
          range "3..9";
        }
        default "6";
        description
          "Configure B1 BER Threshold Crossing Alert (TCA)
           threshold";
      }
      leaf loopback {
        type string;
        description
          "OC port loopback mode:internal - Select local
           (terminal) loopback,line - Select network
           (facility) loopback";
      }
      leaf threshold-b2-tca {
        type uint32 {
          range "3..9";
        }
        default "6";
        description
          "Configure B2 BER Threshold Crossing Alert (TCA)
           threshold";
      }
      leaf threshold-sf-ber {
        type uint32 {
          range "3..5";
        }
        default "3";
        description
          "Configure Signal Fail BER threshold";
      }
      leaf clock-source {
        type Sonet-ma-clock-source;
        default "line";
        description
          "Configure SONET port Transmit clock source";
      }
      leaf perf-mon {
        type Sonet-perf-mon;
        default "enable";
        description
          "Enable/Disable Performance Monitoring";
      }
    }
  }
  augment "/a1:interface-configurations/a1:interface-configuration" {
    description
      "This augment extends the configuration data of
       'Cisco-IOS-XR-ifmgr-cfg'";
    container stm-cfg {
      description
        "SONET port controller configuration";
      container au4s {
        description
          "Configure Administrative Unit Group(AUG) for
           STM controller";
        list au4 {
          key "augmap";
          description
            "Mapping type AU4";
          leaf augmap {
            type Mappingau4;
            description
              "mapping type AU4";
          }
          list au-4 {
            key "au4number";
            description
              "AU4 number";
            leaf au4number {
              type uint32 {
                range "1";
              }
              description
                "select au4number";
            }
            list mode {
              key "aumode";
              description
                "Configure mode for this Auxilary Unit 4(AU4)";
              leaf aumode {
                type Augmodetug;
                description
                  "au mode";
              }
              list tug3-id {
                key "tug3idnumber";
                description
                  "(TUG-3 id)";
                leaf tug3idnumber {
                  type uint32 {
                    range "1..3";
                  }
                  description
                    "select tug3id number";
                }
                list tug3-mode {
                  key "tug3mode";
                  description
                    "TUG-3 mode (Tributary Unit Group (TUG-n))";
                  leaf tug3mode {
                    type Tug3mode;
                    description
                      "tug 3 mode type";
                  }
                  list tug2-id {
                    key "tug2number";
                    description
                      "Configure TUG-2";
                    leaf tug2number {
                      type uint32 {
                        range "1..7";
                      }
                      description
                        "TUG2 Number";
                    }
                    list payload {
                      key "payloadtype";
                      description
                        "Configure payload type";
                      leaf payloadtype {
                        type Payloadmode;
                        description
                          "Payload type";
                      }
                      list vc12 {
                        key "vc12-number";
                        description
                          "Configure VC12 type Virtual Container";
                        leaf mapping {
                          type Mapping;
                          description
                            "Configure mapping for this VC(Virtual
                             Container)";
                        }
                        leaf vc12-number {
                          type uint32 {
                            range "1..3";
                          }
                          description
                            "Select VC12 number";
                        }
                      }
                    }
                  }
                }
              }
            }
          }
        }
      }
    }
  }
}
